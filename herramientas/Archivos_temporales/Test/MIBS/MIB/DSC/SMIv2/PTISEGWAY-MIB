--
-- This SMIv2 module has been generated by smidump 0.2-cvs. Do not edit.
--

PTISEGWAY-MIB DEFINITIONS ::= BEGIN

IMPORTS
    Integer32, MODULE-IDENTITY, NOTIFICATION-TYPE, OBJECT-TYPE, 
    enterprises
        FROM SNMPv2-SMI
    DisplayString, RowStatus
        FROM SNMPv2-TC
    laLoad, memTotalFree
        FROM UCD-SNMP-MIB;

ptiSegway MODULE-IDENTITY
    LAST-UPDATED    "202004092025Z"
    ORGANIZATION    
            "www.pt.com"
    CONTACT-INFO    
            "Enter address"
    DESCRIPTION     
            "ptiSegway product MIB objects"
    REVISION        "201303140000Z"
    DESCRIPTION     
            "Initial release"
    ::= { pti 17 }


pti OBJECT IDENTIFIER
    ::= { enterprises 1556 }

ptConnGroup OBJECT IDENTIFIER
    ::= { ptiSegway 15 }

ptConnGroupTable OBJECT-TYPE
    SYNTAX          SEQUENCE OF PtConnGroupEntry
    MAX-ACCESS      not-accessible
    STATUS          current
    DESCRIPTION     
            "This is the ConnGroup type of the elements underneath."
    ::= { ptConnGroup 1 }

ptConnGroupEntry OBJECT-TYPE
    SYNTAX          PtConnGroupEntry
    MAX-ACCESS      not-accessible
    STATUS          current
    DESCRIPTION     
            "A sequence of ConnGroup attributes."
    INDEX           { ptConnGroupIndex }
    ::= { ptConnGroupTable 1 }

PtConnGroupEntry ::=
    SEQUENCE {
        ptConnGroupIndex                Integer32
    }

ptConnGroupIndex OBJECT-TYPE
    SYNTAX          Integer32 (-2147483648..2147483647)
    MAX-ACCESS      read-only
    STATUS          current
    DESCRIPTION     
            "The row number for the ConnGroup table"
    ::= { ptConnGroupEntry 255 }

ptMTPMTP3NAManager OBJECT IDENTIFIER
    ::= { ptConnGroup 46 }

ptMTPMTP3NAManagerTable OBJECT-TYPE
    SYNTAX          SEQUENCE OF PtMTPMTP3NAManagerEntry
    MAX-ACCESS      not-accessible
    STATUS          current
    DESCRIPTION     
            "No description supplied in the proxy config file."
    ::= { ptMTPMTP3NAManager 1 }

ptMTPMTP3NAManagerEntry OBJECT-TYPE
    SYNTAX          PtMTPMTP3NAManagerEntry
    MAX-ACCESS      not-accessible
    STATUS          current
    DESCRIPTION     
            "A sequence of MTPMTP3NAManager attributes."
    INDEX           { ptConnGroupIndex, ptMTPMTP3NAManagerIndex }
    ::= { ptMTPMTP3NAManagerTable 1 }

PtMTPMTP3NAManagerEntry ::=
    SEQUENCE {
        ptMTPMTP3NAManagerNADebugLevel  Integer32,
        ptMTPMTP3NAManagerLDLDebugLevel Integer32,
        ptMTPMTP3NAManagerSCTPDebugLevel Integer32,
        ptMTPMTP3NAManagerLDLSCTPDebugLevel   Integer32,
        ptMTPMTP3NAManagerMSUQueueDepth Integer32,
        ptMTPMTP3NAManagerTimeCongOnset1 INTEGER,
        ptMTPMTP3NAManagerTimeCongOnset2 INTEGER,
        ptMTPMTP3NAManagerTimeCongOnset3 INTEGER,
        ptMTPMTP3NAManagerTelemetryDiagnostics      INTEGER,
        ptMTPMTP3NAManagerActions       INTEGER,
        ptMTPMTP3NAManagerParentOID     OBJECT IDENTIFIER,
        ptMTPMTP3NAManagerRowStatus     RowStatus,
        ptMTPMTP3NAManagerIndex         Integer32
    }

ptMTPMTP3NAManagerNADebugLevel OBJECT-TYPE
    SYNTAX          Integer32 (-2147483648..2147483647)
    MAX-ACCESS      read-create
    STATUS          current
    DESCRIPTION     
            "MTP3 NA Debug Level (0 - 255). \nSystem wide MTP3 related events will be traced and logged to the Debug Log. \nPlease do not change the NA Debug Level attribute unless instructed by support as increased logging beyond default setting may adversly impact performance. \nDefault value: 1."
    ::= { ptMTPMTP3NAManagerEntry 1 }

ptMTPMTP3NAManagerLDLDebugLevel OBJECT-TYPE
    SYNTAX          Integer32 (-2147483648..2147483647)
    MAX-ACCESS      read-create
    STATUS          current
    DESCRIPTION     
            "MTP3 LDL Debug Level (0 - 255). \nLayer Distribtion Library (LDL) related events will be traced and logged to the Debug Log. \nPlease do not change the LDL Debug Level attribute unless instructed by support as increased logging beyond default setting may adversly impact performance. \nDefault value: 2."
    ::= { ptMTPMTP3NAManagerEntry 2 }

ptMTPMTP3NAManagerSCTPDebugLevel OBJECT-TYPE
    SYNTAX          Integer32 (-2147483648..2147483647)
    MAX-ACCESS      read-create
    STATUS          current
    DESCRIPTION     
            "MTP3 SCTP Debug Level (0 - 255). \nSCTP related events will be traced and logged to the Debug Log. \nPlease do not change the SCTP Debug Level attribute unless instructed by support as increased logging beyond default setting may adversly impact performance. \nDefault value: 0. \nObsolete as of 15.1.0 for LK SCTP deployments."
    ::= { ptMTPMTP3NAManagerEntry 3 }

ptMTPMTP3NAManagerLDLSCTPDebugLevel OBJECT-TYPE
    SYNTAX          Integer32 (-2147483648..2147483647)
    MAX-ACCESS      read-create
    STATUS          current
    DESCRIPTION     
            "MTP3 LDL SCTP Debug Level (0 - 255). \nLDL SCTP related events will be traced and logged to the Debug Log. \nPlease do not change the LDL SCTP Debug Level attribute unless instructed by support as increased logging beyond default setting may adversly impact performance. \nDefault value: 0. \nObsolete as of 15.1.0 for LK SCTP deployments."
    ::= { ptMTPMTP3NAManagerEntry 4 }

ptMTPMTP3NAManagerMSUQueueDepth OBJECT-TYPE
    SYNTAX          Integer32 (50000..2000000)
    MAX-ACCESS      read-create
    STATUS          current
    DESCRIPTION     
            " Please do not change these parameters unless instructed by customer support. \nThe parameters on this page affect the queueing of MSUs between processes, especially between DREs. Configuring the queues to be too small may result in the queues overflowing under normal conditions, hence resulting in unnecessary MSU loss. Configuring the queues to be too large can result in problems during overload, including long delay in MSUs delivery, possible MSU missequencing, and possibly exceeding system resources. \nThe queues have the following configurable thresholds: \n * The MSU threshold is the most MSUs that will be queued before the queue is considered full. Any further MSUs requiring queueing are discarded until space opens in the queue. \n * The time-based thresholds indicate the age beyond which MSUs in the queue should be considered obsolete and should be discarded to shed work. Setting this value higher that time-controlled changeover (T1) or changeback timer (T3) values could result in MSU missequencing if these procedures are executed during heavy overload conditions. This parameter has three levels and should satisfy Onset 1 <= Onset 2 <= Onset 3. Onset levels 1 and 2 generate log warnings, Onset 3 begins discarding MSUs."
    ::= { ptMTPMTP3NAManagerEntry 5 }

ptMTPMTP3NAManagerTimeCongOnset1 OBJECT-TYPE
    SYNTAX          INTEGER { default(-1) }
    MAX-ACCESS      read-create
    STATUS          current
    DESCRIPTION     
            " Please do not change these parameters unless instructed by customer support. \nThe parameters on this page affect the queueing of MSUs between processes, especially between DREs. Configuring the queues to be too small may result in the queues overflowing under normal conditions, hence resulting in unnecessary MSU loss. Configuring the queues to be too large can result in problems during overload, including long delay in MSUs delivery, possible MSU missequencing, and possibly exceeding system resources. \nThe queues have the following configurable thresholds: \n * The MSU threshold is the most MSUs that will be queued before the queue is considered full. Any further MSUs requiring queueing are discarded until space opens in the queue. \n * The time-based thresholds indicate the age beyond which MSUs in the queue should be considered obsolete and should be discarded to shed work. Setting this value higher that time-controlled changeover (T1) or changeback timer (T3) values could result in MSU missequencing if these procedures are executed during heavy overload conditions. This parameter has three levels and should satisfy Onset 1 <= Onset 2 <= Onset 3. Onset levels 1 and 2 generate log warnings, Onset 3 begins discarding MSUs."
    ::= { ptMTPMTP3NAManagerEntry 7 }

ptMTPMTP3NAManagerTimeCongOnset2 OBJECT-TYPE
    SYNTAX          INTEGER { default(-1) }
    MAX-ACCESS      read-create
    STATUS          current
    DESCRIPTION     
            " Please do not change these parameters unless instructed by customer support. \nThe parameters on this page affect the queueing of MSUs between processes, especially between DREs. Configuring the queues to be too small may result in the queues overflowing under normal conditions, hence resulting in unnecessary MSU loss. Configuring the queues to be too large can result in problems during overload, including long delay in MSUs delivery, possible MSU missequencing, and possibly exceeding system resources. \nThe queues have the following configurable thresholds: \n * The MSU threshold is the most MSUs that will be queued before the queue is considered full. Any further MSUs requiring queueing are discarded until space opens in the queue. \n * The time-based thresholds indicate the age beyond which MSUs in the queue should be considered obsolete and should be discarded to shed work. Setting this value higher that time-controlled changeover (T1) or changeback timer (T3) values could result in MSU missequencing if these procedures are executed during heavy overload conditions. This parameter has three levels and should satisfy Onset 1 <= Onset 2 <= Onset 3. Onset levels 1 and 2 generate log warnings, Onset 3 begins discarding MSUs."
    ::= { ptMTPMTP3NAManagerEntry 8 }

ptMTPMTP3NAManagerTimeCongOnset3 OBJECT-TYPE
    SYNTAX          INTEGER { default(-1) }
    MAX-ACCESS      read-create
    STATUS          current
    DESCRIPTION     
            " Please do not change these parameters unless instructed by customer support. \nThe parameters on this page affect the queueing of MSUs between processes, especially between DREs. Configuring the queues to be too small may result in the queues overflowing under normal conditions, hence resulting in unnecessary MSU loss. Configuring the queues to be too large can result in problems during overload, including long delay in MSUs delivery, possible MSU missequencing, and possibly exceeding system resources. \nThe queues have the following configurable thresholds: \n * The MSU threshold is the most MSUs that will be queued before the queue is considered full. Any further MSUs requiring queueing are discarded until space opens in the queue. \n * The time-based thresholds indicate the age beyond which MSUs in the queue should be considered obsolete and should be discarded to shed work. Setting this value higher that time-controlled changeover (T1) or changeback timer (T3) values could result in MSU missequencing if these procedures are executed during heavy overload conditions. This parameter has three levels and should satisfy Onset 1 <= Onset 2 <= Onset 3. Onset levels 1 and 2 generate log warnings, Onset 3 begins discarding MSUs."
    ::= { ptMTPMTP3NAManagerEntry 9 }

ptMTPMTP3NAManagerTelemetryDiagnostics OBJECT-TYPE
    SYNTAX          INTEGER { notLogged(0), logged(1) }
    MAX-ACCESS      read-create
    STATUS          current
    DESCRIPTION     
            "If the Debug Telemetry Diagnostics flag is set to LOGGED, then information concerning DRE telemetry diagnostics data will be sent to the Debug log file every minute. \n The recommended default setting of this flag is LOGGED, so that the user could monitor the telemetry data."
    ::= { ptMTPMTP3NAManagerEntry 16 }

ptMTPMTP3NAManagerActions OBJECT-TYPE
    SYNTAX          INTEGER { restoreDebugDefaults(1) }
    MAX-ACCESS      read-create
    STATUS          current
    DESCRIPTION     
            "The OID of all possible actions for this instance"
    ::= { ptMTPMTP3NAManagerEntry 252 }

ptMTPMTP3NAManagerParentOID OBJECT-TYPE
    SYNTAX          OBJECT IDENTIFIER
    MAX-ACCESS      read-create
    STATUS          current
    DESCRIPTION     
            "The OID of the parent object for this instance"
    ::= { ptMTPMTP3NAManagerEntry 253 }

ptMTPMTP3NAManagerRowStatus OBJECT-TYPE
    SYNTAX          RowStatus
    MAX-ACCESS      read-create
    STATUS          current
    DESCRIPTION     
            "The row status for the MTPMTP3NAManager table"
    ::= { ptMTPMTP3NAManagerEntry 254 }

ptMTPMTP3NAManagerIndex OBJECT-TYPE
    SYNTAX          Integer32 (-2147483648..2147483647)
    MAX-ACCESS      not-accessible
    STATUS          current
    DESCRIPTION     
            "The row number for the MTPMTP3NAManager table"
    ::= { ptMTPMTP3NAManagerEntry 255 }

ptMTPMTP3NA OBJECT IDENTIFIER
    ::= { ptMTPMTP3NAManager 65 }

ptMTPMTP3NATable OBJECT-TYPE
    SYNTAX          SEQUENCE OF PtMTPMTP3NAEntry
    MAX-ACCESS      not-accessible
    STATUS          current
    DESCRIPTION     
            "A sequence of signaling node attributes used for the configuration 
             of the Network Appearance (NA). Actions to Activate and Deactivate 
             the NA also appear in these screen."
    ::= { ptMTPMTP3NA 1 }

ptMTPMTP3NAEntry OBJECT-TYPE
    SYNTAX          PtMTPMTP3NAEntry
    MAX-ACCESS      not-accessible
    STATUS          current
    DESCRIPTION     
            "A sequence of MTPMTP3NA attributes."
    INDEX           { ptConnGroupIndex, ptMTPMTP3NAMTP3NAManagerIndex, 
                      ptMTPMTP3NAIndex }
    ::= { ptMTPMTP3NATable 1 }

PtMTPMTP3NAEntry ::=
    SEQUENCE {
        ptMTPMTP3NAContext              DisplayString,
        ptMTPMTP3NALocalPointCode       Integer32,
        ptMTPMTP3NASS7NodeType          INTEGER,
        ptMTPMTP3NASS7Variant           INTEGER,
        ptMTPMTP3NANetworkIndicator     INTEGER,
        ptMTPMTP3NAStatus               INTEGER,
        ptMTPMTP3NACLLI                 DisplayString,
        ptMTPMTP3NANetworkAppearance    Integer32,
        ptMTPMTP3NAActiveSNMSlot        Integer32,
        ptMTPMTP3NASLSSize              INTEGER,
        ptMTPMTP3NARotateSLS            INTEGER,
        ptMTPMTP3NAL4ConnectionPort     Integer32,
        ptMTPMTP3NAGenerateUPU          INTEGER,
        ptMTPMTP3NALocalMTPRestartSupport INTEGER,
        ptMTPMTP3NAPCNumberingValidation INTEGER,
        ptMTPMTP3NASpareSSFBits         INTEGER,
        ptMTPMTP3NAMateSTP              Integer32,
        ptMTPMTP3NAVNodeFeature         INTEGER,
        ptMTPMTP3NARoutingFeature       INTEGER,
        ptMTPMTP3NAR48Compliance        INTEGER,
        ptMTPMTP3NADebug                INTEGER,
        ptMTPMTP3NAErrors               INTEGER,
        ptMTPMTP3NASNMManagement        INTEGER,
        ptMTPMTP3NAPeerAdministration   INTEGER,
        ptMTPMTP3NAL2Connection         INTEGER,
        ptMTPMTP3NADREConnection        INTEGER,
        ptMTPMTP3NADREAdministration    INTEGER,
        ptMTPMTP3NADRESwitchover        INTEGER,
        ptMTPMTP3NASetup                INTEGER,
        ptMTPMTP3NAOtherTimers          INTEGER,
        ptMTPMTP3NAReroutingProcedure   INTEGER,
        ptMTPMTP3NACOCBProcedure        INTEGER,
        ptMTPMTP3NALinkStatus           INTEGER,
        ptMTPMTP3NAL2Messages           INTEGER,
        ptMTPMTP3NAUserManagement       INTEGER,
        ptMTPMTP3NAUserPrimitives       INTEGER,
        ptMTPMTP3NAMSUTraffic           INTEGER,
        ptMTPMTP3NAMSUTrafficRaw        INTEGER,
        ptMTPMTP3NASLT                  INTEGER,
        ptMTPMTP3NASLSTables            INTEGER,
        ptMTPMTP3NAL3T1                 INTEGER,
        ptMTPMTP3NAL3T2                 INTEGER,
        ptMTPMTP3NAL3T3                 INTEGER,
        ptMTPMTP3NAL3T4                 INTEGER,
        ptMTPMTP3NAL3T5                 INTEGER,
        ptMTPMTP3NAL3T6                 INTEGER,
        ptMTPMTP3NAL3T7                 INTEGER,
        ptMTPMTP3NAL3T8                 INTEGER,
        ptMTPMTP3NAL3T10                INTEGER,
        ptMTPMTP3NAL3T11                INTEGER,
        ptMTPMTP3NAL3T12                INTEGER,
        ptMTPMTP3NAL3T13                INTEGER,
        ptMTPMTP3NAL3T14                INTEGER,
        ptMTPMTP3NAL3T15                INTEGER,
        ptMTPMTP3NAL3T16                INTEGER,
        ptMTPMTP3NAL3T17                INTEGER,
        ptMTPMTP3NAL3T18                INTEGER,
        ptMTPMTP3NAL3T19                INTEGER,
        ptMTPMTP3NAL3T20                INTEGER,
        ptMTPMTP3NAL3T21                INTEGER,
        ptMTPMTP3NAL3T22                INTEGER,
        ptMTPMTP3NAL3T23                INTEGER,
        ptMTPMTP3NAL3T24                INTEGER,
        ptMTPMTP3NAL3T25                INTEGER,
        ptMTPMTP3NAL3T26                INTEGER,
        ptMTPMTP3NAL3T27                INTEGER,
        ptMTPMTP3NAL3T28                INTEGER,
        ptMTPMTP3NAL3T29                INTEGER,
        ptMTPMTP3NAL3T30                INTEGER,
        ptMTPMTP3NAL3T31                INTEGER,
        ptMTPMTP3NAL3T32                INTEGER,
        ptMTPMTP3NAL3T33                INTEGER,
        ptMTPMTP3NAL3T34                INTEGER,
        ptMTPMTP3NAXListLifespan        INTEGER,
        ptMTPMTP3NASLTSI                INTEGER,
        ptMTPMTP3NASLTMPattern          DisplayString,
        ptMTPMTP3NAM2PADefaultVersion   INTEGER,
        ptMTPMTP3NASLSIgnoreBit         INTEGER,
        ptMTPMTP3NASLSLinksetSelectBit  INTEGER,
        ptMTPMTP3NACRDTSupport          INTEGER,
        ptMTPMTP3NACRDTN                Integer32,
        ptMTPMTP3NACRDTM                Integer32,
        ptMTPMTP3NACRDTTimerLoop        Integer32,
        ptMTPMTP3NANIUserOverride       INTEGER,
        ptMTPMTP3NALongMSUDiscardInterval Integer32,
        ptMTPMTP3NALongMSUDiscardMaximum Integer32,
        ptMTPMTP3NAMaximumMSULength     Integer32,
        ptMTPMTP3NAPCDisplayFormat      DisplayString,
        ptMTPMTP3NAPCRoutingFormat      DisplayString,
        ptMTPMTP3NAMaxEqualCostRoutes   Integer32,
        ptMTPMTP3NAApplicationIDMgmt    INTEGER,
        ptMTPMTP3NAGenerateTFM          INTEGER,
        ptMTPMTP3NADiscardMSUDPCEqualsOPC INTEGER,
        ptMTPMTP3NAEnableAlarmsOnActivate INTEGER,
        ptMTPMTP3NAConfirmationRequired INTEGER,
        ptMTPMTP3NANTTUSNSupport        INTEGER,
        ptMTPMTP3NARxMSUCount           Integer32,
        ptMTPMTP3NATxMSUCount           Integer32,
        ptMTPMTP3NAL3T19Notification    INTEGER,
        ptMTPMTP3NAL3T19LinkReset       INTEGER,
        ptMTPMTP3NAL3T19Attempts        INTEGER,
        ptMTPMTP3NAL3T31FalseLinkCongestion   INTEGER,
        ptMTPMTP3NALoadshareMode        INTEGER,
        ptMTPMTP3NAMTP3NAManagerIndex   Integer32,
        ptMTPMTP3NAActions              INTEGER,
        ptMTPMTP3NAParentOID            OBJECT IDENTIFIER,
        ptMTPMTP3NARowStatus            RowStatus,
        ptMTPMTP3NAIndex                Integer32
    }

ptMTPMTP3NAContext OBJECT-TYPE
    SYNTAX          DisplayString (SIZE(0..255))
    MAX-ACCESS      read-only
    STATUS          current
    DESCRIPTION     
            "A condensed textual representation of the signaling node object"
    ::= { ptMTPMTP3NAEntry 1 }

ptMTPMTP3NALocalPointCode OBJECT-TYPE
    SYNTAX          Integer32 (-2147483648..2147483647)
    MAX-ACCESS      read-create
    STATUS          current
    DESCRIPTION     
            "The SS7 local point code of this signaling node in the format Network.Cluster.Member. Maximum value is 255.255.255. If the personality is ITU, the format is Zone.Area.Member and the range for Zone and Member is 0 to 7, Area is 0 to 255."
    ::= { ptMTPMTP3NAEntry 2 }

ptMTPMTP3NASS7NodeType OBJECT-TYPE
    SYNTAX          INTEGER { stp(0), endNode(1) }
    MAX-ACCESS      read-create
    STATUS          current
    DESCRIPTION     
            "Obsolete as of 12.0.0. The node type of this Network Appearance, should be set to either STP or END_NODE depending upon MTP3 Routing needs. \n The ability to route messages at the MTP3 level is a licensed feature."
    ::= { ptMTPMTP3NAEntry 3 }

ptMTPMTP3NASS7Variant OBJECT-TYPE
    SYNTAX          INTEGER { itu(1), ansi(3), ttc(5), ntt(6), china(4), 
                        newZealand(9) }
    MAX-ACCESS      read-create
    STATUS          current
    DESCRIPTION     
            "The SS7 Variant supported at the MTP3 level. This value should also be set at the SCCP, GTT and SG layers, if they are in use. \n Valid options are: ITU, ANSI, CHINA, JAPAN (NTT and TTC), NEW_ZEALAND.\nNot every MTP3 SS7 variants are supported on all DSC product lines, please confirm your licensed custom applications documentation for their current variant support."
    ::= { ptMTPMTP3NAEntry 4 }

ptMTPMTP3NANetworkIndicator OBJECT-TYPE
    SYNTAX          INTEGER { ni00(0), ni01(1), ni10(2), ni11(3) }
    MAX-ACCESS      read-create
    STATUS          current
    DESCRIPTION     
            "The Network Indicator is a 2 bit value that identifies the network in the MTP3 service indicator octet. \n Valid options are: NI_00 for International, NI_01 for Spare International, NI_10 for National (default), NI_11 for National Spare. \nWhen PT_C20 Application ID Management is used, the NI may not be modified after the NA is activated. \nModification requires the NA to be deleted"
    ::= { ptMTPMTP3NAEntry 5 }

ptMTPMTP3NAStatus OBJECT-TYPE
    SYNTAX          INTEGER { active(0), inactive(1), unlicensed(2) }
    MAX-ACCESS      read-only
    STATUS          current
    DESCRIPTION     
            "Node Status is a read-only attribute that shows your system status of this Network Appearance. Valid options are: ACTIVE, INACTIVE. \n Traffic will not flow, and links will not align on an Inactive node. "
    ::= { ptMTPMTP3NAEntry 6 }

ptMTPMTP3NACLLI OBJECT-TYPE
    SYNTAX          DisplayString (SIZE(0..255))
    MAX-ACCESS      read-create
    STATUS          current
    DESCRIPTION     
            "Set this attribute to the Common Language Location Identifier (CLLI) of the NA. The CLLI is used in the system log file for debugging purposes. \n\nOur system allows for alphanumeric characters, punctuation marks, and keyboard symbols. However, some other systems will only allow for alphanumeric characters. \nThe CLLI code is usually unique to a network and is often provided by the network design team. \n\nNote: Only the first 16 characters in this attribute are used in the logs. We recommend a unique and meaningful entry for this attribute to make the syslog events easier to interpret, especially when running multiple Network Appearances. \n\nWhen PT_C20 Application ID Management is used: \n * the CLLI may not contain spaces, dots, or other special characters. \n * the CLLI may not be modified after the NA is activated. Modification requires the NA to be deleted. \n\nWhen NA is used for SNAMI application: \n * the CLLI may not contain spaces. \n * the CLLI must be UPPERCASE. \n * the CLLI is exactly 11 characters in length."
    ::= { ptMTPMTP3NAEntry 7 }

ptMTPMTP3NANetworkAppearance OBJECT-TYPE
    SYNTAX          Integer32 (-2147483648..2147483647)
    MAX-ACCESS      read-only
    STATUS          current
    DESCRIPTION     
            "Signaling Node Network Appearance (NA) Identifier is a number that uniquely identifies the Network Appearance (or MTP Stack with its own LPC) within the system."
    ::= { ptMTPMTP3NAEntry 9 }

ptMTPMTP3NAActiveSNMSlot OBJECT-TYPE
    SYNTAX          Integer32 (0..255)
    MAX-ACCESS      read-only
    STATUS          current
    DESCRIPTION     
            "Peer Identifier of the Active SNM. The SNM is one of two processes running our MTP3 layer. A process is either 'active' or 'standby'. On a two slot system there will be one of each. Both are processing traffic, but the 'active' is the SNM that controls the User Interface and the SLC tables. \n During some upgrade procedures you may be asked (in the upgrade instructions) to consult this attribute so that you may bring to down the Standby SNM first."
    ::= { ptMTPMTP3NAEntry 10 }

ptMTPMTP3NASLSSize OBJECT-TYPE
    SYNTAX          INTEGER { four(4), five(5), eight(8) }
    MAX-ACCESS      read-create
    STATUS          current
    DESCRIPTION     
            "Signaling Link Selector Size ( 4, 5, 8 bits ). This sets the number of bits used in the SLS field of the MTP routing label. ANSI network typically use 8 or 5 bits, and the ITU network typically use 4 bits."
    ::= { ptMTPMTP3NAEntry 11 }

ptMTPMTP3NARotateSLS OBJECT-TYPE
    SYNTAX          INTEGER { disabled(0), enabled(1) }
    MAX-ACCESS      read-create
    STATUS          current
    DESCRIPTION     
            "SLS rotation is used to load share traffic across links in an ANSI network. This flag enables or disables the SLS rotation on a Network appearance basis. \n An ANSI STP will typically rotate the SLS after selecting a link. \nAn ITU STP will typically not rotate the SLS. \n In either case the SLS value is not rotated when a message is sent across the C-Link (see the Linkset 'Rotate SLS' attribute).\nIf SLS rotation is disabled here, the corresponding Linkset attributes become meaningless."
    ::= { ptMTPMTP3NAEntry 12 }

ptMTPMTP3NAL4ConnectionPort OBJECT-TYPE
    SYNTAX          Integer32 (0..9999)
    MAX-ACCESS      read-only
    STATUS          current
    DESCRIPTION     
            "L4 Connection Port is the internal TCP/IP port on which the internal processes (SCCP and Signalling Gateway) connect. This is a read-only informational atttribute."
    ::= { ptMTPMTP3NAEntry 13 }

ptMTPMTP3NAGenerateUPU OBJECT-TYPE
    SYNTAX          INTEGER { disabled(0), enabled(1) }
    MAX-ACCESS      read-create
    STATUS          current
    DESCRIPTION     
            "Enable or disable User Part Unavailable (UPU) message generation for the signaling node. It is recommended to enable the generation of UPUs."
    ::= { ptMTPMTP3NAEntry 14 }

ptMTPMTP3NALocalMTPRestartSupport OBJECT-TYPE
    SYNTAX          INTEGER { disabled(0), enabled(1) }
    MAX-ACCESS      read-create
    STATUS          current
    DESCRIPTION     
            "Indicates whether this node supports Local MTP Restart procedures. MTP Restart procedures invoke a set of timers (t25, t27 and t28) that are used when an isolated node is returning to service. These timers allow the node to get routing information from the adjacent nodes before attempting to run traffic. \n We recommend Restart be set to ENABLED, unless you have a specific network condition that does not allow Restart. For example older adjacent nodes may not support this feature at this node and might be confused by the Traffic-Restart-Allowed (TRA) message sent out at the start of this process. \n Restart Support may also be set on a per link basis if you have one particular adjacent node that does not handle MTP Restart procedures. \n For more information about Restart feature, see the appropriate sections in the T1.111.4 Signaling Network Functions and Messages (ANSI) and Q.704 Signaling Network Functions and Messages (ITU-T). "
    ::= { ptMTPMTP3NAEntry 15 }

ptMTPMTP3NAPCNumberingValidation OBJECT-TYPE
    SYNTAX          INTEGER { disabled(0), enabled(1) }
    MAX-ACCESS      read-create
    STATUS          current
    DESCRIPTION     
            "When Point Code Numbering Validation is turned on, the system will require that all Point Codes used are allowed under the appropriate ITU or ANSI standards. \n For example 0.1.3 is not a valid point code in ANSI. Turning off PC Numbering Validation would allow the point code on this node, however it does not indicate that other external nodes and systems who received this PC will be able to process it. "
    ::= { ptMTPMTP3NAEntry 16 }

ptMTPMTP3NASpareSSFBits OBJECT-TYPE
    SYNTAX          INTEGER { spareSsfBits(255), spareSsfBits00(0), 
                        spareSsfBits01(1), spareSsfBits10(2), 
                        spareSsfBits11(3) }
    MAX-ACCESS      read-create
    STATUS          current
    DESCRIPTION     
            "Spare Bits in the SSF are normally used as either spare or as priority bits (default behaviour). In some National variants the spare bits may be configured and act like an extension of the Network Indicator: messages are only accepted if the spare bits match the configured value."
    ::= { ptMTPMTP3NAEntry 17 }

ptMTPMTP3NAMateSTP OBJECT-TYPE
    SYNTAX          Integer32 (-2147483648..2147483647)
    MAX-ACCESS      read-only
    STATUS          current
    DESCRIPTION     
            "The Mate STP point code is the local point code of the other signaling node in a mated-pair configuration. On STP products, there should be a Routeset and a Linkset to the Mate-STP, and typically all Routesets to other nodes will contain a route through the mate STP at a higher cost. The signaling gateway may have at most one mate."
    ::= { ptMTPMTP3NAEntry 18 }

ptMTPMTP3NAVNodeFeature OBJECT-TYPE
    SYNTAX          INTEGER { disabled(0), enabled(1) }
    MAX-ACCESS      read-create
    STATUS          current
    DESCRIPTION     
            "The Virtual Nodes feature is enabled by license on our SS7 Gateway and STP products. Virtual nodes are used by gateway applications. \nThe Local Point Code (LPC) identifies the node to which links terminate. However if we are using a point code to be shared across a pair of nodes and to which an application will register, then a Virtual Node (VPC) is required. The VNode feature must be turned on before VNodes may be created on this system."
    ::= { ptMTPMTP3NAEntry 19 }

ptMTPMTP3NARoutingFeature OBJECT-TYPE
    SYNTAX          INTEGER { disabled(0), enabled(1) }
    MAX-ACCESS      read-create
    STATUS          current
    DESCRIPTION     
            "The STP function of routing SS7 messages at MTP level 3 is enabled by license. With this enabled the node will be able to receive messages and forward messages destined for one of its available routesets. Without MTP routing the system will act only as a gateway for IP applications. \nThe feature is Available on our SS7 Gateway and STP products and is not available on Edge products."
    ::= { ptMTPMTP3NAEntry 20 }

ptMTPMTP3NAR48Compliance OBJECT-TYPE
    SYNTAX          INTEGER { disabled(0), enabled(1) }
    MAX-ACCESS      read-create
    STATUS          current
    DESCRIPTION     
            "This flag is used to turn on or off R4-8 compliance for SS7 messages during STP routing. \n Typically all traffic that has be GTT routed or from a user application will have the OPC set to LPC. However for some of our custom routing products (converters and PCE) this may not be desirable. \nThe feature is Available on our SS7 Gateway and STP products and is not available on Edge products. \n R4_8 Compliance is typically set to ENABLED. "
    ::= { ptMTPMTP3NAEntry 21 }

ptMTPMTP3NADebug OBJECT-TYPE
    SYNTAX          INTEGER { disabled(0), enabled(1) }
    MAX-ACCESS      read-create
    STATUS          current
    DESCRIPTION     
            "If set to ENABLED, the debug flags that follow in this screen are applied. This is a setting for the debug system as a whole. The remaining flags are individual settings for specific debug features. \nIt is strongly recommended that this flag be set to ENABLED on all systems."
    ::= { ptMTPMTP3NAEntry 22 }

ptMTPMTP3NAErrors OBJECT-TYPE
    SYNTAX          INTEGER { notLogged(0), logged(1) }
    MAX-ACCESS      read-create
    STATUS          current
    DESCRIPTION     
            "If set to LOGGED the Debug Error flag will enable all logs sent to Syslog to also be sent to the Debug log. With Error messages and other Debug information in the one Debug log file, it is easier to interpret the log events. \n It is strongly recommended that this flag be set to LOGGED on all systems."
    ::= { ptMTPMTP3NAEntry 23 }

ptMTPMTP3NASNMManagement OBJECT-TYPE
    SYNTAX          INTEGER { notLogged(0), logged(1) }
    MAX-ACCESS      read-create
    STATUS          current
    DESCRIPTION     
            "If the Debug SNM Management flag is set to LOGGED, then information concerning the state of management of the MTP Level 3 will be sent to the Debug log file. \n The recommended setting of this flag is NOT_LOGGED, so that the system resources are not unduly taken up in the production of log messages."
    ::= { ptMTPMTP3NAEntry 24 }

ptMTPMTP3NAPeerAdministration OBJECT-TYPE
    SYNTAX          INTEGER { notLogged(0), logged(1) }
    MAX-ACCESS      read-create
    STATUS          current
    DESCRIPTION     
            "If the Peer Administration flag is set to LOGGED, then activities with the distributed peer of the MTP will be logged to the Debug log file. \n The recommended setting of this flag is NOT_LOGGED, so that the system resources are not unduly taken up in the production of log messages."
    ::= { ptMTPMTP3NAEntry 25 }

ptMTPMTP3NAL2Connection OBJECT-TYPE
    SYNTAX          INTEGER { notLogged(0), logged(1) }
    MAX-ACCESS      read-create
    STATUS          current
    DESCRIPTION     
            "If the L2 Connection flag is set to LOGGED, then the then activities concerning the internal connections to the L2 process will be logged to the Debug log file. \n The recommended setting of this flag is NOT_LOGGED, so that the system resources are not unduly taken up in the production of log messages."
    ::= { ptMTPMTP3NAEntry 26 }

ptMTPMTP3NADREConnection OBJECT-TYPE
    SYNTAX          INTEGER { notLogged(0), logged(1) }
    MAX-ACCESS      read-create
    STATUS          current
    DESCRIPTION     
            "If the DRE Connection flag is set to LOGGED, then activities concerning the internal connections to the DRE process will be logged to the Debug log file. \n The recommended setting of this flag is NOT_LOGGED, so that the system resources are not unduly taken up in the production of log messages."
    ::= { ptMTPMTP3NAEntry 27 }

ptMTPMTP3NADREAdministration OBJECT-TYPE
    SYNTAX          INTEGER { notLogged(0), logged(1) }
    MAX-ACCESS      read-create
    STATUS          current
    DESCRIPTION     
            "If the DRE Administration flag is set to LOGGED, then activities concerning the management of the DRE process will be logged to the Debug log file. \n The recommended setting of this flag is NOT_LOGGED, so that the system resources are not unduly taken up in the production of log messages."
    ::= { ptMTPMTP3NAEntry 28 }

ptMTPMTP3NADRESwitchover OBJECT-TYPE
    SYNTAX          INTEGER { notLogged(0), logged(1) }
    MAX-ACCESS      read-create
    STATUS          current
    DESCRIPTION     
            "If the DRE Switchover flag is set to LOGGED, then these activities will be logged to the Debug log file. The DRE Switchover activities take place when one DRE process takes over for a DRE process that has become unavailable for some reason. \n The recommended setting of this flag is NOT_LOGGED, so that the system resources are not unduly taken up in the production of log messages."
    ::= { ptMTPMTP3NAEntry 29 }

ptMTPMTP3NASetup OBJECT-TYPE
    SYNTAX          INTEGER { notLogged(0), logged(1) }
    MAX-ACCESS      read-create
    STATUS          current
    DESCRIPTION     
            "If the Setup flag is set to LOGGED, then activities associated with the startup of the process and its initial configuration will be logged in the Debug log file. \n The recommended setting of this flag is NOT_LOGGED, so that the system resources are not unduly taken up in the production of log messages."
    ::= { ptMTPMTP3NAEntry 30 }

ptMTPMTP3NAOtherTimers OBJECT-TYPE
    SYNTAX          INTEGER { notLogged(0), logged(1) }
    MAX-ACCESS      read-create
    STATUS          current
    DESCRIPTION     
            "If the Other Timers flag is set to LOGGED , then an information message will be placed in the Debug Log file when various timers ( other than the IO Timers) are used. \n The recommended setting of this flag is NOT_LOGGED, so that the system resources are not unduly taken up in the production of log messages."
    ::= { ptMTPMTP3NAEntry 31 }

ptMTPMTP3NAReroutingProcedure OBJECT-TYPE
    SYNTAX          INTEGER { notLogged(0), logged(1) }
    MAX-ACCESS      read-create
    STATUS          current
    DESCRIPTION     
            "If Rerouting Procedure flag is set to LOGGED, then informational messages are placed in the Debug Log File when the MTP level 3 invokes Rerouting procedures. Controlled Rerouting is the SS7 concept whereby the networked adjusts routing to state changes in nodes. \n The recommended setting of this flag is NOT_LOGGED, so that the system resources are not unduly taken up in the production of log messages."
    ::= { ptMTPMTP3NAEntry 32 }

ptMTPMTP3NACOCBProcedure OBJECT-TYPE
    SYNTAX          INTEGER { notLogged(0), logged(1) }
    MAX-ACCESS      read-create
    STATUS          current
    DESCRIPTION     
            "If Change Over / Change Back (CO/CB) Procedure flag, is set to LOGGED, then informational messages concerning how links go through Change Over and Change Back procedures are placed in the Debug Log. \n The recommended setting of this flag is NOT_LOGGED, so that the system resources are not unduly taken up in the production of log messages."
    ::= { ptMTPMTP3NAEntry 33 }

ptMTPMTP3NALinkStatus OBJECT-TYPE
    SYNTAX          INTEGER { notLogged(0), logged(1) }
    MAX-ACCESS      read-create
    STATUS          current
    DESCRIPTION     
            "If Link Status flag is set to LOGGED, then informational messages concerning the state changes of the SS7 links are placed in the Debug Log. \n The recommended setting of this flag is NOT_LOGGED, so that the system resources are not unduly taken up in the production of log messages."
    ::= { ptMTPMTP3NAEntry 34 }

ptMTPMTP3NAL2Messages OBJECT-TYPE
    SYNTAX          INTEGER { notLogged(0), logged(1) }
    MAX-ACCESS      read-create
    STATUS          current
    DESCRIPTION     
            "If Level 2 messages flag is set to LOGGED, then informational messages detailing the communications between the DRE and its Level 2 module are placed in the Debug Log. \n The recommended setting of this flag is NOT_LOGGED, so that the system resources are not unduly taken up in the production of log messages."
    ::= { ptMTPMTP3NAEntry 35 }

ptMTPMTP3NAUserManagement OBJECT-TYPE
    SYNTAX          INTEGER { notLogged(0), logged(1) }
    MAX-ACCESS      read-create
    STATUS          current
    DESCRIPTION     
            "If MTP User management flag is set to LOGGED, then information concerning the state of communications between the DRE and its connected users (SCCP or Signalling Gateway) are placed in the Debug Log. \n This feature is applicable on the SS7 Gateway and STP products, and not on Edge devices. \n The recommended setting of this flag is NOT_LOGGED, so that the system resources are not unduly taken up in the production of log messages."
    ::= { ptMTPMTP3NAEntry 36 }

ptMTPMTP3NAUserPrimitives OBJECT-TYPE
    SYNTAX          INTEGER { notLogged(0), logged(1) }
    MAX-ACCESS      read-create
    STATUS          current
    DESCRIPTION     
            "If MTP User Primitive message flag is set to LOGGED, then the messages used for of communications between the DRE and its connected users (SCCP or Signalling Gateway) are placed in the Debug Log. The API used is internal and not meant to be readable by customers, thus this flag is o typically only used at the request of customer support. \n This feature is applicable on the SS7 Gateway and STP products, and not on Edge devices. \n The recommended setting of this flag is NOT_LOGGED, so that the system resources are not unduly taken up in the production of log messages."
    ::= { ptMTPMTP3NAEntry 37 }

ptMTPMTP3NAMSUTraffic OBJECT-TYPE
    SYNTAX          INTEGER { notLogged(0), logged(1) }
    MAX-ACCESS      read-create
    STATUS          current
    DESCRIPTION     
            "If the MSU Traffic flag is set to LOGGED, then a summary of each MSU will be presented as the MSU enters or leaves MTP Level 3. \n CAUTION: this flag can produce a huge volume of data, and can easily swamp a busy system with logging requests. \n The recommended setting of this flag is NOT_LOGGED, so that the system resources are not unduly taken up in the production of log messages."
    ::= { ptMTPMTP3NAEntry 38 }

ptMTPMTP3NAMSUTrafficRaw OBJECT-TYPE
    SYNTAX          INTEGER { notLogged(0), logged(1) }
    MAX-ACCESS      read-create
    STATUS          current
    DESCRIPTION     
            "If the MSU Traffic Raw flag is set to LOGGED, then all messages and contents received or sent at the MTP Level 3 will be placed in the Debug Log in a hexadecimal representation. The format used is internal and not meant to be readable by customers, thus this flag is o typically only used at the request of customer support. \n CAUTION: this flag can produce a huge volume of data, and can easily swamp a busy system with logging requests. \n The recommended setting of this flag is NOT_LOGGED, so that the system resources are not unduly taken up in the production of log messages."
    ::= { ptMTPMTP3NAEntry 39 }

ptMTPMTP3NASLT OBJECT-TYPE
    SYNTAX          INTEGER { notLogged(0), logged(1) }
    MAX-ACCESS      read-create
    STATUS          current
    DESCRIPTION     
            "If the Debug SLT flag is set to LOGGED, then the messages and procedures concerning SLTM/SLTA/SRT/SRA functionality at MTP level 3 will be traced and logged to the Debug Log. \n The recommended setting of this flag is NOT_LOGGED, so that the system resources are not unduly taken up in the production of log messages."
    ::= { ptMTPMTP3NAEntry 40 }

ptMTPMTP3NASLSTables OBJECT-TYPE
    SYNTAX          INTEGER { notLogged(0), logged(1) }
    MAX-ACCESS      read-create
    STATUS          current
    DESCRIPTION     
            "If the Debug SLS Tables flag is set to LOGGED, then information concerning changes to the state of the SLS Tables is presented in the logs. Changes to the SLS tables take place when links change state. This information is internal and not typically needed by customers. This flag is typically only used at the request of customer support. \n The recommended setting of this flag is NOT_LOGGED, so that the system resources are not unduly taken up in the production of log messages."
    ::= { ptMTPMTP3NAEntry 41 }

ptMTPMTP3NAL3T1 OBJECT-TYPE
    SYNTAX          INTEGER { default(-1) }
    MAX-ACCESS      read-create
    STATUS          current
    DESCRIPTION     
            "Changeover delay ( 500 - 1200 ms ) [ANSI/ITU/JT] \nThe default value is 1000 ms. \nSetting MTP Level 3 timers on the NA will encompass all linkset, routeset and NA functionality. The L3 T1 timer can be overridden from a Linkset. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 42 }

ptMTPMTP3NAL3T2 OBJECT-TYPE
    SYNTAX          INTEGER { default(-1) }
    MAX-ACCESS      read-create
    STATUS          current
    DESCRIPTION     
            "Waiting for COA ( 700 - 2000 ms ) [ANSI/ITU/JT] \nThe default value is 1000 ms. \nSetting MTP Level 3 timers on the NA will encompass all linkset, routeset and NA functionality. The L3 T2 timer can be overridden from a Linkset. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 43 }

ptMTPMTP3NAL3T3 OBJECT-TYPE
    SYNTAX          INTEGER { default(-1) }
    MAX-ACCESS      read-create
    STATUS          current
    DESCRIPTION     
            "Changeback delay ( 500 - 1200 ms ) [ANSI/ITU/JT] \nThe default value is 1000 ms. \nSetting MTP Level 3 timers on the NA will encompass all linkset, routeset and NA functionality. The L3 T3 timer can be overridden from a Linkset. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 44 }

ptMTPMTP3NAL3T4 OBJECT-TYPE
    SYNTAX          INTEGER { default(-1) }
    MAX-ACCESS      read-create
    STATUS          current
    DESCRIPTION     
            "Waiting for CBA: first attempt ( 500 - 1200 ms ) [ANSI/ITU/JT] \nThe default value is 1000 ms. \nSetting MTP Level 3 timers on the NA will encompass all linkset, routeset and NA functionality. The L3 T4 timer can be overridden from a Linkset. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 45 }

ptMTPMTP3NAL3T5 OBJECT-TYPE
    SYNTAX          INTEGER { default(-1) }
    MAX-ACCESS      read-create
    STATUS          current
    DESCRIPTION     
            "Waiting for CBA: second attempt ( 500 - 1200 ms ) [ANSI/ITU] \nThe default value is 1000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 46 }

ptMTPMTP3NAL3T6 OBJECT-TYPE
    SYNTAX          INTEGER { default(-1) }
    MAX-ACCESS      read-create
    STATUS          current
    DESCRIPTION     
            "Controlled rerouting delay ( 500 - 1200 ms ) [ANSI/ITU/JT] \nThe default value is 1000 ms. \nSetting MTP Level 3 timers on the NA will encompass all linkset, routeset and NA functionality. The L3 T6 timer can be overridden from a Linkset. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 47 }

ptMTPMTP3NAL3T7 OBJECT-TYPE
    SYNTAX          INTEGER { default(-1) }
    MAX-ACCESS      read-create
    STATUS          current
    DESCRIPTION     
            "Waiting for CSS/CNS/CNP ( 1000 - 2000 ms ) [ANSI/ITU] \nThe default value is 1500 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 48 }

ptMTPMTP3NAL3T8 OBJECT-TYPE
    SYNTAX          INTEGER { default(-1) }
    MAX-ACCESS      read-create
    STATUS          current
    DESCRIPTION     
            "TFP inhibition timer ( 800 - 1200 ms ) [ANSI/ITU/JT] \nThe default value is 1000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 49 }

ptMTPMTP3NAL3T10 OBJECT-TYPE
    SYNTAX          INTEGER { default(-1) }
    MAX-ACCESS      read-create
    STATUS          current
    DESCRIPTION     
            "Waiting to repeat RSM ( 30,000 - 60,000 ms ) [ANSI/ITU/JT] \nThe default value is 30,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 50 }

ptMTPMTP3NAL3T11 OBJECT-TYPE
    SYNTAX          INTEGER { default(-1) }
    MAX-ACCESS      read-create
    STATUS          current
    DESCRIPTION     
            "TFR timer ( 30,000 - 90,000 ms ) [ANSI/ITU] \nThe default value is 60,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 51 }

ptMTPMTP3NAL3T12 OBJECT-TYPE
    SYNTAX          INTEGER { default(-1) }
    MAX-ACCESS      read-create
    STATUS          current
    DESCRIPTION     
            "Waiting for LUA ( 800 - 1500 ms ) [ANSI/ITU] \nThe default value is 1000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 52 }

ptMTPMTP3NAL3T13 OBJECT-TYPE
    SYNTAX          INTEGER { default(-1) }
    MAX-ACCESS      read-create
    STATUS          current
    DESCRIPTION     
            "Waiting for LFU ( 800 - 1500 ms ) [ANSI/ITU] \nThe default value is 1000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 53 }

ptMTPMTP3NAL3T14 OBJECT-TYPE
    SYNTAX          INTEGER { default(-1) }
    MAX-ACCESS      read-create
    STATUS          current
    DESCRIPTION     
            "Waiting for LIA ( 2000 - 3000 ms ) [ANSI/ITU] \nThe default value is 3000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 54 }

ptMTPMTP3NAL3T15 OBJECT-TYPE
    SYNTAX          INTEGER { default(-1) }
    MAX-ACCESS      read-create
    STATUS          current
    DESCRIPTION     
            "Waiting to repeat RCT ( 2000 - 3000 ms ) [ANSI/ITU/JT] \nThe default value is 2000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 55 }

ptMTPMTP3NAL3T16 OBJECT-TYPE
    SYNTAX          INTEGER { default(-1) }
    MAX-ACCESS      read-create
    STATUS          current
    DESCRIPTION     
            "Waiting for congestion status update ( 1400 - 2000 ms ) [ANSI/ITU/JT] \nThe default value is 2000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 56 }

ptMTPMTP3NAL3T17 OBJECT-TYPE
    SYNTAX          INTEGER { default(-1) }
    MAX-ACCESS      read-create
    STATUS          current
    DESCRIPTION     
            "Alignment failure and restart delay ( 800 - 1500 ms ) [ANSI/ITU] \nThe value is set to 1 ms in SS7 variants where the L3 T17 is not applicable. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 57 }

ptMTPMTP3NAL3T18 OBJECT-TYPE
    SYNTAX          INTEGER { default(-1) }
    MAX-ACCESS      read-create
    STATUS          current
    DESCRIPTION     
            "ANSI: Repeat TFR once by response method ( 2000 - 20000 ms ) \nThe default value in ANSI is 2000 ms. \nITU: Internal MTP restart timer. \nThe Q704 standard lists this value as being network dependent. We have set the ITU default value as 5000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 58 }

ptMTPMTP3NAL3T19 OBJECT-TYPE
    SYNTAX          INTEGER { default(-1) }
    MAX-ACCESS      read-create
    STATUS          current
    DESCRIPTION     
            "ANSI: Failed link craft referral ( 480,000 - 600,000 ms ) \nThe default ANSI value is 480,000 ms. \nITU: MTP restart timer to control ping-pong TFP/TFR/TFA ( 67,000 - 69,000 ms ) \nThe default ITU value is 68,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 59 }

ptMTPMTP3NAL3T20 OBJECT-TYPE
    SYNTAX          INTEGER { default(-1) }
    MAX-ACCESS      read-create
    STATUS          current
    DESCRIPTION     
            "ANSI: Waiting to repeat local inhibit test ( 90,000 - 120,000 ms ) \nITU: MTP restart timer at Signaling Point whose MTP restarts ( 59,000 - 61,000 ms ) \nThe default ITU value is 60,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 60 }

ptMTPMTP3NAL3T21 OBJECT-TYPE
    SYNTAX          INTEGER { default(-1) }
    MAX-ACCESS      read-create
    STATUS          current
    DESCRIPTION     
            "ANSI: Waiting to repeat remote inhibit test ( 90,000 - 120,000 ms ) \nThe default ANSI value is 90,000 ms. \nITU: MTP restart timer used at Signaling Point adjacent to the restarting Signaling Point ( 63,000 - 65,000 ms ) \nThe default value is 64,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 61 }

ptMTPMTP3NAL3T22 OBJECT-TYPE
    SYNTAX          INTEGER { default(-1) }
    MAX-ACCESS      read-create
    STATUS          current
    DESCRIPTION     
            "ANSI: Wait to receive TRA during a Signaling Point Restart \nThe default ANSI value is 10,000 ms. \nITU: Local inhibit test timer ( 180,000 - 360,000 ms ) \nThe default ITU value is 180,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 62 }

ptMTPMTP3NAL3T23 OBJECT-TYPE
    SYNTAX          INTEGER { default(-1) }
    MAX-ACCESS      read-create
    STATUS          current
    DESCRIPTION     
            "ANSI: Wait to broadcast all traffic restart allowed messages \nThe default ANSI value is 10,000 ms. \nITU: Remote inhibit test timer ( 180,000 - 360,000 ms ) \nThe default ITU value is 180,000 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 63 }

ptMTPMTP3NAL3T24 OBJECT-TYPE
    SYNTAX          INTEGER { default(-1) }
    MAX-ACCESS      read-create
    STATUS          current
    DESCRIPTION     
            "ANSI: Waiting to broadcast TRA on SP Restart \nThe default ANSI value is 10,000 ms. \nITU: Stabilizing timer for latching LPO to RPO \nThe default ITU value is 500 ms. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 64 }

ptMTPMTP3NAL3T25 OBJECT-TYPE
    SYNTAX          INTEGER { default(-1) }
    MAX-ACCESS      read-create
    STATUS          current
    DESCRIPTION     
            "ANSI: Wait for TRA from adjacent restarting SP ( 30,000 - 35,000 ms ) \nThe default ANSI value is 30,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 65 }

ptMTPMTP3NAL3T26 OBJECT-TYPE
    SYNTAX          INTEGER { default(-1) }
    MAX-ACCESS      read-create
    STATUS          current
    DESCRIPTION     
            "ANSI: Wait to repeat TRW at restarting Signaling Point ( 12,000 - 15,000 ms ) \nThe default ANSI value is 12,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 66 }

ptMTPMTP3NAL3T27 OBJECT-TYPE
    SYNTAX          INTEGER { default(-1) }
    MAX-ACCESS      read-create
    STATUS          current
    DESCRIPTION     
            "ANSI: Minimum duration of unavailability for full restart ( 2000 - 5000 ms ) \nThe default ANSI value is 5000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 67 }

ptMTPMTP3NAL3T28 OBJECT-TYPE
    SYNTAX          INTEGER { default(-1) }
    MAX-ACCESS      read-create
    STATUS          current
    DESCRIPTION     
            "Waiting for TRW at the Signaling Point adjacent to the restarting Signaling Point ( 3,000 - 35,000 ms ) \nThe default ANSI value is 30,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 68 }

ptMTPMTP3NAL3T29 OBJECT-TYPE
    SYNTAX          INTEGER { default(-1) }
    MAX-ACCESS      read-create
    STATUS          current
    DESCRIPTION     
            "ANSI: TRA sent in response to unexpected TRA or TRW ( 60,000 - 65,000 ) \nThe default ANSI value is 60,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 69 }

ptMTPMTP3NAL3T30 OBJECT-TYPE
    SYNTAX          INTEGER { default(-1) }
    MAX-ACCESS      read-create
    STATUS          current
    DESCRIPTION     
            "ANSI: Limit transmission of TFP/TFR's after receiving unexpected TRA/TRW's (30,000-35,000) \nThe default ANSI value is 30,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 70 }

ptMTPMTP3NAL3T31 OBJECT-TYPE
    SYNTAX          INTEGER { default(-1) }
    MAX-ACCESS      read-create
    STATUS          current
    DESCRIPTION     
            "ANSI: False link congestion detection (10,000-120,000) \nThe default ANSI value is 30,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 71 }

ptMTPMTP3NAL3T32 OBJECT-TYPE
    SYNTAX          INTEGER { default(-1) }
    MAX-ACCESS      read-create
    STATUS          current
    DESCRIPTION     
            "ANSI: Link oscillation - Procedure A \nThe default ANSI value is 90,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 72 }

ptMTPMTP3NAL3T33 OBJECT-TYPE
    SYNTAX          INTEGER { default(-1) }
    MAX-ACCESS      read-create
    STATUS          current
    DESCRIPTION     
            "ANSI: Probation for link oscillation - Procedure B GR-246_CORE (60,000-600,000) \nThe default ANSI value is 90,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 73 }

ptMTPMTP3NAL3T34 OBJECT-TYPE
    SYNTAX          INTEGER { default(-1) }
    MAX-ACCESS      read-create
    STATUS          current
    DESCRIPTION     
            "Suspension for link oscillation - Procedure B GR-246_CORE (5,000-120,000) \nThe default ANSI value is 90,000 ms. \nITU: This timer is not used in ITU networks. \nSetting MTP Level 3 timers is only done one time for the entire NA as they encompass all linkset, routeset and NA functionality. \nCAUTION: It is recommended that you do not change the timer default values unless instructed otherwise by Signalling Systems Customer Support. Timer values should be modified with care, especially on a live system. Interaction of timers trough the various MTP3 procedures is complex and changing them incorrectly can reduce system stability."
    ::= { ptMTPMTP3NAEntry 74 }

ptMTPMTP3NAXListLifespan OBJECT-TYPE
    SYNTAX          INTEGER { disabled(-1), tenMinutes(600000), 
                        thirtyMinutes(1800000), oneHour(3600000), 
                        twoHours(7200000), threeHours(10800000), 
                        fourHours(14400000), sixHours(21600000), 
                        twelveHours(43200000), oneDay(86400000), 
                        twoDays(172800000) }
    MAX-ACCESS      read-create
    STATUS          current
    DESCRIPTION     
            "The X-List Life Timer sets the lifespan of the dynamically created X-Routesets. If an X-Routeset has not received traffic for the given period of time, the X-Routeset will be deleted from the system. \nThe available options for this attribute are: \n DISABLED (implies X-routesets are never to be deleted.) \n TEN_MINUTES \n THRITY_MINUTES \n ONE_HOUR \n TWO_HOURS \n THREE_HOURS \n FOUR_HOURS \n SIX_HOURS \n TWELVE_HOURS \n ONE_DAY \n TWO_DAYS \nThe default value is DISABLED. \nSetting MTP Level 3 timers is only done one time for the entire NA as they encompass all linkset, routeset and NA functionality. \nCAUTION: It is recommended that you do not change this timer value without prior forethought and planning. Removal of X-List entries enables one to 'clean-up' seldom used entries, but could impact system and network performance. \n Timer values generally should be modified with care, especially on a live system. Interaction of timers trough the various MTP3 procedures is complex and changing them incorrectly can reduce system stability."
    ::= { ptMTPMTP3NAEntry 76 }

ptMTPMTP3NASLTSI OBJECT-TYPE
    SYNTAX          INTEGER { auto(0), ntmRegular(1), ntmSpecial(2) }
    MAX-ACCESS      read-create
    STATUS          current
    DESCRIPTION     
            "The Service Indicator (SI) used for Signaling Link Test (SLT) messages. \n AUTO sets the value based on SS7 Variant \n NTM_REGULAR uses the SI value 1 \n NTM_SPECIAL uses the SI value 2 \nThe default value is AUTO. \nThis value is used to customize the Signaling Link Test Messages (SLTM) and Signaling Link Test Message Acknowledgements (SLTA). \nThis is not a value that should be changed on a running system. As such you must deactivate all linksets on the NA before you will be allowed to change the SLT parameters for this NA. Reactivate the links after the change has been made."
    ::= { ptMTPMTP3NAEntry 77 }

ptMTPMTP3NASLTMPattern OBJECT-TYPE
    SYNTAX          DisplayString (SIZE(0..255))
    MAX-ACCESS      read-create
    STATUS          current
    DESCRIPTION     
            "The Test Pattern Used for Signaling Link Test Messages (SLTM) messages written in hexadecimal format. Enter this value as a string representing the hex value (for example, AABBCCDD) \nThis value is used to customize the Signaling Link Test Messages (SLTM) and Signaling Link Test Message Acknowledgements (SLTA). \nThis is not a value that should be changed on a running system. As such you must deactivate all linksets on the NA before you will be allowed to change the SLT parameters for this NA. Reactivate the links after the change has been made."
    ::= { ptMTPMTP3NAEntry 78 }

ptMTPMTP3NAM2PADefaultVersion OBJECT-TYPE
    SYNTAX          INTEGER { draft6(6), rfc4165(13) }
    MAX-ACCESS      read-create
    STATUS          current
    DESCRIPTION     
            "M2PA Default Version sets the standard SIGTRAN version to which the M2PA messages will conform. This need only be set if this node is using M2PA links. The current M2PA standard, and the recommended value is RFC 4165. Connections to older systems may require use of the earlier Draft 6."
    ::= { ptMTPMTP3NAEntry 79 }

ptMTPMTP3NASLSIgnoreBit OBJECT-TYPE
    SYNTAX          INTEGER { none(-1), zero(0), one(1), two(2), 
                        three(3), five(5) }
    MAX-ACCESS      read-create
    STATUS          current
    DESCRIPTION     
            "Setting SLS ignore bit allows better loadsharing distribution between links. Ability to change SLS Ignore bit depends on the standard. For ANSI SLS Ignore Bit is always set to bit 5 as per clause T1.111.5. "
    ::= { ptMTPMTP3NAEntry 80 }

ptMTPMTP3NASLSLinksetSelectBit OBJECT-TYPE
    SYNTAX          INTEGER { zero(0), one(1), two(2), three(3) }
    MAX-ACCESS      read-create
    STATUS          current
    DESCRIPTION     
            "Select SLS Linkset Selection bit is applicable for ITU only. It allows better loadsharing distribution between links"
    ::= { ptMTPMTP3NAEntry 81 }

ptMTPMTP3NACRDTSupport OBJECT-TYPE
    SYNTAX          INTEGER { disabled(0), enabled(1) }
    MAX-ACCESS      read-create
    STATUS          current
    DESCRIPTION     
            "The ANSI CRDT procedure is supported on ANSI STPs, as per GR-246-CORE Issue 10 T1.111.7 (Method A) and GR-82-CORE Issue 10. It describes an MTP3 procedure with three configurable parameters: 'M', 'N' and 'TLoop'. \nThe CRDT procedure may be explicitly enabled or disabled for ANSI STPs via this attribute. If the 'SS7 Variant' is not set to ANSI, or if the 'STP Routing' feature is not enabled then this attribute has no effect. \nSetting this attribute to DISABLED resets the state of all routes that were marked as prohibited for failing a CRDT test."
    ::= { ptMTPMTP3NAEntry 82 }

ptMTPMTP3NACRDTN OBJECT-TYPE
    SYNTAX          Integer32 (50..200)
    MAX-ACCESS      read-create
    STATUS          current
    DESCRIPTION     
            "The ANSI CRDT procedure is supported on ANSI STPs, as per GR-246-CORE Issue 10 T1.111.7 (Method A) and GR-82-CORE Issue 10. It describes an MTP3 procedure with three configurable parameters: 'M', 'N' and 'TLoop'. This attribute is the 'N'. The rest of this description is a summary of the CRDT procedure. \n\nANSI CRDT Method A is performed by MTP3 as follows (overview): \n- when congestion status increases on a link, sample N MSUs (range 50-200) sent on that link. \n- From the N MSUs, compute the M most common DPCs (range 3-10). \n- Send test messages to those destinations. \n- If a test message comes back within TLoop (10 - 20s) then there is a loop in the MTP3 routing tables in the network. Disable the tested routes and those of lower priority. "
    ::= { ptMTPMTP3NAEntry 83 }

ptMTPMTP3NACRDTM OBJECT-TYPE
    SYNTAX          Integer32 (3..10)
    MAX-ACCESS      read-create
    STATUS          current
    DESCRIPTION     
            "The ANSI CRDT procedure is supported on ANSI STPs, as per GR-246-CORE Issue 10 T1.111.7 (Method A) and GR-82-CORE Issue 10. It describes an MTP3 procedure with three configurable parameters: 'M', 'N' and 'TLoop'. This attribute is the 'M'. The rest of this description is a summary of the CRDT procedure. \n\nANSI CRDT Method A is performed by MTP3 as follows (overview): \n- when congestion status increases on a link, sample N MSUs (range 50-200) sent on that link. \n- From the N MSUs, compute the M most common DPCs (range 3-10). \n- Send test messages to those destinations. \n- If a test message comes back within TLoop (10 - 20s) then there is a loop in the MTP3 routing tables in the network. Disable the tested routes and those of lower priority. "
    ::= { ptMTPMTP3NAEntry 84 }

ptMTPMTP3NACRDTTimerLoop OBJECT-TYPE
    SYNTAX          Integer32
    MAX-ACCESS      read-create
    STATUS          current
    DESCRIPTION     
            "The ANSI CRDT procedure is supported on ANSI STPs, as per GR-246-CORE Issue 10 T1.111.7 (Method A) and GR-82-CORE Issue 10. It describes an MTP3 procedure with three configurable parameters: 'M', 'N' and 'TLoop'. This attribute is the 'TLoop'. The rest of this description is a summary of the CRDT procedure. \n\nANSI CRDT Method A is performed by MTP3 as follows (overview): \n- when congestion status increases on a link, sample N MSUs (range 50-200) sent on that link. \n- From the N MSUs, compute the M most common DPCs (range 3-10). \n- Send test messages to those destinations. \n- If a test message comes back within TLoop (10 - 20s) then there is a loop in the MTP3 routing tables in the network. Disable the tested routes and those of lower priority. "
    ::= { ptMTPMTP3NAEntry 85 }

ptMTPMTP3NANIUserOverride OBJECT-TYPE
    SYNTAX          INTEGER { disabled(0), enabled(1) }
    MAX-ACCESS      read-create
    STATUS          current
    DESCRIPTION     
            "NI User Override for incoming MSUs. If enabled, the Network Indicator from the MTP3 NA will override the NI value in the MSUs coming from the L4 Connection users. NI override only applies to MSUs with SI greater or equal to 3."
    ::= { ptMTPMTP3NAEntry 86 }

ptMTPMTP3NALongMSUDiscardInterval OBJECT-TYPE
    SYNTAX          Integer32
    MAX-ACCESS      read-create
    STATUS          current
    DESCRIPTION     
            "The interval in which the maximum number of traps can be raised to report a Long MSU discard for an unsupported destination. Unsupported destination could be a linkset, user part or application. \nThis timer also indicates how long the dashboard alarm will remain visible after the last Long MSU discard by the unsupported destination."
    ::= { ptMTPMTP3NAEntry 87 }

ptMTPMTP3NALongMSUDiscardMaximum OBJECT-TYPE
    SYNTAX          Integer32
    MAX-ACCESS      read-create
    STATUS          current
    DESCRIPTION     
            "The maximum number of SNMP traps that can be raised in the Long MSU Discard Interval for a particular destination."
    ::= { ptMTPMTP3NAEntry 88 }

ptMTPMTP3NAMaximumMSULength OBJECT-TYPE
    SYNTAX          Integer32
    MAX-ACCESS      read-create
    STATUS          current
    DESCRIPTION     
            "The maximum number of bytes allowed, including routing label and SIO, for an MSU in this NA. Range is 273 to 4092 bytes. \nThe value should remain at the default of 273 unless the NA is meant to support MTP3B with long MSUs."
    ::= { ptMTPMTP3NAEntry 89 }

ptMTPMTP3NAPCDisplayFormat OBJECT-TYPE
    SYNTAX          DisplayString (SIZE(0..255))
    MAX-ACCESS      read-create
    STATUS          current
    DESCRIPTION     
            "Point Code Display Format based on SS7 Variant. \n The PC Routing format is defined to delimiter the point code for SS7 routing purposes to determine the breakdown of the network.cluster.member in ANSI based networks (zone.area.member in ITU). The most common usage is for network or cluster based routeset definitions in MTP3. \n The PC Display format is used only to display the point code value in the UI and logs. Some PC Display format cannot be defined as PC Routing formats as they do not identify the PC delimiter breakdown such as ITU Decimal and Japan ff-ff. \n For example, in ITU, the PC Routing Format may be set to '3.8.3' while the PC Display Format may be '3.8.3' or Decimal. A PC Display format of '3.8.3' displays a point code like '1.002.3' while in Decimal displays the same point code as '2067'. In ANSI, the PC Routing and Display formats must both be set to '8.8.8'. \n Note: the PC Display and Routing formats are typically identical unless the PC Display is set to ITU Decimal or Japan ff-ff which do not have delimiter information for routing procedures. \n Note: Member and cluster routing are part of the ANSI specifications. Default and Network routing are an enhancement in the DSC MTP3 implementation. While ITU specifications only mention member routesets, where a PC can be treated as a simple number, the DSC routeset implementation supports all 4 types (MEMBER, CLUSTER, NETWORK, and DEFAULT) in all SS7 variants for a possibly more flexible configuration. As the Cluster and Network routesets are available as an option in all SS7 Variants, the PC Routing Format must be specified when creating an MTP3 NA, to indicate which part of the point code is the network, cluster and member. If the CLUSTER and NETWORK routeset types are not required for a given ITU deployment, the MTP3 NA PC Routing Format is recommended to be set to 3.8.3 to agree with the ITU Q.708 administrative boundaries. Alternatively, in a national deployment, the PC Routing Format may be set to correspond to the administrative boundaries of the national organization. \n For ITU based, must be 14-bit compatible, for Japan 16-bit, while ANSI and China 24-bit. \n\n Valid options are: 8.8.8, 3.8.3, ff-ff, 4.4.6, 5.4.7, 3.4.7, 4.3.7, 4.6.4, 6.4.4, 4.7.3, 5.4.5, and Decimal. Note that the dash delimiter is also accepted (i.e. 8-8-8). \n\n For ANSI platforms using SNAMI, the format must be 8.8.8"
    ::= { ptMTPMTP3NAEntry 90 }

ptMTPMTP3NAPCRoutingFormat OBJECT-TYPE
    SYNTAX          DisplayString (SIZE(0..255))
    MAX-ACCESS      read-create
    STATUS          current
    DESCRIPTION     
            "Point Code Routing Format based on SS7 Variant. \n The PC Routing format is defined to delimiter the point code for SS7 routing purposes to determine the breakdown of the network.cluster.member in ANSI based networks (zone.area.member in ITU). The most common usage is for network or cluster based routeset definitions in MTP3. \n The PC Display format is used only to display the point code value in the UI and logs. Some PC Display format cannot be defined as PC Routing formats as they do not identify the PC delimiter breakdown such as ITU Decimal and Japan ff-ff. \n For example, in ITU, the PC Routing Format may be set to '3.8.3' while the PC Display Format may be '3.8.3' or Decimal. A PC Display format of '3.8.3' displays a point code like '1.002.3' while in Decimal displays the same point code as '2067'. In ANSI, the PC Routing and Display formats must both be set to '8.8.8'. \n Note: the PC Display and Routing formats are typically identical unless the PC Display is set to ITU Decimal or Japan ff-ff which do not have delimiter information for routing procedures. \n Note: Member and cluster routing are part of the ANSI specifications. Default and Network routing are an enhancement in the DSC MTP3 implementation. While ITU specifications only mention member routesets, where a PC can be treated as a simple number, the DSC routeset implementation supports all 4 types (MEMBER, CLUSTER, NETWORK, and DEFAULT) in all SS7 variants for a possibly more flexible configuration. As the Cluster and Network routesets are available as an option in all SS7 Variants, the PC Routing Format must be specified when creating an MTP3 NA, to indicate which part of the point code is the network, cluster and member. If the CLUSTER and NETWORK routeset types are not required for a given ITU deployment, the MTP3 NA PC Routing Format is recommended to be set to 3.8.3 to agree with the ITU Q.708 administrative boundaries. Alternatively, in a national deployment, the PC Routing Format may be set to correspond to the administrative boundaries of the national organization. \n For ITU based, must be 14-bit compatible, for Japan 16-bit, while ANSI and China 24-bit. The x-y or x-y-z fields must be 8-bit or less. \n Valid options are: 8.8.8, 3.8.3, 4.4.6, 5.4.7, 3.4.7, 4.3.7, 4.6.4, 6.4.4, 4.7.3, and 5.4.5."
    ::= { ptMTPMTP3NAEntry 91 }

ptMTPMTP3NAMaxEqualCostRoutes OBJECT-TYPE
    SYNTAX          Integer32 (2..4)
    MAX-ACCESS      read-create
    STATUS          current
    DESCRIPTION     
            "Set the maximum number of equal cost routes per routeset."
    ::= { ptMTPMTP3NAEntry 92 }

ptMTPMTP3NAApplicationIDMgmt OBJECT-TYPE
    SYNTAX          INTEGER { none(0), ptC20(1) }
    MAX-ACCESS      read-create
    STATUS          current
    DESCRIPTION     
            "Application ID Management feature for registered AppID special handling. \nThis feature is designed for application related deployments where the registration of the associated Application ID (aka same name as this attribute) triggers predetermined MTP3 events such as link outage, special user messaging, and so forth. \nSupported values: NONE and PT_C20. \nBy default, the attribute is set to NONE. \nThe attribute can only modified when the node is cleared and inactive. \nMust be set to PT_C20 for SP2K deployments interfacing with a C20 call agents."
    ::= { ptMTPMTP3NAEntry 93 }

ptMTPMTP3NAGenerateTFM OBJECT-TYPE
    SYNTAX          INTEGER { disabled(0), enabled(1) }
    MAX-ACCESS      read-create
    STATUS          current
    DESCRIPTION     
            "TFM generation for PT_C20 End Nodes. \nEnabled by default. Can only be disabled if the Application ID Mgmt is set to PT_C20 and the VNode and Routing features are disabled. When disabled, all TFM messages (TFP, TFA, TCP, etc) are not generated by the MTP3 NA."
    ::= { ptMTPMTP3NAEntry 94 }

ptMTPMTP3NADiscardMSUDPCEqualsOPC OBJECT-TYPE
    SYNTAX          INTEGER { disabled(0), enabled(1) }
    MAX-ACCESS      read-create
    STATUS          current
    DESCRIPTION     
            "Discard MSUs incoming from L4 Connections with DPC equal to OPC. \nIf set to ENABLED, MSUs from MTP3 users (such as SCCP/GTT and Signaling Gateway) are discarded if the MSU's OPC and DPC are identical. In cases with complicated internal routing, an MSU might have its OPC equal to its DPC as a transient state, in which case this attribute might need to be set to DISABLED. \nBy default, the attribute is set to ENABLED."
    ::= { ptMTPMTP3NAEntry 95 }

ptMTPMTP3NAEnableAlarmsOnActivate OBJECT-TYPE
    SYNTAX          INTEGER { disabled(0), enabled(1) }
    MAX-ACCESS      read-create
    STATUS          current
    DESCRIPTION     
            "Enable Alarms on Activate. \nWhen ENABLED, Alarms are forced to the enabled state when the object is Activated. \nWhen DISABLED, Alarms retain their current state when the object is Activated. \nDefault Value: ENABLED. \nValid values: ENABLED, DISABLED."
    ::= { ptMTPMTP3NAEntry 96 }

ptMTPMTP3NAConfirmationRequired OBJECT-TYPE
    SYNTAX          INTEGER { disabled(0), enabled(1) }
    MAX-ACCESS      read-create
    STATUS          current
    DESCRIPTION     
            "This flag is used to turn on the confirmation request dialogue when the last link in a linkset is deactivated. The dialogue notifies the user of the possible consequences of deactivation the last link in a linkset."
    ::= { ptMTPMTP3NAEntry 98 }

ptMTPMTP3NANTTUSNSupport OBJECT-TYPE
    SYNTAX          INTEGER { disabled(0), enabled(1) }
    MAX-ACCESS      read-create
    STATUS          current
    DESCRIPTION     
            "The NTT USN message is part of the NTT standard. This attribute also allows USN support to be enabled in TTC. \nWhen this feature is enabled, a received SRT with an unknown Destination Point Code is answered with a USN sent to the SRT OPC and not with the usual TFP. \nThis attribute is ENABLED for NTT, configurable in TTC with default DISABLED, and is DISABLED and not configurable in other SS7 variants."
    ::= { ptMTPMTP3NAEntry 99 }

ptMTPMTP3NARxMSUCount OBJECT-TYPE
    SYNTAX          Integer32 (-2147483648..2147483647)
    MAX-ACCESS      read-only
    STATUS          current
    DESCRIPTION     
            "Number of MSUs received per second for the NA"
    ::= { ptMTPMTP3NAEntry 100 }

ptMTPMTP3NATxMSUCount OBJECT-TYPE
    SYNTAX          Integer32 (-2147483648..2147483647)
    MAX-ACCESS      read-only
    STATUS          current
    DESCRIPTION     
            "Number of MSUs transmitted per second for the NA"
    ::= { ptMTPMTP3NAEntry 101 }

ptMTPMTP3NAL3T19Notification OBJECT-TYPE
    SYNTAX          INTEGER { disabled(0), enabled(1) }
    MAX-ACCESS      read-create
    STATUS          current
    DESCRIPTION     
            "This parameter affects the behaviour of the ANSI Link Craft Referral Timer (ANSI T19). See GR-246-CORE issue 10 T1.111.4 section 12.2 and 12.3 and GR-82-CORE section 4.2.4.10.1 for more details. If the Notification is set to enabled, then the system logs each T19 expiry event after unsuccessful activation of a link. If this attribute is set to disabled, then no system logs are generated when a link fails to come into service within T19."
    ::= { ptMTPMTP3NAEntry 130 }

ptMTPMTP3NAL3T19LinkReset OBJECT-TYPE
    SYNTAX          INTEGER { disabled(0), enabled(1) }
    MAX-ACCESS      read-create
    STATUS          current
    DESCRIPTION     
            "This parameter affects the behaviour of the ANSI Link Craft Referral Timer (ANSI T19). See GR-246-CORE issue 10 T1.111.4 section 12.2 and 12.3 and GR-82-CORE section 4.2.4.10.1 for more details. If this attribute is set to enabled, then the link will be reset after each expiry of T19 timer. If this attribute is disabled, then the link will not be reset after the expiry of T19 timer."
    ::= { ptMTPMTP3NAEntry 131 }

ptMTPMTP3NAL3T19Attempts OBJECT-TYPE
    SYNTAX          INTEGER { zero(0), one(1), two(2), three(3), 
                        forever(4) }
    MAX-ACCESS      read-create
    STATUS          current
    DESCRIPTION     
            "This parameter affects the behaviour of the ANSI Link Craft Referral Timer (ANSI T19). See GR-246-CORE issue 10 T1.111.4 section 12.2 and 12.3 and GR-82-CORE section 4.2.4.10.1 for more details. \n \n If this attribute is set to FOREVER, then the timer runs forever until the link gets activated. After each expiry of the timer, the link is either reset or continued for activation depending on the L3 T19 Link Reset setting. \n \n If this attribute is set to ZERO, then the timer is totally disabled and will not run at all. If this attribute is set to ONE, then the link will stop activating and is deactivated after the first T19 expiry. \n \n If this attribute is set to TWO or THREE and if the L3 T19 Link Reset setting is enabled then the link-reset continue forever. If this attribute is set to TWO or THREE and if L3 T19 Link Reset attribute is disabled then the link will continue to get activated for 1 or 2 periods of T19 duration depending on the selection, and finally timer will stop the link activation, and it deactivates the link after the last T19 expiry."
    ::= { ptMTPMTP3NAEntry 132 }

ptMTPMTP3NAL3T31FalseLinkCongestion OBJECT-TYPE
    SYNTAX          INTEGER { disabledAllCongestionLevels(0), 
                        enabledAllCongestionLevels(1), 
                        enabledAllExceptLevel1(2) }
    MAX-ACCESS      read-create
    STATUS          current
    DESCRIPTION     
            " This parameter affects the behaviour of L3 False Link Congestion timer (ANSI T31). See GR-246-CORE issue 10 T1.111.4 section 3.8.2.2 and GR-82-CORE section 4.2.4.1 R4-42 to R4-44 for more details. \n \n If L3 T31 False Link Congestion attribute is set to DISABLED_ALL_CONGESTION_LEVELS, then the timer will not run at all. \n \n If the attribute is set to ENABLED_ALL_CONGESTION_LEVELS, then the timer is started whenever the link congestion level changes to a value greater than level 0. The timer is restarted on every change of congestion level between level 1, level 2 and level 3. When the congestion level drops to level 0 then the timer is cancelled or if the timer expires then the link is restarted. \n \n If the attribute is set to ENABLED_ALL_EXCEPT_LEVEL1, then the congestion level 1 is not considered for starting and restarting the timer. If the congestion level changes to level 2 or level 3 then the timer is started. The timer is restarted whenever the congestion level changes between level 2 and level 3. When the congestion level drops to level 1 or level 0, then the timer is cancelled or if the timer expires then the link is restarted. \n \n The timer value is taken from the timer T31 and it should be in the range of 10000 msec to 120000 msec and the default value is 30000 msec. Whenever the link is restarted due to expiry of the timer, then the management is notified by the system log."
    ::= { ptMTPMTP3NAEntry 133 }

ptMTPMTP3NALoadshareMode OBJECT-TYPE
    SYNTAX          INTEGER { sls(1), sccp0(2), enhancedSls(3), 
                        enhancedSlsAndSccp0(4), ttcAbPlane(5) }
    MAX-ACCESS      read-create
    STATUS          current
    DESCRIPTION     
            "Loadshare mode affects the algorithm that determines which MSUs are routed on which links (the loadsharing algorithm). When set to 'SLS', the usual loadsharing algorithm is used, based on the SLS in the incoming MSU. This algorithm is usually satisfactory, but may have drawbacks in some SS7 variants and network configurations in which the range of meaningful SLS values may be limited. Also, MSUs such as SCCP messages with Protocol Class 0 do not have sequencing requirements. When set to 'SCCP0', SCCP messages that do not require sequencing are loadshared evenly between links without regard to the incoming SLS and the outgoing SLS is modified. Other MSUs are loadshared in the usual way using the MSU SLS. When set to 'ENHANCED SLS', a new SLS value is generated based on incoming information such as OPC, DPC and link SLC. When set to ENHANCED SLS AND SCCP0, the option will process Protocol class 0 messages first and use the same functionality at SCCP0, plus remaining messages are processed using the same functionality as the ENHANCED SLS option. Applies to SI > 2 messages only. When set to 'TTC AB PLANE' the A/B Plane Bit is used to select the outgoing linkset. This attribute only takes effect if a routeset is using a combined linkset (two routes with equal cost), and if one linkset is configured as a A-plane linkset (using the Linkset 'AB Plane Bit' attribute) and the other linkset is configured as a B-plane linkset. In this case, the A/B Plane Bit in the MSU SLS is used to select the outgoing linkset when sufficient links are available. In some cases there is a trade-off between evenly distributing traffic across available links and respecting the A/B bit for linkset selection. These cases are handled as follows. \n* If each linkset has half or more its links available, the AB Plane Bit is used to select the outgoing linkset and the other SLS bits are used to select the link within the linkset. \n* If one of the linksets has less than half its links available (''abnormal'' or ''quasi-normal'') but the other linkset has half or more its links available (''normal'' or ''fully normal''), then only one linkset is used for traffic: the linkset with half or more of its links available. \n* If each linkset has less than half its links available, priority is given to making the traffic on each link as even as possible, while respecting the AB Plane Bit when this doesn't further unbalance traffic."
    ::= { ptMTPMTP3NAEntry 134 }

ptMTPMTP3NAMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPMTP3NAEntry 242 }

ptMTPMTP3NAActions OBJECT-TYPE
    SYNTAX          INTEGER { activate(1), deactivate(2), 
                        restoreDebugDefaults(3) }
    MAX-ACCESS      read-create
    STATUS          current
    DESCRIPTION     
            "The OID of all possible actions for this instance"
    ::= { ptMTPMTP3NAEntry 252 }

ptMTPMTP3NAParentOID OBJECT-TYPE
    SYNTAX          OBJECT IDENTIFIER
    MAX-ACCESS      read-create
    STATUS          current
    DESCRIPTION     
            "The OID of the parent object for this instance"
    ::= { ptMTPMTP3NAEntry 253 }

ptMTPMTP3NARowStatus OBJECT-TYPE
    SYNTAX          RowStatus
    MAX-ACCESS      read-create
    STATUS          current
    DESCRIPTION     
            "The row status for the MTPMTP3NA table"
    ::= { ptMTPMTP3NAEntry 254 }

ptMTPMTP3NAIndex OBJECT-TYPE
    SYNTAX          Integer32 (-2147483648..2147483647)
    MAX-ACCESS      not-accessible
    STATUS          current
    DESCRIPTION     
            "The row number for the MTPMTP3NA table"
    ::= { ptMTPMTP3NAEntry 255 }

ptMTPDREs OBJECT IDENTIFIER
    ::= { ptMTPMTP3NA 49 }

ptMTPDREsTable OBJECT-TYPE
    SYNTAX          SEQUENCE OF PtMTPDREsEntry
    MAX-ACCESS      not-accessible
    STATUS          current
    DESCRIPTION     
            "No description supplied in the proxy config file."
    ::= { ptMTPDREs 1 }

ptMTPDREsEntry OBJECT-TYPE
    SYNTAX          PtMTPDREsEntry
    MAX-ACCESS      not-accessible
    STATUS          current
    DESCRIPTION     
            "A sequence of MTPDREs attributes."
    INDEX           { ptConnGroupIndex, ptMTPDREsMTP3NAManagerIndex, 
                      ptMTPDREsMTP3NAIndex, ptMTPDREsIndex }
    ::= { ptMTPDREsTable 1 }

PtMTPDREsEntry ::=
    SEQUENCE {
        ptMTPDREsCount                  Integer32,
        ptMTPDREsMTP3NAManagerIndex     Integer32,
        ptMTPDREsMTP3NAIndex            Integer32,
        ptMTPDREsParentOID              OBJECT IDENTIFIER,
        ptMTPDREsRowStatus              RowStatus,
        ptMTPDREsIndex                  Integer32
    }

ptMTPDREsCount OBJECT-TYPE
    SYNTAX          Integer32 (-2147483648..2147483647)
    MAX-ACCESS      read-only
    STATUS          current
    DESCRIPTION     
            "Number of DREs"
    ::= { ptMTPDREsEntry 1 }

ptMTPDREsMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPDREsEntry 242 }

ptMTPDREsMTP3NAIndex OBJECT-TYPE
    SYNTAX          Integer32 (-2147483648..2147483647)
    MAX-ACCESS      not-accessible
    STATUS          current
    DESCRIPTION     
            "This is the index of the parent type for this object.
             This parent type is MTP3NA."
    ::= { ptMTPDREsEntry 243 }

ptMTPDREsParentOID OBJECT-TYPE
    SYNTAX          OBJECT IDENTIFIER
    MAX-ACCESS      read-create
    STATUS          current
    DESCRIPTION     
            "The OID of the parent object for this instance"
    ::= { ptMTPDREsEntry 253 }

ptMTPDREsRowStatus OBJECT-TYPE
    SYNTAX          RowStatus
    MAX-ACCESS      read-create
    STATUS          current
    DESCRIPTION     
            "The row status for the MTPDREs table"
    ::= { ptMTPDREsEntry 254 }

ptMTPDREsIndex OBJECT-TYPE
    SYNTAX          Integer32 (-2147483648..2147483647)
    MAX-ACCESS      not-accessible
    STATUS          current
    DESCRIPTION     
            "The row number for the MTPDREs table"
    ::= { ptMTPDREsEntry 255 }

ptMTPDRE OBJECT IDENTIFIER
    ::= { ptMTPDREs 47 }

ptMTPDRETable OBJECT-TYPE
    SYNTAX          SEQUENCE OF PtMTPDREEntry
    MAX-ACCESS      not-accessible
    STATUS          current
    DESCRIPTION     
            "The Distributed Routing Engine (DRE) is the process that implements 
             the signaling message handling portion of the MTP Level 3 (MTP3). 
             This process works closely with Signaling Network Management 
             (SNM) to provide MTP Level 3 functionality. The DRE provides 
             most of the message routing, while the SNM manages links, routes, 
             the associated Signaling Link Selection (SLS) tables, and the 
             user interface for configuration. \nIn most cases there is simply 
             one DRE and one SNM per CPU, however some configurations may 
             have a number of remote DRE processes reporting back to a central 
             SNM."
    ::= { ptMTPDRE 1 }

ptMTPDREEntry OBJECT-TYPE
    SYNTAX          PtMTPDREEntry
    MAX-ACCESS      not-accessible
    STATUS          current
    DESCRIPTION     
            "A sequence of MTPDRE attributes."
    INDEX           { ptConnGroupIndex, ptMTPDREMTP3NAManagerIndex, 
                      ptMTPDREMTP3NAIndex, ptMTPDREDREsIndex, 
                      ptMTPDREIndex }
    ::= { ptMTPDRETable 1 }

PtMTPDREEntry ::=
    SEQUENCE {
        ptMTPDREContext                 DisplayString,
        ptMTPDREDREID                   Integer32,
        ptMTPDRECLLI                    DisplayString,
        ptMTPDREState                   INTEGER,
        ptMTPDREIPAddress1              DisplayString,
        ptMTPDREIPAddress2              DisplayString,
        ptMTPDREMTP3NAManagerIndex      Integer32,
        ptMTPDREMTP3NAIndex             Integer32,
        ptMTPDREDREsIndex               Integer32,
        ptMTPDREParentOID               OBJECT IDENTIFIER,
        ptMTPDRERowStatus               RowStatus,
        ptMTPDREIndex                   Integer32
    }

ptMTPDREContext OBJECT-TYPE
    SYNTAX          DisplayString (SIZE(0..255))
    MAX-ACCESS      read-only
    STATUS          current
    DESCRIPTION     
            "A system generated condensed textual identifier of the DRE object."
    ::= { ptMTPDREEntry 1 }

ptMTPDREDREID OBJECT-TYPE
    SYNTAX          Integer32 (1..64)
    MAX-ACCESS      read-only
    STATUS          current
    DESCRIPTION     
            "A unique identifier for the DRE object. \n The ID is set at creation time and cannot be modified after that. \nThe Distributed Routing Engine (DRE) is the process that implements the signaling message handling portion of the MTP Level 3 (MTP3). This process works closely with Signaling Network Management (SNM) to provide MTP Level 3 functionality. The DRE provides most of the message routing, while the SNM manages links, routes, the associated Signaling Link Selection (SLS) tables, and the user interface for configuration. \nIn most cases there is one DRE and one SNM per slot, however some configurations may have a number of remote DRE processes reporting back to a central SNM."
    ::= { ptMTPDREEntry 2 }

ptMTPDRECLLI OBJECT-TYPE
    SYNTAX          DisplayString (SIZE(0..255))
    MAX-ACCESS      read-create
    STATUS          current
    DESCRIPTION     
            "CLLI code of this DRE object. The CLLI code may be specified by your network designer. The value here is for informational purposes only and may be left blank."
    ::= { ptMTPDREEntry 3 }

ptMTPDREState OBJECT-TYPE
    SYNTAX          INTEGER { inactive(-1), unavailable(0), available(1), 
                        versionMismatch(2) }
    MAX-ACCESS      read-only
    STATUS          current
    DESCRIPTION     
            "Status of the DRE connection (AVAILABLE or UNAVAILABLE). \nMust show as AVAILABLE to be functional. If it is UNAVAILABLE links using it will not align. In this case you should check the IP addressing in the next attributes."
    ::= { ptMTPDREEntry 4 }

ptMTPDREIPAddress1 OBJECT-TYPE
    SYNTAX          DisplayString (SIZE(0..255))
    MAX-ACCESS      read-create
    STATUS          current
    DESCRIPTION     
            "Primary IP address of this DRE. A host name from /etc/hosts or an IP address can be used. A host name is preferred."
    ::= { ptMTPDREEntry 5 }

ptMTPDREIPAddress2 OBJECT-TYPE
    SYNTAX          DisplayString (SIZE(0..255))
    MAX-ACCESS      read-create
    STATUS          current
    DESCRIPTION     
            "Secondary IP address of this DRE. A host name from /etc/hosts or an IP address can be used. A host name is preferred."
    ::= { ptMTPDREEntry 6 }

ptMTPDREMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPDREEntry 242 }

ptMTPDREMTP3NAIndex OBJECT-TYPE
    SYNTAX          Integer32 (-2147483648..2147483647)
    MAX-ACCESS      not-accessible
    STATUS          current
    DESCRIPTION     
            "This is the index of the parent type for this object.
             This parent type is MTP3NA."
    ::= { ptMTPDREEntry 243 }

ptMTPDREDREsIndex OBJECT-TYPE
    SYNTAX          Integer32 (-2147483648..2147483647)
    MAX-ACCESS      not-accessible
    STATUS          current
    DESCRIPTION     
            "This is the index of the parent type for this object.
             This parent type is DREs."
    ::= { ptMTPDREEntry 244 }

ptMTPDREParentOID OBJECT-TYPE
    SYNTAX          OBJECT IDENTIFIER
    MAX-ACCESS      read-create
    STATUS          current
    DESCRIPTION     
            "The OID of the parent object for this instance"
    ::= { ptMTPDREEntry 253 }

ptMTPDRERowStatus OBJECT-TYPE
    SYNTAX          RowStatus
    MAX-ACCESS      read-create
    STATUS          current
    DESCRIPTION     
            "The row status for the MTPDRE table"
    ::= { ptMTPDREEntry 254 }

ptMTPDREIndex OBJECT-TYPE
    SYNTAX          Integer32 (-2147483648..2147483647)
    MAX-ACCESS      not-accessible
    STATUS          current
    DESCRIPTION     
            "The row number for the MTPDRE table"
    ::= { ptMTPDREEntry 255 }

ptMTPL2Connections OBJECT IDENTIFIER
    ::= { ptMTPMTP3NA 61 }

ptMTPL2ConnectionsTable OBJECT-TYPE
    SYNTAX          SEQUENCE OF PtMTPL2ConnectionsEntry
    MAX-ACCESS      not-accessible
    STATUS          current
    DESCRIPTION     
            "No description supplied in the proxy config file."
    ::= { ptMTPL2Connections 1 }

ptMTPL2ConnectionsEntry OBJECT-TYPE
    SYNTAX          PtMTPL2ConnectionsEntry
    MAX-ACCESS      not-accessible
    STATUS          current
    DESCRIPTION     
            "A sequence of MTPL2Connections attributes."
    INDEX           { ptConnGroupIndex, 
                      ptMTPL2ConnectionsMTP3NAManagerIndex, 
                      ptMTPL2ConnectionsMTP3NAIndex, 
                      ptMTPL2ConnectionsIndex }
    ::= { ptMTPL2ConnectionsTable 1 }

PtMTPL2ConnectionsEntry ::=
    SEQUENCE {
        ptMTPL2ConnectionsCount         Integer32,
        ptMTPL2ConnectionsMTP3NAManagerIndex    Integer32,
        ptMTPL2ConnectionsMTP3NAIndex   Integer32,
        ptMTPL2ConnectionsParentOID     OBJECT IDENTIFIER,
        ptMTPL2ConnectionsRowStatus     RowStatus,
        ptMTPL2ConnectionsIndex         Integer32
    }

ptMTPL2ConnectionsCount OBJECT-TYPE
    SYNTAX          Integer32 (-2147483648..2147483647)
    MAX-ACCESS      read-only
    STATUS          current
    DESCRIPTION     
            "Number of L2 Connections"
    ::= { ptMTPL2ConnectionsEntry 1 }

ptMTPL2ConnectionsMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPL2ConnectionsEntry 242 }

ptMTPL2ConnectionsMTP3NAIndex OBJECT-TYPE
    SYNTAX          Integer32 (-2147483648..2147483647)
    MAX-ACCESS      not-accessible
    STATUS          current
    DESCRIPTION     
            "This is the index of the parent type for this object.
             This parent type is MTP3NA."
    ::= { ptMTPL2ConnectionsEntry 243 }

ptMTPL2ConnectionsParentOID OBJECT-TYPE
    SYNTAX          OBJECT IDENTIFIER
    MAX-ACCESS      read-create
    STATUS          current
    DESCRIPTION     
            "The OID of the parent object for this instance"
    ::= { ptMTPL2ConnectionsEntry 253 }

ptMTPL2ConnectionsRowStatus OBJECT-TYPE
    SYNTAX          RowStatus
    MAX-ACCESS      read-create
    STATUS          current
    DESCRIPTION     
            "The row status for the MTPL2Connections table"
    ::= { ptMTPL2ConnectionsEntry 254 }

ptMTPL2ConnectionsIndex OBJECT-TYPE
    SYNTAX          Integer32 (-2147483648..2147483647)
    MAX-ACCESS      not-accessible
    STATUS          current
    DESCRIPTION     
            "The row number for the MTPL2Connections table"
    ::= { ptMTPL2ConnectionsEntry 255 }

ptMTPL2Connection OBJECT IDENTIFIER
    ::= { ptMTPL2Connections 48 }

ptMTPL2ConnectionTable OBJECT-TYPE
    SYNTAX          SEQUENCE OF PtMTPL2ConnectionEntry
    MAX-ACCESS      not-accessible
    STATUS          current
    DESCRIPTION     
            "A sequence of L2 Connection attributes. The L2 Connection indicates 
             to the DRE where the IO is taking place for the links. unless 
             you are adding IO cards, or are using a remote L2 Connection, 
             you should rarely need to create a new L2 Connection."
    ::= { ptMTPL2Connection 1 }

ptMTPL2ConnectionEntry OBJECT-TYPE
    SYNTAX          PtMTPL2ConnectionEntry
    MAX-ACCESS      not-accessible
    STATUS          current
    DESCRIPTION     
            "A sequence of MTPL2Connection attributes."
    INDEX           { ptConnGroupIndex, 
                      ptMTPL2ConnectionMTP3NAManagerIndex, 
                      ptMTPL2ConnectionMTP3NAIndex, 
                      ptMTPL2ConnectionL2ConnectionsIndex, 
                      ptMTPL2ConnectionIndex }
    ::= { ptMTPL2ConnectionTable 1 }

PtMTPL2ConnectionEntry ::=
    SEQUENCE {
        ptMTPL2ConnectionContext        DisplayString,
        ptMTPL2ConnectionCageName       DisplayString,
        ptMTPL2ConnectionCageID         Integer32,
        ptMTPL2ConnectionType           INTEGER,
        ptMTPL2ConnectionMTP2ProtocolVersion    Integer32,
        ptMTPL2ConnectionDREID          Integer32,
        ptMTPL2ConnectionState          INTEGER,
        ptMTPL2ConnectionLocalIPAddress1 DisplayString,
        ptMTPL2ConnectionLocalIPAddress2 DisplayString,
        ptMTPL2ConnectionLocalPort      Integer32,
        ptMTPL2ConnectionRemoteIPAddress1 DisplayString,
        ptMTPL2ConnectionRemoteIPAddress2 DisplayString,
        ptMTPL2ConnectionRemotePort     Integer32,
        ptMTPL2ConnectionHeartbeat      INTEGER,
        ptMTPL2ConnectionHeartbeatInterval  Integer32,
        ptMTPL2ConnectionRTOInitial     Integer32,
        ptMTPL2ConnectionRTOMinimum     Integer32,
        ptMTPL2ConnectionRTOMaximum     Integer32,
        ptMTPL2ConnectionMaximumPathRetrans   Integer32,
        ptMTPL2ConnectionMaximumAssocRetrans    Integer32,
        ptMTPL2ConnectionBundling       INTEGER,
        ptMTPL2ConnectionBundlingTO     Integer32,
        ptMTPL2ConnectionDelayedACKTO   Integer32,
        ptMTPL2ConnectionFastRetransThreshold     Integer32,
        ptMTPL2ConnectionChecksum       INTEGER,
        ptMTPL2ConnectionSCTPDebugLevel Integer32,
        ptMTPL2ConnectionAssociationNumber  Integer32,
        ptMTPL2ConnectionConnectionTimeout  INTEGER,
        ptMTPL2ConnectionConnectionRetry INTEGER,
        ptMTPL2ConnectionCommandTimeout INTEGER,
        ptMTPL2ConnectionCommandRetry   INTEGER,
        ptMTPL2ConnectionMTP2ProtocolType INTEGER,
        ptMTPL2ConnectionM2UAVariant    INTEGER,
        ptMTPL2ConnectionMTP3NAManagerIndex   Integer32,
        ptMTPL2ConnectionMTP3NAIndex    Integer32,
        ptMTPL2ConnectionL2ConnectionsIndex   Integer32,
        ptMTPL2ConnectionActions        INTEGER,
        ptMTPL2ConnectionParentOID      OBJECT IDENTIFIER,
        ptMTPL2ConnectionRowStatus      RowStatus,
        ptMTPL2ConnectionIndex          Integer32
    }

ptMTPL2ConnectionContext OBJECT-TYPE
    SYNTAX          DisplayString (SIZE(0..255))
    MAX-ACCESS      read-only
    STATUS          current
    DESCRIPTION     
            "A system generated condensed textual representation of the L2 Connection object."
    ::= { ptMTPL2ConnectionEntry 1 }

ptMTPL2ConnectionCageName OBJECT-TYPE
    SYNTAX          DisplayString (SIZE(0..255))
    MAX-ACCESS      read-create
    STATUS          current
    DESCRIPTION     
            "A descriptive name for the chassis running the L2 Connection object. In many case this is the same chassis as the CPU. This attribute is text only and is used for operator informational purposes only."
    ::= { ptMTPL2ConnectionEntry 2 }

ptMTPL2ConnectionCageID OBJECT-TYPE
    SYNTAX          Integer32 (0..127)
    MAX-ACCESS      read-only
    STATUS          current
    DESCRIPTION     
            "Cage identifier as per Hardware Manager definition. The value given here must correspond to the value specified when the Hardware Manager was configured. \nThe 6301 and 4301 systems will come configured with L2 Connections for the available slots in the chassis. The Cage Ids are listed by slot number as 4-9. \nOn other systems, typically one L2 module is preconfigured and it is listed as Cage Id 1."
    ::= { ptMTPL2ConnectionEntry 3 }

ptMTPL2ConnectionType OBJECT-TYPE
    SYNTAX          INTEGER { hwmSctp(0), hwmTcp(1), tipc(4) }
    MAX-ACCESS      read-only
    STATUS          current
    DESCRIPTION     
            "L2 Connection communications with the DRE can be handled over TCP/IP, SCTP/IP, ATM or the DRE and L2 can be local to each other. SCTP is a telecom specific protocol similar to TCP. SCTP has certain features for guaranteed delivery of packets and sequencing, making it a better choice for this purpose. \nThe protocol used by default is HWM_SCTP, unless you are working on a one card (blade) system. \nThe values for Type, MTP2 Protocol Type, and MTP2 Protocol Version are related. These are layers in a protocol between the DRE and the Level 2 modules."
    ::= { ptMTPL2ConnectionEntry 4 }

ptMTPL2ConnectionMTP2ProtocolVersion OBJECT-TYPE
    SYNTAX          Integer32 (-2147483648..2147483647)
    MAX-ACCESS      read-only
    STATUS          current
    DESCRIPTION     
            "The Internal Protocol version used to interact with this L2 Connection is displayed in this attribute. It is here for informational purposes only and indicates to customer support the relative ages of the software loads being used. \nThe values for Type, MTP2 Protocol Type, and MTP2 Protocol Version are related. These are layers in a protocol between the DRE and the Level 2 modules."
    ::= { ptMTPL2ConnectionEntry 6 }

ptMTPL2ConnectionDREID OBJECT-TYPE
    SYNTAX          Integer32 (1..64)
    MAX-ACCESS      read-only
    STATUS          current
    DESCRIPTION     
            "DRE to manage the L2 Connection. This value is specified at creation time of the L2 Connection, and cannot be modified thereafter."
    ::= { ptMTPL2ConnectionEntry 7 }

ptMTPL2ConnectionState OBJECT-TYPE
    SYNTAX          INTEGER { inactive(-1), unavailable(0), available(1), 
                        versionMismatch(2) }
    MAX-ACCESS      read-only
    STATUS          current
    DESCRIPTION     
            "Status of this L2 Connection (INACTIVE, UNAVAILABLE, VERSION MISMATCH, AVAILABLE). The most common cause of an UNAVAILABLE destination is an IP configuration issue. Should the connection between the DRE and the L2 Connection be UNAVAILABLE, we suggest you see if any of the IP configuration was recently changed and refer to the log messages. VERSION MISMATCH means mismatch between protocol type and protocol version."
    ::= { ptMTPL2ConnectionEntry 9 }

ptMTPL2ConnectionLocalIPAddress1 OBJECT-TYPE
    SYNTAX          DisplayString (SIZE(0..255))
    MAX-ACCESS      read-create
    STATUS          current
    DESCRIPTION     
            "Primary local address of this L2 Connection. This may be a hostname provisioned in /etc/hosts or an IP Address. This information is only used if the connection between the DRE and MTP2 uses SCTP. TCP/IP does not require knowledge of the local address. This value should not require modification in most configurations. This attribute can be modified only for M2UA L2 Connections."
    ::= { ptMTPL2ConnectionEntry 10 }

ptMTPL2ConnectionLocalIPAddress2 OBJECT-TYPE
    SYNTAX          DisplayString (SIZE(0..255))
    MAX-ACCESS      read-create
    STATUS          current
    DESCRIPTION     
            "Secondary local IP address of this L2 Connection. This may be a hostname provisioned in /etc/hosts or an IP Address. This information is only used if the connection between the DRE and MTP2 uses SCTP. TCP/IP does not require knowledge of the local address. This value should not require modification in most configurations. This attribute can be modified only for M2UA L2 Connections."
    ::= { ptMTPL2ConnectionEntry 11 }

ptMTPL2ConnectionLocalPort OBJECT-TYPE
    SYNTAX          Integer32 (0..9999)
    MAX-ACCESS      read-create
    STATUS          current
    DESCRIPTION     
            "Local port of L2 Connection. This value is used for SCTP only and should not require modification in most configurations. This attribute can be modified only for M2UA L2 Connections."
    ::= { ptMTPL2ConnectionEntry 12 }

ptMTPL2ConnectionRemoteIPAddress1 OBJECT-TYPE
    SYNTAX          DisplayString (SIZE(0..255))
    MAX-ACCESS      read-create
    STATUS          current
    DESCRIPTION     
            "Primary remote IP address of this L2 Connection. This is the address of an MTP2 process. It should be a hostname provisioned in /etc/hosts or an IP Address. This value should not require modification in most configurations. When the connection to MTP2 uses SCTP, this address is the SCTP Primary Path. This attribute can be modified only for M2UA L2 Connections."
    ::= { ptMTPL2ConnectionEntry 13 }

ptMTPL2ConnectionRemoteIPAddress2 OBJECT-TYPE
    SYNTAX          DisplayString (SIZE(0..255))
    MAX-ACCESS      read-create
    STATUS          current
    DESCRIPTION     
            "Secondary remote IP address of this L2 Connection. This is the address of an MTP2 process. It should be a hostname provisioned in /etc/hosts or an IP Address. This value should not require modification in most configurations. This attribute can be modified only for M2UA L2 Connections."
    ::= { ptMTPL2ConnectionEntry 14 }

ptMTPL2ConnectionRemotePort OBJECT-TYPE
    SYNTAX          Integer32 (0..9999)
    MAX-ACCESS      read-create
    STATUS          current
    DESCRIPTION     
            "Remote port of MTP2. This value should not require modification in most configurations. This attribute can be modified only for M2UA L2 Connections."
    ::= { ptMTPL2ConnectionEntry 15 }

ptMTPL2ConnectionHeartbeat OBJECT-TYPE
    SYNTAX          INTEGER { disabled(0), enabled(1) }
    MAX-ACCESS      read-create
    STATUS          current
    DESCRIPTION     
            "Enabling the Heartbeat Feature causes test message to the remote connection to determine its availability on the network \n The default value is ON."
    ::= { ptMTPL2ConnectionEntry 16 }

ptMTPL2ConnectionHeartbeatInterval OBJECT-TYPE
    SYNTAX          Integer32 (0..65535)
    MAX-ACCESS      read-create
    STATUS          current
    DESCRIPTION     
            "Heartbeat interval in milliseconds for the SCTP association. \nThe default value is 100 milliseconds."
    ::= { ptMTPL2ConnectionEntry 17 }

ptMTPL2ConnectionRTOInitial OBJECT-TYPE
    SYNTAX          Integer32 (0..2147483647)
    MAX-ACCESS      read-create
    STATUS          current
    DESCRIPTION     
            "Round-Trip Delay (RTO) Initial sets the initial expected time for packets to be sent and returned. Entered in milliseconds. \nThe default is 180 (ms)."
    ::= { ptMTPL2ConnectionEntry 18 }

ptMTPL2ConnectionRTOMinimum OBJECT-TYPE
    SYNTAX          Integer32 (0..2147483647)
    MAX-ACCESS      read-create
    STATUS          current
    DESCRIPTION     
            "Round Trip Delay (RTO) Minimum is the smallest expected time for packets to be sent and returned. Entered in milliseconds. The default is 180 (ms)."
    ::= { ptMTPL2ConnectionEntry 19 }

ptMTPL2ConnectionRTOMaximum OBJECT-TYPE
    SYNTAX          Integer32 (0..2147483647)
    MAX-ACCESS      read-create
    STATUS          current
    DESCRIPTION     
            "Round Trip Delay (RTO) Maximum is the largest expected time for packets to be sent and returned. Entered in milliseconds. The default is 250 (ms)."
    ::= { ptMTPL2ConnectionEntry 20 }

ptMTPL2ConnectionMaximumPathRetrans OBJECT-TYPE
    SYNTAX          Integer32 (0..2147483647)
    MAX-ACCESS      read-create
    STATUS          current
    DESCRIPTION     
            "Maximum path retransmissions sets the number of retransmissions that will be attempted over the current transmission path without success before the path is deemed unavailable and a new transmission path is sought. The default value is 10 and is to be used on a good quality local network."
    ::= { ptMTPL2ConnectionEntry 21 }

ptMTPL2ConnectionMaximumAssocRetrans OBJECT-TYPE
    SYNTAX          Integer32 (0..2147483647)
    MAX-ACCESS      read-create
    STATUS          current
    DESCRIPTION     
            "Maximum association retransmissions sets the number of retransmissions to a remote device over all possible paths that will be attempted without success before deeming the end device as unavailable. The default value is 15, and is to be used on a good quality local network."
    ::= { ptMTPL2ConnectionEntry 22 }

ptMTPL2ConnectionBundling OBJECT-TYPE
    SYNTAX          INTEGER { disabled(0), enabled(1) }
    MAX-ACCESS      read-create
    STATUS          current
    DESCRIPTION     
            "Enabling Bundling allows the bundling of messages into larger packets for greater line efficiency. \nThe default value is ON."
    ::= { ptMTPL2ConnectionEntry 23 }

ptMTPL2ConnectionBundlingTO OBJECT-TYPE
    SYNTAX          Integer32 (0..2147483647)
    MAX-ACCESS      read-create
    STATUS          current
    DESCRIPTION     
            "Bundling Time Out (TO) is set in milliseconds and indicates the length of time that messages will be queued before being bundled into larger packets. This is only applicable if the Bundling attribute is set to ON. \nThe default value is 20 milliseconds. "
    ::= { ptMTPL2ConnectionEntry 24 }

ptMTPL2ConnectionDelayedACKTO OBJECT-TYPE
    SYNTAX          Integer32 (10..500)
    MAX-ACCESS      read-create
    STATUS          current
    DESCRIPTION     
            "Delayed Acknowledgement Time Out (ACK TO) sets the time in milliseconds that the system waits after receiving a packet before sending an acknowledgement. \nThe valid range is between 10 and 500 milliseconds. \nThe default value is 20 milliseconds."
    ::= { ptMTPL2ConnectionEntry 25 }

ptMTPL2ConnectionFastRetransThreshold OBJECT-TYPE
    SYNTAX          Integer32 (0..2147483647)
    MAX-ACCESS      read-create
    STATUS          current
    DESCRIPTION     
            "Fast Retransmit Threshold sets the number of times a packet can be reported as missing before SCTP on the originating system retransmits packets using fast retransmission. \nThe default value is 4. "
    ::= { ptMTPL2ConnectionEntry 26 }

ptMTPL2ConnectionChecksum OBJECT-TYPE
    SYNTAX          INTEGER { crc32c(0), adler32(1), none(2), auto(3) }
    MAX-ACCESS      read-only
    STATUS          current
    DESCRIPTION     
            "Checksum sets the error detection algorithm on the SCTP connection. Valid values are: CRC32C, ADLER32, NONE, or AUTO. \nNot all options are available on all systems. \nThe default value is CRC32C. "
    ::= { ptMTPL2ConnectionEntry 27 }

ptMTPL2ConnectionSCTPDebugLevel OBJECT-TYPE
    SYNTAX          Integer32 (0..255)
    MAX-ACCESS      read-create
    STATUS          current
    DESCRIPTION     
            "SCTP debug level determines how much information is tracked and logged to the Debug Log file. It is recommended that one does NOT raise this value on a busy system, so that the CPU is not unduly busy proving log information rather that processing traffic. The values range from 0, meaning no debugging information, to 5, which provides a considerable amount of information. \nThe default value is 1. "
    ::= { ptMTPL2ConnectionEntry 28 }

ptMTPL2ConnectionAssociationNumber OBJECT-TYPE
    SYNTAX          Integer32 (0..2147483647)
    MAX-ACCESS      read-only
    STATUS          current
    DESCRIPTION     
            "SCTP Association Number"
    ::= { ptMTPL2ConnectionEntry 29 }

ptMTPL2ConnectionConnectionTimeout OBJECT-TYPE
    SYNTAX          INTEGER { default(-1) }
    MAX-ACCESS      read-create
    STATUS          current
    DESCRIPTION     
            "Connection timeout (ms), the amount of time we wait for a connection to establish before reporting a failure."
    ::= { ptMTPL2ConnectionEntry 30 }

ptMTPL2ConnectionConnectionRetry OBJECT-TYPE
    SYNTAX          INTEGER { default(-1) }
    MAX-ACCESS      read-create
    STATUS          current
    DESCRIPTION     
            "Connection retry interval (ms). This is the amount of time between connection attempts."
    ::= { ptMTPL2ConnectionEntry 31 }

ptMTPL2ConnectionCommandTimeout OBJECT-TYPE
    SYNTAX          INTEGER { default(-1) }
    MAX-ACCESS      read-create
    STATUS          current
    DESCRIPTION     
            "Command timeout (ms), the amount of time we wait for an acknowledgement of a Link command before declaring the link failed and starting the Command Retry timer."
    ::= { ptMTPL2ConnectionEntry 32 }

ptMTPL2ConnectionCommandRetry OBJECT-TYPE
    SYNTAX          INTEGER { default(-1) }
    MAX-ACCESS      read-create
    STATUS          current
    DESCRIPTION     
            "Command Retry (ms). If a command timeout occurs, mark the link as failed. Attempt to recover after this timer expires."
    ::= { ptMTPL2ConnectionEntry 33 }

ptMTPL2ConnectionMTP2ProtocolType OBJECT-TYPE
    SYNTAX          INTEGER { proprietary(0), m2ua(1), atmProprietary(2) }
    MAX-ACCESS      read-only
    STATUS          current
    DESCRIPTION     
            "The Internal Protocol API that is used to interact with this L2 Connection is either M2UA or a proprietary protocol. M2UA requires that the L2 Connection Communications Type be SCTP. \nThe values for Type, MTP2 Protocol Type, and MTP2 Protocol Version are related. These are layers in a protocol between the DRE and the Level 2 modules."
    ::= { ptMTPL2ConnectionEntry 34 }

ptMTPL2ConnectionM2UAVariant OBJECT-TYPE
    SYNTAX          INTEGER { generic(0), audiocodes(1) }
    MAX-ACCESS      read-create
    STATUS          current
    DESCRIPTION     
            "M2UA variant.\n The protocol defined in RFC3331, however there are many aspects described as implementation specific. "
    ::= { ptMTPL2ConnectionEntry 35 }

ptMTPL2ConnectionMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPL2ConnectionEntry 242 }

ptMTPL2ConnectionMTP3NAIndex OBJECT-TYPE
    SYNTAX          Integer32 (-2147483648..2147483647)
    MAX-ACCESS      not-accessible
    STATUS          current
    DESCRIPTION     
            "This is the index of the parent type for this object.
             This parent type is MTP3NA."
    ::= { ptMTPL2ConnectionEntry 243 }

ptMTPL2ConnectionL2ConnectionsIndex OBJECT-TYPE
    SYNTAX          Integer32 (-2147483648..2147483647)
    MAX-ACCESS      not-accessible
    STATUS          current
    DESCRIPTION     
            "This is the index of the parent type for this object.
             This parent type is L2Connections."
    ::= { ptMTPL2ConnectionEntry 244 }

ptMTPL2ConnectionActions OBJECT-TYPE
    SYNTAX          INTEGER { activate(1), deactivate(2) }
    MAX-ACCESS      read-create
    STATUS          current
    DESCRIPTION     
            "The OID of all possible actions for this instance"
    ::= { ptMTPL2ConnectionEntry 252 }

ptMTPL2ConnectionParentOID OBJECT-TYPE
    SYNTAX          OBJECT IDENTIFIER
    MAX-ACCESS      read-create
    STATUS          current
    DESCRIPTION     
            "The OID of the parent object for this instance"
    ::= { ptMTPL2ConnectionEntry 253 }

ptMTPL2ConnectionRowStatus OBJECT-TYPE
    SYNTAX          RowStatus
    MAX-ACCESS      read-create
    STATUS          current
    DESCRIPTION     
            "The row status for the MTPL2Connection table"
    ::= { ptMTPL2ConnectionEntry 254 }

ptMTPL2ConnectionIndex OBJECT-TYPE
    SYNTAX          Integer32 (-2147483648..2147483647)
    MAX-ACCESS      not-accessible
    STATUS          current
    DESCRIPTION     
            "The row number for the MTPL2Connection table"
    ::= { ptMTPL2ConnectionEntry 255 }

ptMTPVNodes OBJECT IDENTIFIER
    ::= { ptMTPMTP3NA 62 }

ptMTPVNodesTable OBJECT-TYPE
    SYNTAX          SEQUENCE OF PtMTPVNodesEntry
    MAX-ACCESS      not-accessible
    STATUS          current
    DESCRIPTION     
            "No description supplied in the proxy config file."
    ::= { ptMTPVNodes 1 }

ptMTPVNodesEntry OBJECT-TYPE
    SYNTAX          PtMTPVNodesEntry
    MAX-ACCESS      not-accessible
    STATUS          current
    DESCRIPTION     
            "A sequence of MTPVNodes attributes."
    INDEX           { ptConnGroupIndex, ptMTPVNodesMTP3NAManagerIndex, 
                      ptMTPVNodesMTP3NAIndex, ptMTPVNodesIndex }
    ::= { ptMTPVNodesTable 1 }

PtMTPVNodesEntry ::=
    SEQUENCE {
        ptMTPVNodesCount                Integer32,
        ptMTPVNodesMTP3NAManagerIndex   Integer32,
        ptMTPVNodesMTP3NAIndex          Integer32,
        ptMTPVNodesParentOID            OBJECT IDENTIFIER,
        ptMTPVNodesRowStatus            RowStatus,
        ptMTPVNodesIndex                Integer32
    }

ptMTPVNodesCount OBJECT-TYPE
    SYNTAX          Integer32 (-2147483648..2147483647)
    MAX-ACCESS      read-only
    STATUS          current
    DESCRIPTION     
            "Number of VNodes"
    ::= { ptMTPVNodesEntry 1 }

ptMTPVNodesMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPVNodesEntry 242 }

ptMTPVNodesMTP3NAIndex OBJECT-TYPE
    SYNTAX          Integer32 (-2147483648..2147483647)
    MAX-ACCESS      not-accessible
    STATUS          current
    DESCRIPTION     
            "This is the index of the parent type for this object.
             This parent type is MTP3NA."
    ::= { ptMTPVNodesEntry 243 }

ptMTPVNodesParentOID OBJECT-TYPE
    SYNTAX          OBJECT IDENTIFIER
    MAX-ACCESS      read-create
    STATUS          current
    DESCRIPTION     
            "The OID of the parent object for this instance"
    ::= { ptMTPVNodesEntry 253 }

ptMTPVNodesRowStatus OBJECT-TYPE
    SYNTAX          RowStatus
    MAX-ACCESS      read-create
    STATUS          current
    DESCRIPTION     
            "The row status for the MTPVNodes table"
    ::= { ptMTPVNodesEntry 254 }

ptMTPVNodesIndex OBJECT-TYPE
    SYNTAX          Integer32 (-2147483648..2147483647)
    MAX-ACCESS      not-accessible
    STATUS          current
    DESCRIPTION     
            "The row number for the MTPVNodes table"
    ::= { ptMTPVNodesEntry 255 }

ptMTPVNode OBJECT IDENTIFIER
    ::= { ptMTPVNodes 50 }

ptMTPVNodeTable OBJECT-TYPE
    SYNTAX          SEQUENCE OF PtMTPVNodeEntry
    MAX-ACCESS      not-accessible
    STATUS          current
    DESCRIPTION     
            "A Virtual Node is used by applications to register to this system 
             to send and receive gateway SS7 traffic over IP. VNodes may 
             be shared between the two mates of an STP pair."
    ::= { ptMTPVNode 1 }

ptMTPVNodeEntry OBJECT-TYPE
    SYNTAX          PtMTPVNodeEntry
    MAX-ACCESS      not-accessible
    STATUS          current
    DESCRIPTION     
            "A sequence of MTPVNode attributes."
    INDEX           { ptConnGroupIndex, ptMTPVNodeMTP3NAManagerIndex, 
                      ptMTPVNodeMTP3NAIndex, ptMTPVNodeVNodesIndex, 
                      ptMTPVNodeIndex }
    ::= { ptMTPVNodeTable 1 }

PtMTPVNodeEntry ::=
    SEQUENCE {
        ptMTPVNodeContext               DisplayString,
        ptMTPVNodeVPC                   Integer32,
        ptMTPVNodeCLLI                  DisplayString,
        ptMTPVNodeDescription           DisplayString,
        ptMTPVNodeState                 INTEGER,
        ptMTPVNodeBroadcastTFA          INTEGER,
        ptMTPVNodeBroadcastTFP          INTEGER,
        ptMTPVNodeBroadcastTFR          INTEGER,
        ptMTPVNodeMateSTPDistribution   INTEGER,
        ptMTPVNodeMTP3NAManagerIndex    Integer32,
        ptMTPVNodeMTP3NAIndex           Integer32,
        ptMTPVNodeVNodesIndex           Integer32,
        ptMTPVNodeActions               INTEGER,
        ptMTPVNodeParentOID             OBJECT IDENTIFIER,
        ptMTPVNodeRowStatus             RowStatus,
        ptMTPVNodeIndex                 Integer32
    }

ptMTPVNodeContext OBJECT-TYPE
    SYNTAX          DisplayString (SIZE(0..255))
    MAX-ACCESS      read-only
    STATUS          current
    DESCRIPTION     
            "A condensed textual representation of the virtual node object."
    ::= { ptMTPVNodeEntry 1 }

ptMTPVNodeVPC OBJECT-TYPE
    SYNTAX          Integer32 (-2147483648..2147483647)
    MAX-ACCESS      read-only
    STATUS          current
    DESCRIPTION     
            "The SS7 point code of this virtual node in the format Network.Cluster.Member. Maximum value is 255.255.255. If the personality is ITU, the format is Zone.Area.Member and the range for Zone and Member is 0 to 7, Area is 0 to 255. "
    ::= { ptMTPVNodeEntry 2 }

ptMTPVNodeCLLI OBJECT-TYPE
    SYNTAX          DisplayString (SIZE(0..255))
    MAX-ACCESS      read-create
    STATUS          current
    DESCRIPTION     
            "Common Language Location Identifier (CLLI) of this virtual node. This is an informational attribute only."
    ::= { ptMTPVNodeEntry 3 }

ptMTPVNodeDescription OBJECT-TYPE
    SYNTAX          DisplayString (SIZE(0..255))
    MAX-ACCESS      read-create
    STATUS          current
    DESCRIPTION     
            "A textual description of this virtual node. This attribute is for Operator informational purposes only."
    ::= { ptMTPVNodeEntry 4 }

ptMTPVNodeState OBJECT-TYPE
    SYNTAX          INTEGER { inactive(0), active(1) }
    MAX-ACCESS      read-only
    STATUS          current
    DESCRIPTION     
            "The Virtual Node Status indicates if this VNode is available to be used by a registration to register to. It does NOT indicate whether an application has actually registered to the VNode. That information can be found on the Level 4 connections screen."
    ::= { ptMTPVNodeEntry 5 }

ptMTPVNodeBroadcastTFA OBJECT-TYPE
    SYNTAX          INTEGER { disabled(0), enabled(1) }
    MAX-ACCESS      read-create
    STATUS          current
    DESCRIPTION     
            "Enable or disable the broadcasting of TFA SS7 messages for this virtual node. It is recommended to leave the broadcast as enabled."
    ::= { ptMTPVNodeEntry 6 }

ptMTPVNodeBroadcastTFP OBJECT-TYPE
    SYNTAX          INTEGER { disabled(0), enabled(1) }
    MAX-ACCESS      read-create
    STATUS          current
    DESCRIPTION     
            "Enable or disable the broadcasting of TFP SS7 messages for this virtual node. It is recommended to leave the broadcast as enabled."
    ::= { ptMTPVNodeEntry 7 }

ptMTPVNodeBroadcastTFR OBJECT-TYPE
    SYNTAX          INTEGER { disabled(0), enabled(1) }
    MAX-ACCESS      read-create
    STATUS          current
    DESCRIPTION     
            "Enable or disable the broadcasting of TFR SS7 messages for this virtual node. It is recommended to leave the broadcast as enabled."
    ::= { ptMTPVNodeEntry 8 }

ptMTPVNodeMateSTPDistribution OBJECT-TYPE
    SYNTAX          INTEGER { disabled(0), enabled(1) }
    MAX-ACCESS      read-create
    STATUS          current
    DESCRIPTION     
            "Enable or disable the mate STP distribution of the virtual node. This feature is set to ENABLED by default.\n It is modifiable only if the L4Converter is licensed and is set to DISABLED to allow SCCP Relay support. The L4 application is not distributed over the mate STP and thus incoming message must use the C-Link instead of sending the message back up to the application."
    ::= { ptMTPVNodeEntry 9 }

ptMTPVNodeMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPVNodeEntry 242 }

ptMTPVNodeMTP3NAIndex OBJECT-TYPE
    SYNTAX          Integer32 (-2147483648..2147483647)
    MAX-ACCESS      not-accessible
    STATUS          current
    DESCRIPTION     
            "This is the index of the parent type for this object.
             This parent type is MTP3NA."
    ::= { ptMTPVNodeEntry 243 }

ptMTPVNodeVNodesIndex OBJECT-TYPE
    SYNTAX          Integer32 (-2147483648..2147483647)
    MAX-ACCESS      not-accessible
    STATUS          current
    DESCRIPTION     
            "This is the index of the parent type for this object.
             This parent type is VNodes."
    ::= { ptMTPVNodeEntry 244 }

ptMTPVNodeActions OBJECT-TYPE
    SYNTAX          INTEGER { activate(1), deactivate(2) }
    MAX-ACCESS      read-create
    STATUS          current
    DESCRIPTION     
            "The OID of all possible actions for this instance"
    ::= { ptMTPVNodeEntry 252 }

ptMTPVNodeParentOID OBJECT-TYPE
    SYNTAX          OBJECT IDENTIFIER
    MAX-ACCESS      read-create
    STATUS          current
    DESCRIPTION     
            "The OID of the parent object for this instance"
    ::= { ptMTPVNodeEntry 253 }

ptMTPVNodeRowStatus OBJECT-TYPE
    SYNTAX          RowStatus
    MAX-ACCESS      read-create
    STATUS          current
    DESCRIPTION     
            "The row status for the MTPVNode table"
    ::= { ptMTPVNodeEntry 254 }

ptMTPVNodeIndex OBJECT-TYPE
    SYNTAX          Integer32 (-2147483648..2147483647)
    MAX-ACCESS      not-accessible
    STATUS          current
    DESCRIPTION     
            "The row number for the MTPVNode table"
    ::= { ptMTPVNodeEntry 255 }

ptMTPRoutesetList OBJECT IDENTIFIER
    ::= { ptMTPMTP3NA 63 }

ptMTPRoutesetListTable OBJECT-TYPE
    SYNTAX          SEQUENCE OF PtMTPRoutesetListEntry
    MAX-ACCESS      not-accessible
    STATUS          current
    DESCRIPTION     
            "No description supplied in the proxy config file."
    ::= { ptMTPRoutesetList 1 }

ptMTPRoutesetListEntry OBJECT-TYPE
    SYNTAX          PtMTPRoutesetListEntry
    MAX-ACCESS      not-accessible
    STATUS          current
    DESCRIPTION     
            "A sequence of MTPRoutesetList attributes."
    INDEX           { ptConnGroupIndex, 
                      ptMTPRoutesetListMTP3NAManagerIndex, 
                      ptMTPRoutesetListMTP3NAIndex, 
                      ptMTPRoutesetListIndex }
    ::= { ptMTPRoutesetListTable 1 }

PtMTPRoutesetListEntry ::=
    SEQUENCE {
        ptMTPRoutesetListCount          Integer32,
        ptMTPRoutesetListName           DisplayString,
        ptMTPRoutesetListIdentifier     Integer32,
        ptMTPRoutesetListMTP3NAManagerIndex   Integer32,
        ptMTPRoutesetListMTP3NAIndex    Integer32,
        ptMTPRoutesetListParentOID      OBJECT IDENTIFIER,
        ptMTPRoutesetListRowStatus      RowStatus,
        ptMTPRoutesetListIndex          Integer32
    }

ptMTPRoutesetListCount OBJECT-TYPE
    SYNTAX          Integer32 (-2147483648..2147483647)
    MAX-ACCESS      read-only
    STATUS          current
    DESCRIPTION     
            "Number of Routeset Lists"
    ::= { ptMTPRoutesetListEntry 1 }

ptMTPRoutesetListName OBJECT-TYPE
    SYNTAX          DisplayString (SIZE(0..255))
    MAX-ACCESS      read-only
    STATUS          current
    DESCRIPTION     
            "The name of the Routeset List. This name is used to reference the Routeset List from a linkset. It must be unique among the Routeset Lists within the NA. It must consist of at most eight alphanumeric characters. Alphabetic characters must be uppercase."
    ::= { ptMTPRoutesetListEntry 2 }

ptMTPRoutesetListIdentifier OBJECT-TYPE
    SYNTAX          Integer32 (-2147483648..2147483647)
    MAX-ACCESS      read-only
    STATUS          current
    DESCRIPTION     
            "Routeset List Identifier. Internal use only."
    ::= { ptMTPRoutesetListEntry 3 }

ptMTPRoutesetListMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPRoutesetListEntry 242 }

ptMTPRoutesetListMTP3NAIndex OBJECT-TYPE
    SYNTAX          Integer32 (-2147483648..2147483647)
    MAX-ACCESS      not-accessible
    STATUS          current
    DESCRIPTION     
            "This is the index of the parent type for this object.
             This parent type is MTP3NA."
    ::= { ptMTPRoutesetListEntry 243 }

ptMTPRoutesetListParentOID OBJECT-TYPE
    SYNTAX          OBJECT IDENTIFIER
    MAX-ACCESS      read-create
    STATUS          current
    DESCRIPTION     
            "The OID of the parent object for this instance"
    ::= { ptMTPRoutesetListEntry 253 }

ptMTPRoutesetListRowStatus OBJECT-TYPE
    SYNTAX          RowStatus
    MAX-ACCESS      read-create
    STATUS          current
    DESCRIPTION     
            "The row status for the MTPRoutesetList table"
    ::= { ptMTPRoutesetListEntry 254 }

ptMTPRoutesetListIndex OBJECT-TYPE
    SYNTAX          Integer32 (-2147483648..2147483647)
    MAX-ACCESS      not-accessible
    STATUS          current
    DESCRIPTION     
            "The row number for the MTPRoutesetList table"
    ::= { ptMTPRoutesetListEntry 255 }

ptMTPRouteset OBJECT IDENTIFIER
    ::= { ptMTPRoutesetList 51 }

ptMTPRoutesetTable OBJECT-TYPE
    SYNTAX          SEQUENCE OF PtMTPRoutesetEntry
    MAX-ACCESS      not-accessible
    STATUS          current
    DESCRIPTION     
            "A sequence of Routeset attributes."
    ::= { ptMTPRouteset 1 }

ptMTPRoutesetEntry OBJECT-TYPE
    SYNTAX          PtMTPRoutesetEntry
    MAX-ACCESS      not-accessible
    STATUS          current
    DESCRIPTION     
            "A sequence of MTPRouteset attributes."
    INDEX           { ptConnGroupIndex, ptMTPRoutesetMTP3NAManagerIndex, 
                      ptMTPRoutesetMTP3NAIndex, 
                      ptMTPRoutesetRoutesetListIndex, ptMTPRoutesetIndex }
    ::= { ptMTPRoutesetTable 1 }

PtMTPRoutesetEntry ::=
    SEQUENCE {
        ptMTPRoutesetContext            DisplayString,
        ptMTPRoutesetDPC                Integer32,
        ptMTPRoutesetDestinationType    INTEGER,
        ptMTPRoutesetCLLI               DisplayString,
        ptMTPRoutesetRoutesetState      INTEGER,
        ptMTPRoutesetCongestionLevel    INTEGER,
        ptMTPRoutesetDestinationState   INTEGER,
        ptMTPRoutesetBroadcastTCA       INTEGER,
        ptMTPRoutesetBroadcastTCP       INTEGER,
        ptMTPRoutesetBroadcastTCR       INTEGER,
        ptMTPRoutesetBroadcastTFA       INTEGER,
        ptMTPRoutesetBroadcastTFP       INTEGER,
        ptMTPRoutesetBroadcastTFR       INTEGER,
        ptMTPRoutesetCongestionNotifOfUPs Integer32,
        ptMTPRoutesetAllowXRoutesets    INTEGER,
        ptMTPRoutesetTestState          INTEGER,
        ptMTPRoutesetRoutesetID         INTEGER,
        ptMTPRoutesetLoadshareMode      INTEGER,
        ptMTPRoutesetAlarms             INTEGER,
        ptMTPRoutesetMTP3NAManagerIndex Integer32,
        ptMTPRoutesetMTP3NAIndex        Integer32,
        ptMTPRoutesetRoutesetListIndex  Integer32,
        ptMTPRoutesetActions            INTEGER,
        ptMTPRoutesetParentOID          OBJECT IDENTIFIER,
        ptMTPRoutesetRowStatus          RowStatus,
        ptMTPRoutesetIndex              Integer32
    }

ptMTPRoutesetContext OBJECT-TYPE
    SYNTAX          DisplayString (SIZE(0..255))
    MAX-ACCESS      read-only
    STATUS          current
    DESCRIPTION     
            "A condensed textual representation of the routeset object."
    ::= { ptMTPRoutesetEntry 1 }

ptMTPRoutesetDPC OBJECT-TYPE
    SYNTAX          Integer32 (-2147483648..2147483647)
    MAX-ACCESS      read-only
    STATUS          current
    DESCRIPTION     
            "Destination SS7 point code of this routeset This value should be set a creation time of the routeset and cannot be modified thereafter. The point code of the routeset gives the destination that one is seeking. The routes within the routeset will indicate the adjacent point codes that can be used to the get to the destination."
    ::= { ptMTPRoutesetEntry 2 }

ptMTPRoutesetDestinationType OBJECT-TYPE
    SYNTAX          INTEGER { default(1), network(2), cluster(3), 
                        member(4) }
    MAX-ACCESS      read-only
    STATUS          current
    DESCRIPTION     
            "Describes the destination type of the routeset (network, cluster, member, or default)."
    ::= { ptMTPRoutesetEntry 3 }

ptMTPRoutesetCLLI OBJECT-TYPE
    SYNTAX          DisplayString (SIZE(0..255))
    MAX-ACCESS      read-create
    STATUS          current
    DESCRIPTION     
            "Common Language Location Identifier (CLLI) of this routeset."
    ::= { ptMTPRoutesetEntry 4 }

ptMTPRoutesetRoutesetState OBJECT-TYPE
    SYNTAX          INTEGER { active(0), inactive(1), xlist(2) }
    MAX-ACCESS      read-only
    STATUS          current
    DESCRIPTION     
            "Status of this routeset (active, inactive, xlist) xlist means that the routeset was dynamically created by the MTP L3 and has exceptions, such as some routes may not be available."
    ::= { ptMTPRoutesetEntry 5 }

ptMTPRoutesetCongestionLevel OBJECT-TYPE
    SYNTAX          INTEGER { false(0), level1(1), level2(2), level3(3), 
                        true(4) }
    MAX-ACCESS      read-only
    STATUS          current
    DESCRIPTION     
            "Congestion level of the routeset. \nIn ANSI, TTC and NTT networks the values range from 1 to 3 or FALSE if not congested. \nIn ITU networks the values are TRUE or FALSE."
    ::= { ptMTPRoutesetEntry 6 }

ptMTPRoutesetDestinationState OBJECT-TYPE
    SYNTAX          INTEGER { inaccessible(0), accessible(1), 
                        accessibleAlt(2), manuallyBlocked(3) }
    MAX-ACCESS      read-only
    STATUS          current
    DESCRIPTION     
            "Status of the routeset destination. The possible states are, inaccessible, accessible, manually blocked, accessible via alternate route. When a routeset is deactivated the routeset destination state is set to manually blocked and the routeset state is set to inactive whether the destination state is accessible or inaccessible."
    ::= { ptMTPRoutesetEntry 7 }

ptMTPRoutesetBroadcastTCA OBJECT-TYPE
    SYNTAX          INTEGER { disabled(0), enabled(1) }
    MAX-ACCESS      read-create
    STATUS          current
    DESCRIPTION     
            "Enable or disable the broadcasting of TCA SS7 messages for this routeset"
    ::= { ptMTPRoutesetEntry 8 }

ptMTPRoutesetBroadcastTCP OBJECT-TYPE
    SYNTAX          INTEGER { disabled(0), enabled(1) }
    MAX-ACCESS      read-create
    STATUS          current
    DESCRIPTION     
            "Enable or disable the broadcasting of TCP SS7 messages for this routeset"
    ::= { ptMTPRoutesetEntry 9 }

ptMTPRoutesetBroadcastTCR OBJECT-TYPE
    SYNTAX          INTEGER { disabled(0), enabled(1) }
    MAX-ACCESS      read-create
    STATUS          current
    DESCRIPTION     
            "Enable or disable the broadcasting of TCR SS7 messages for this routeset."
    ::= { ptMTPRoutesetEntry 10 }

ptMTPRoutesetBroadcastTFA OBJECT-TYPE
    SYNTAX          INTEGER { disabled(0), enabled(1) }
    MAX-ACCESS      read-create
    STATUS          current
    DESCRIPTION     
            "Enable or disable the broadcasting of TFA SS7 messages for this routeset."
    ::= { ptMTPRoutesetEntry 11 }

ptMTPRoutesetBroadcastTFP OBJECT-TYPE
    SYNTAX          INTEGER { disabled(0), enabled(1) }
    MAX-ACCESS      read-create
    STATUS          current
    DESCRIPTION     
            "Enable or disable the broadcasting of TFP SS7 messages for this routeset."
    ::= { ptMTPRoutesetEntry 12 }

ptMTPRoutesetBroadcastTFR OBJECT-TYPE
    SYNTAX          INTEGER { disabled(0), enabled(1) }
    MAX-ACCESS      read-create
    STATUS          current
    DESCRIPTION     
            "Enable or disable the broadcasting of TFR SS7 messages for this routeset."
    ::= { ptMTPRoutesetEntry 13 }

ptMTPRoutesetCongestionNotifOfUPs OBJECT-TYPE
    SYNTAX          Integer32 (0..2147483647)
    MAX-ACCESS      read-create
    STATUS          current
    DESCRIPTION     
            "Number of messages between congestion notification of User Part (Default 8). Use of this value limits a flood of congestion notices to a connected application."
    ::= { ptMTPRoutesetEntry 16 }

ptMTPRoutesetAllowXRoutesets OBJECT-TYPE
    SYNTAX          INTEGER { disabled(0), enabled(1) }
    MAX-ACCESS      read-create
    STATUS          current
    DESCRIPTION     
            "Enable or disable the creation of X-List routesets"
    ::= { ptMTPRoutesetEntry 17 }

ptMTPRoutesetTestState OBJECT-TYPE
    SYNTAX          INTEGER { idle(0), waitTry1(1), waitTry2(2), 
                        failed(3), success(4) }
    MAX-ACCESS      read-only
    STATUS          current
    DESCRIPTION     
            "Signaling Test State is a value used only Japanese and New Zealand networks. "
    ::= { ptMTPRoutesetEntry 18 }

ptMTPRoutesetRoutesetID OBJECT-TYPE
    SYNTAX          INTEGER { pending(65534), undefined(65535) }
    MAX-ACCESS      read-create
    STATUS          current
    DESCRIPTION     
            "PT_C20 Application ID Mgmt Routeset unique identifier. \nValid values: 0 to 4000, PENDING, and UNDEFINED. \nBy default, the attribute is set to UNDEFINED. The PENDING value is a transient value only and cannot be set by the user. \nThe attribute can only be modified if the Application ID Mgmt attribute is set to PT_C20. If defined, attribute value must be unique across all NAs. \nThe attribute, if defined, must be reset to UNDEFINED to permit the deletion of the routeset object."
    ::= { ptMTPRoutesetEntry 19 }

ptMTPRoutesetLoadshareMode OBJECT-TYPE
    SYNTAX          INTEGER { nodeValue(0), sls(1), sccp0(2), 
                        enhancedSls(3), enhancedSlsAndSccp0(4), 
                        ttcAbPlane(5) }
    MAX-ACCESS      read-create
    STATUS          current
    DESCRIPTION     
            "Loadshare mode affects the algorithm that determines which MSUs are routed on which links (the loadsharing algorithm). When set to 'NODE_VALUE', the load sharing algorithm will be based upon the Loadshare Mode value in the network appearance. The default value is NODE_VALUE. When set to 'SLS', the usual loadsharing algorithm is used, based on the SLS in the incoming MSU. This algorithm is usually satisfactory, but may have drawbacks in some SS7 variants and network configurations in which the range of meaningful SLS values may be limited. Also, MSUs such as SCCP messages with Protocol Class 0 do not have sequencing requirements. When set to 'SCCP0', SCCP messages that do not require sequencing are loadshared evenly between links without regard to the incoming SLS and the outgoing SLS is modified. Other MSUs are loadshared in the usual way using the MSU SLS. When set to 'ENHANCED SLS', a new SLS value is generated based on incoming information such as OPC, DPC and link SLC. When set to 'ENHANCED SLS AND SCCP0', the option will process Protocol class 0 messages first and use the same functionality at SCCP0, plus remaining messages are processed using the same functionality as the ENHANCED SLS option. Applies to SI > 2 messages only. When set to 'TTC AB PLANE' the A/B Plane Bit is used to select the outgoing linkset. This attribute only takes effect if a routeset is using a combined linkset (two routes with equal cost), and if one linkset is configured as a A-plane linkset (using the Linkset 'AB Plane Bit' attribute) and the other linkset is configured as a B-plane linkset. In this case, the A/B Plane Bit in the MSU SLS is used to select the outgoing linkset when sufficient links are available. In some cases there is a trade-off between evenly distributing traffic across available links and respecting the A/B bit for linkset selection. These cases are handled as follows. \n* If each linkset has half or more its links available, the AB Plane Bit is used to select the outgoing linkset and the other SLS bits are used to select the link within the linkset. \n* If one of the linksets has less than half its links available (''abnormal'' or ''quasi-normal'') but the other linkset has half or more its links available (''normal'' or ''fully normal''), then only one linkset is used for traffic: the linkset with half or more of its links available. \n* If each linkset has less than half its links available, priority is given to making the traffic on each link as even as possible, while respecting the AB Plane Bit when this doesn't further unbalance traffic."
    ::= { ptMTPRoutesetEntry 20 }

ptMTPRoutesetAlarms OBJECT-TYPE
    SYNTAX          INTEGER { disabled(0), enabled(1) }
    MAX-ACCESS      read-create
    STATUS          current
    DESCRIPTION     
            "Alarms affect the alarms associated with the Routeset. DISABLED mode: Alarms will not be raised. ENABLED mode: Alarms will be raised. \nValid values: ENABLED and DISABLED. \nDefault value: ENABLED."
    ::= { ptMTPRoutesetEntry 47 }

ptMTPRoutesetMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPRoutesetEntry 242 }

ptMTPRoutesetMTP3NAIndex OBJECT-TYPE
    SYNTAX          Integer32 (-2147483648..2147483647)
    MAX-ACCESS      not-accessible
    STATUS          current
    DESCRIPTION     
            "This is the index of the parent type for this object.
             This parent type is MTP3NA."
    ::= { ptMTPRoutesetEntry 243 }

ptMTPRoutesetRoutesetListIndex OBJECT-TYPE
    SYNTAX          Integer32 (-2147483648..2147483647)
    MAX-ACCESS      not-accessible
    STATUS          current
    DESCRIPTION     
            "This is the index of the parent type for this object.
             This parent type is RoutesetList."
    ::= { ptMTPRoutesetEntry 244 }

ptMTPRoutesetActions OBJECT-TYPE
    SYNTAX          INTEGER { activate(1), deactivate(2), test(3), 
                        dumpSLSTable(4), cRDT(5) }
    MAX-ACCESS      read-create
    STATUS          current
    DESCRIPTION     
            "The OID of all possible actions for this instance"
    ::= { ptMTPRoutesetEntry 252 }

ptMTPRoutesetParentOID OBJECT-TYPE
    SYNTAX          OBJECT IDENTIFIER
    MAX-ACCESS      read-create
    STATUS          current
    DESCRIPTION     
            "The OID of the parent object for this instance"
    ::= { ptMTPRoutesetEntry 253 }

ptMTPRoutesetRowStatus OBJECT-TYPE
    SYNTAX          RowStatus
    MAX-ACCESS      read-create
    STATUS          current
    DESCRIPTION     
            "The row status for the MTPRouteset table"
    ::= { ptMTPRoutesetEntry 254 }

ptMTPRoutesetIndex OBJECT-TYPE
    SYNTAX          Integer32 (-2147483648..2147483647)
    MAX-ACCESS      not-accessible
    STATUS          current
    DESCRIPTION     
            "The row number for the MTPRouteset table"
    ::= { ptMTPRoutesetEntry 255 }

ptMTPRoute OBJECT IDENTIFIER
    ::= { ptMTPRouteset 52 }

ptMTPRouteTable OBJECT-TYPE
    SYNTAX          SEQUENCE OF PtMTPRouteEntry
    MAX-ACCESS      not-accessible
    STATUS          current
    DESCRIPTION     
            "A sequence of Route attributes."
    ::= { ptMTPRoute 1 }

ptMTPRouteEntry OBJECT-TYPE
    SYNTAX          PtMTPRouteEntry
    MAX-ACCESS      not-accessible
    STATUS          current
    DESCRIPTION     
            "A sequence of MTPRoute attributes."
    INDEX           { ptConnGroupIndex, ptMTPRouteMTP3NAManagerIndex, 
                      ptMTPRouteMTP3NAIndex, ptMTPRouteRoutesetListIndex, 
                      ptMTPRouteRoutesetIndex, ptMTPRouteIndex }
    ::= { ptMTPRouteTable 1 }

PtMTPRouteEntry ::=
    SEQUENCE {
        ptMTPRouteContext               DisplayString,
        ptMTPRouteAPC                   Integer32,
        ptMTPRouteCost                  Integer32,
        ptMTPRouteCLLI                  DisplayString,
        ptMTPRouteState                 INTEGER,
        ptMTPRouteLinksetName           DisplayString,
        ptMTPRouteMTP3NAManagerIndex    Integer32,
        ptMTPRouteMTP3NAIndex           Integer32,
        ptMTPRouteRoutesetListIndex     Integer32,
        ptMTPRouteRoutesetIndex         Integer32,
        ptMTPRouteActions               INTEGER,
        ptMTPRouteParentOID             OBJECT IDENTIFIER,
        ptMTPRouteRowStatus             RowStatus,
        ptMTPRouteIndex                 Integer32
    }

ptMTPRouteContext OBJECT-TYPE
    SYNTAX          DisplayString (SIZE(0..255))
    MAX-ACCESS      read-only
    STATUS          current
    DESCRIPTION     
            "A condensed textual representation of the route object."
    ::= { ptMTPRouteEntry 1 }

ptMTPRouteAPC OBJECT-TYPE
    SYNTAX          Integer32 (-2147483648..2147483647)
    MAX-ACCESS      read-only
    STATUS          current
    DESCRIPTION     
            "Adjacent SS7 point code of this route."
    ::= { ptMTPRouteEntry 2 }

ptMTPRouteCost OBJECT-TYPE
    SYNTAX          Integer32 (0..100)
    MAX-ACCESS      read-create
    STATUS          current
    DESCRIPTION     
            "Cost of this route"
    ::= { ptMTPRouteEntry 3 }

ptMTPRouteCLLI OBJECT-TYPE
    SYNTAX          DisplayString (SIZE(0..255))
    MAX-ACCESS      read-only
    STATUS          current
    DESCRIPTION     
            "Common Language Location Identifier (CLLI) of the associated linkset."
    ::= { ptMTPRouteEntry 4 }

ptMTPRouteState OBJECT-TYPE
    SYNTAX          INTEGER { unavailable(0), available(1), 
                        prohibited(2), restricted(3), prohibitedCrdt(4) }
    MAX-ACCESS      read-only
    STATUS          current
    DESCRIPTION     
            "Status of this route (unavailable, available, prohibited, restricted or prohibited_crdt). PROHIBITED_CRDT applies only in ANSI and indicates that the route failed the ANSI Circular Route Detection Test (CRDT). The route remains unavailable until it is reset by maintenance personnel using the Reset State action."
    ::= { ptMTPRouteEntry 5 }

ptMTPRouteLinksetName OBJECT-TYPE
    SYNTAX          DisplayString (SIZE(0..255))
    MAX-ACCESS      read-only
    STATUS          current
    DESCRIPTION     
            "Linkset Name of this route."
    ::= { ptMTPRouteEntry 6 }

ptMTPRouteMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPRouteEntry 242 }

ptMTPRouteMTP3NAIndex OBJECT-TYPE
    SYNTAX          Integer32 (-2147483648..2147483647)
    MAX-ACCESS      not-accessible
    STATUS          current
    DESCRIPTION     
            "This is the index of the parent type for this object.
             This parent type is MTP3NA."
    ::= { ptMTPRouteEntry 243 }

ptMTPRouteRoutesetListIndex OBJECT-TYPE
    SYNTAX          Integer32 (-2147483648..2147483647)
    MAX-ACCESS      not-accessible
    STATUS          current
    DESCRIPTION     
            "This is the index of the parent type for this object.
             This parent type is RoutesetList."
    ::= { ptMTPRouteEntry 244 }

ptMTPRouteRoutesetIndex OBJECT-TYPE
    SYNTAX          Integer32 (-2147483648..2147483647)
    MAX-ACCESS      not-accessible
    STATUS          current
    DESCRIPTION     
            "This is the index of the parent type for this object.
             This parent type is Routeset."
    ::= { ptMTPRouteEntry 245 }

ptMTPRouteActions OBJECT-TYPE
    SYNTAX          INTEGER { resetState(1) }
    MAX-ACCESS      read-create
    STATUS          current
    DESCRIPTION     
            "The OID of all possible actions for this instance"
    ::= { ptMTPRouteEntry 252 }

ptMTPRouteParentOID OBJECT-TYPE
    SYNTAX          OBJECT IDENTIFIER
    MAX-ACCESS      read-create
    STATUS          current
    DESCRIPTION     
            "The OID of the parent object for this instance"
    ::= { ptMTPRouteEntry 253 }

ptMTPRouteRowStatus OBJECT-TYPE
    SYNTAX          RowStatus
    MAX-ACCESS      read-create
    STATUS          current
    DESCRIPTION     
            "The row status for the MTPRoute table"
    ::= { ptMTPRouteEntry 254 }

ptMTPRouteIndex OBJECT-TYPE
    SYNTAX          Integer32 (-2147483648..2147483647)
    MAX-ACCESS      not-accessible
    STATUS          current
    DESCRIPTION     
            "The row number for the MTPRoute table"
    ::= { ptMTPRouteEntry 255 }

ptMTPLinksets OBJECT IDENTIFIER
    ::= { ptMTPMTP3NA 64 }

ptMTPLinksetsTable OBJECT-TYPE
    SYNTAX          SEQUENCE OF PtMTPLinksetsEntry
    MAX-ACCESS      not-accessible
    STATUS          current
    DESCRIPTION     
            "No description supplied in the proxy config file."
    ::= { ptMTPLinksets 1 }

ptMTPLinksetsEntry OBJECT-TYPE
    SYNTAX          PtMTPLinksetsEntry
    MAX-ACCESS      not-accessible
    STATUS          current
    DESCRIPTION     
            "A sequence of MTPLinksets attributes."
    INDEX           { ptConnGroupIndex, ptMTPLinksetsMTP3NAManagerIndex, 
                      ptMTPLinksetsMTP3NAIndex, ptMTPLinksetsIndex }
    ::= { ptMTPLinksetsTable 1 }

PtMTPLinksetsEntry ::=
    SEQUENCE {
        ptMTPLinksetsCount              Integer32,
        ptMTPLinksetsMTP3NAManagerIndex Integer32,
        ptMTPLinksetsMTP3NAIndex        Integer32,
        ptMTPLinksetsActions            INTEGER,
        ptMTPLinksetsParentOID          OBJECT IDENTIFIER,
        ptMTPLinksetsRowStatus          RowStatus,
        ptMTPLinksetsIndex              Integer32
    }

ptMTPLinksetsCount OBJECT-TYPE
    SYNTAX          Integer32 (-2147483648..2147483647)
    MAX-ACCESS      read-only
    STATUS          current
    DESCRIPTION     
            "Number of Linksets"
    ::= { ptMTPLinksetsEntry 1 }

ptMTPLinksetsMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPLinksetsEntry 242 }

ptMTPLinksetsMTP3NAIndex OBJECT-TYPE
    SYNTAX          Integer32 (-2147483648..2147483647)
    MAX-ACCESS      not-accessible
    STATUS          current
    DESCRIPTION     
            "This is the index of the parent type for this object.
             This parent type is MTP3NA."
    ::= { ptMTPLinksetsEntry 243 }

ptMTPLinksetsActions OBJECT-TYPE
    SYNTAX          INTEGER { resetIMF(1) }
    MAX-ACCESS      read-create
    STATUS          current
    DESCRIPTION     
            "The OID of all possible actions for this instance"
    ::= { ptMTPLinksetsEntry 252 }

ptMTPLinksetsParentOID OBJECT-TYPE
    SYNTAX          OBJECT IDENTIFIER
    MAX-ACCESS      read-create
    STATUS          current
    DESCRIPTION     
            "The OID of the parent object for this instance"
    ::= { ptMTPLinksetsEntry 253 }

ptMTPLinksetsRowStatus OBJECT-TYPE
    SYNTAX          RowStatus
    MAX-ACCESS      read-create
    STATUS          current
    DESCRIPTION     
            "The row status for the MTPLinksets table"
    ::= { ptMTPLinksetsEntry 254 }

ptMTPLinksetsIndex OBJECT-TYPE
    SYNTAX          Integer32 (-2147483648..2147483647)
    MAX-ACCESS      not-accessible
    STATUS          current
    DESCRIPTION     
            "The row number for the MTPLinksets table"
    ::= { ptMTPLinksetsEntry 255 }

ptMTPLinkset OBJECT IDENTIFIER
    ::= { ptMTPLinksets 53 }

ptMTPLinksetTable OBJECT-TYPE
    SYNTAX          SEQUENCE OF PtMTPLinksetEntry
    MAX-ACCESS      not-accessible
    STATUS          current
    DESCRIPTION     
            "A sequence of Linkset attributes."
    ::= { ptMTPLinkset 1 }

ptMTPLinksetEntry OBJECT-TYPE
    SYNTAX          PtMTPLinksetEntry
    MAX-ACCESS      not-accessible
    STATUS          current
    DESCRIPTION     
            "A sequence of MTPLinkset attributes."
    INDEX           { ptConnGroupIndex, ptMTPLinksetMTP3NAManagerIndex, 
                      ptMTPLinksetMTP3NAIndex, ptMTPLinksetLinksetsIndex, 
                      ptMTPLinksetIndex }
    ::= { ptMTPLinksetTable 1 }

PtMTPLinksetEntry ::=
    SEQUENCE {
        ptMTPLinksetContext             DisplayString,
        ptMTPLinksetAPC                 Integer32,
        ptMTPLinksetLinkType            INTEGER,
        ptMTPLinksetCLLI                DisplayString,
        ptMTPLinksetState               INTEGER,
        ptMTPLinksetUserActivated       INTEGER,
        ptMTPLinksetRotateSLS           INTEGER,
        ptMTPLinksetBroadcastTCA        INTEGER,
        ptMTPLinksetBroadcastTCP        INTEGER,
        ptMTPLinksetBroadcastTCR        INTEGER,
        ptMTPLinksetBroadcastTFA        INTEGER,
        ptMTPLinksetBroadcastTFP        INTEGER,
        ptMTPLinksetBroadcastTFR        INTEGER,
        ptMTPLinksetRepeatSLT           INTEGER,
        ptMTPLinksetRemoteMTPRestartSupport   INTEGER,
        ptMTPLinksetL2T1                INTEGER,
        ptMTPLinksetL2T2                INTEGER,
        ptMTPLinksetL2T3                INTEGER,
        ptMTPLinksetL2T4e               INTEGER,
        ptMTPLinksetL2T4n               INTEGER,
        ptMTPLinksetL2T5                INTEGER,
        ptMTPLinksetL2T6                INTEGER,
        ptMTPLinksetL2T7                INTEGER,
        ptMTPLinksetSLTMT1              INTEGER,
        ptMTPLinksetSLTMT2              INTEGER,
        ptMTPLinksetTXAbatementL1       Integer32,
        ptMTPLinksetTXOnsetL1           Integer32,
        ptMTPLinksetTXAbatementL2       Integer32,
        ptMTPLinksetTXOnsetL2           Integer32,
        ptMTPLinksetTXAbatementL3       Integer32,
        ptMTPLinksetTXOnsetL3           Integer32,
        ptMTPLinksetErrorCorrectionMode INTEGER,
        ptMTPLinksetNAERM               Integer32,
        ptMTPLinksetEAERM               Integer32,
        ptMTPLinksetSUERM               Integer32,
        ptMTPLinksetMaximumMSUsRTB      Integer32,
        ptMTPLinksetMaximumOctetsRTB    Integer32,
        ptMTPLinksetSLTSI               INTEGER,
        ptMTPLinksetSLTMPattern         DisplayString,
        ptMTPLinksetUsagePercentage     Integer32,
        ptMTPLinksetUsageIntervalMinutes Integer32,
        ptMTPLinksetUsageIntervalSeconds Integer32,
        ptMTPLinksetRoutesetListName    DisplayString,
        ptMTPLinksetIMFSupport          INTEGER,
        ptMTPLinksetAlarms              INTEGER,
        ptMTPLinksetPCMappingTableName  DisplayString,
        ptMTPLinksetRFC4165T1           INTEGER,
        ptMTPLinksetRFC4165T2           INTEGER,
        ptMTPLinksetRFC4165T3           INTEGER,
        ptMTPLinksetRFC4165T4n          INTEGER,
        ptMTPLinksetRFC4165T4e          INTEGER,
        ptMTPLinksetRFC4165T6           INTEGER,
        ptMTPLinksetRFC4165T7           INTEGER,
        ptMTPLinksetRFC4165StatusInterval INTEGER,
        ptMTPLinksetRFC4165ProvingRate  INTEGER,
        ptMTPLinksetDraft6T1            INTEGER,
        ptMTPLinksetDraft6T3            INTEGER,
        ptMTPLinksetDraft6T4n           INTEGER,
        ptMTPLinksetDraft6T4e           INTEGER,
        ptMTPLinksetDraft6T6            INTEGER,
        ptMTPLinksetDraft6T7            INTEGER,
        ptMTPLinksetDraft6StatusInterval INTEGER,
        ptMTPLinksetDraft6ProvingRate   INTEGER,
        ptMTPLinksetDraft6AcknowledgementInterval         INTEGER,
        ptMTPLinksetRFC4165AcknowledgementInterval          INTEGER,
        ptMTPLinksetM2PARXAbatementBusy Integer32,
        ptMTPLinksetM2PARXOnsetBusy     Integer32,
        ptMTPLinksetM2PATXQueueSize     Integer32,
        ptMTPLinksetM2PARTBSize         Integer32,
        ptMTPLinksetHeartbeat           INTEGER,
        ptMTPLinksetHeartbeatInterval   Integer32,
        ptMTPLinksetRTOInitial          Integer32,
        ptMTPLinksetRTOMinimum          Integer32,
        ptMTPLinksetRTOMaximum          Integer32,
        ptMTPLinksetMaximumPathRetrans  Integer32,
        ptMTPLinksetMaximumAssocRetrans Integer32,
        ptMTPLinksetBundling            INTEGER,
        ptMTPLinksetBundlingTO          Integer32,
        ptMTPLinksetDelayedACKTO        Integer32,
        ptMTPLinksetFastRetransThreshold Integer32,
        ptMTPLinksetChecksum            INTEGER,
        ptMTPLinksetBytesBeforeAck      Integer32,
        ptMTPLinksetMessagesBeforeAck   Integer32,
        ptMTPLinksetReverseRotateSLS    INTEGER,
        ptMTPLinksetAnnexAT1            INTEGER,
        ptMTPLinksetAnnexAT4n           INTEGER,
        ptMTPLinksetOPCVerification     INTEGER,
        ptMTPLinksetLongMSUSupport      INTEGER,
        ptMTPLinksetLinksetName         DisplayString,
        ptMTPLinksetLongMSUProving      INTEGER,
        ptMTPLinksetSCTPClient          INTEGER,
        ptMTPLinksetM3UAClient          INTEGER,
        ptMTPLinksetM3UAMGSharedPC      INTEGER,
        ptMTPLinksetProvingMessageSize  Integer32,
        ptMTPLinksetNetworkIndicator    INTEGER,
        ptMTPLinksetABPlaneBit          INTEGER,
        ptMTPLinksetL3T1                INTEGER,
        ptMTPLinksetL3T2                INTEGER,
        ptMTPLinksetL3T3                INTEGER,
        ptMTPLinksetL3T4                INTEGER,
        ptMTPLinksetL3T6                INTEGER,
        ptMTPLinksetMTP3NAManagerIndex  Integer32,
        ptMTPLinksetMTP3NAIndex         Integer32,
        ptMTPLinksetLinksetsIndex       Integer32,
        ptMTPLinksetActions             INTEGER,
        ptMTPLinksetParentOID           OBJECT IDENTIFIER,
        ptMTPLinksetRowStatus           RowStatus,
        ptMTPLinksetIndex               Integer32
    }

ptMTPLinksetContext OBJECT-TYPE
    SYNTAX          DisplayString (SIZE(0..255))
    MAX-ACCESS      read-only
    STATUS          current
    DESCRIPTION     
            "A condensed textual representation of the SS7 linkset object."
    ::= { ptMTPLinksetEntry 1 }

ptMTPLinksetAPC OBJECT-TYPE
    SYNTAX          Integer32 (-2147483648..2147483647)
    MAX-ACCESS      read-only
    STATUS          current
    DESCRIPTION     
            "Adjacent SS7 point code of this linkset."
    ::= { ptMTPLinksetEntry 2 }

ptMTPLinksetLinkType OBJECT-TYPE
    SYNTAX          INTEGER { aLink(0), bLink(1), cLink(2), dLink(3), 
                        eLink(4), fLink(5) }
    MAX-ACCESS      read-create
    STATUS          current
    DESCRIPTION     
            "Type of SS7 linkset. (A, B, C, D, E, F). \nChanging the type for the NTT variant to F \nforces the AB Plane Bit to A, and from F forces \nit to SLC_ENCODED, and requires the linkset to \nbe empty."
    ::= { ptMTPLinksetEntry 4 }

ptMTPLinksetCLLI OBJECT-TYPE
    SYNTAX          DisplayString (SIZE(0..255))
    MAX-ACCESS      read-create
    STATUS          current
    DESCRIPTION     
            "Common Language Location Identifier (CLLI) of this linkset."
    ::= { ptMTPLinksetEntry 5 }

ptMTPLinksetState OBJECT-TYPE
    SYNTAX          INTEGER { inactive(0), active(1), failed(2) }
    MAX-ACCESS      read-only
    STATUS          current
    DESCRIPTION     
            "Status of this linkset (inactive, active, failed)"
    ::= { ptMTPLinksetEntry 6 }

ptMTPLinksetUserActivated OBJECT-TYPE
    SYNTAX          INTEGER { disabled(0), enabled(1) }
    MAX-ACCESS      read-only
    STATUS          current
    DESCRIPTION     
            "Attempt to activate when possible"
    ::= { ptMTPLinksetEntry 7 }

ptMTPLinksetRotateSLS OBJECT-TYPE
    SYNTAX          INTEGER { disabled(0), enabled(1) }
    MAX-ACCESS      read-create
    STATUS          current
    DESCRIPTION     
            "Enable or disable SLS rotation of MSUs that are sent on this linkset.\nIf SLS rotation is disabled for the node (via the 'MTP3 NA' 'Rotate SLS' attribute) then this parameter has no effect. SLS Rotation is only applied to MSUs with SI at least 3 (SLS is not rotated for MTP3 management messages)."
    ::= { ptMTPLinksetEntry 8 }

ptMTPLinksetBroadcastTCA OBJECT-TYPE
    SYNTAX          INTEGER { disabled(0), enabled(1) }
    MAX-ACCESS      read-create
    STATUS          current
    DESCRIPTION     
            "Enable or disable the broadcasting of TCA SS7 messages for this linkset"
    ::= { ptMTPLinksetEntry 9 }

ptMTPLinksetBroadcastTCP OBJECT-TYPE
    SYNTAX          INTEGER { disabled(0), enabled(1) }
    MAX-ACCESS      read-create
    STATUS          current
    DESCRIPTION     
            "Enable or disable the broadcasting of TCP SS7 messages for this linkset"
    ::= { ptMTPLinksetEntry 10 }

ptMTPLinksetBroadcastTCR OBJECT-TYPE
    SYNTAX          INTEGER { disabled(0), enabled(1) }
    MAX-ACCESS      read-create
    STATUS          current
    DESCRIPTION     
            "Enable or disable the broadcasting of TCR SS7 messages for this linkset"
    ::= { ptMTPLinksetEntry 11 }

ptMTPLinksetBroadcastTFA OBJECT-TYPE
    SYNTAX          INTEGER { disabled(0), enabled(1) }
    MAX-ACCESS      read-create
    STATUS          current
    DESCRIPTION     
            "Enable or disable the broadcasting of TFA SS7 messages for this linkset"
    ::= { ptMTPLinksetEntry 12 }

ptMTPLinksetBroadcastTFP OBJECT-TYPE
    SYNTAX          INTEGER { disabled(0), enabled(1) }
    MAX-ACCESS      read-create
    STATUS          current
    DESCRIPTION     
            "Enable or disable the broadcasting of TFP SS7 messages for this linkset"
    ::= { ptMTPLinksetEntry 13 }

ptMTPLinksetBroadcastTFR OBJECT-TYPE
    SYNTAX          INTEGER { disabled(0), enabled(1) }
    MAX-ACCESS      read-create
    STATUS          current
    DESCRIPTION     
            "Enable or disable the broadcasting of TFR SS7 messages for this linkset"
    ::= { ptMTPLinksetEntry 14 }

ptMTPLinksetRepeatSLT OBJECT-TYPE
    SYNTAX          INTEGER { disabled(0), enabled(1) }
    MAX-ACCESS      read-create
    STATUS          current
    DESCRIPTION     
            "Enable or disable the repeating of Signaling Link Test Message (SLTM or SRT in Japan) SS7 messages for this linkset."
    ::= { ptMTPLinksetEntry 15 }

ptMTPLinksetRemoteMTPRestartSupport OBJECT-TYPE
    SYNTAX          INTEGER { disabled(0), enabled(1) }
    MAX-ACCESS      read-create
    STATUS          current
    DESCRIPTION     
            "Adjacent node MTP restart support"
    ::= { ptMTPLinksetEntry 16 }

ptMTPLinksetL2T1 OBJECT-TYPE
    SYNTAX          INTEGER { default(-1) }
    MAX-ACCESS      read-create
    STATUS          current
    DESCRIPTION     
            "Aligned/Ready ( 13,000 ms ) [ANSI], ( 4.8 Kbps: 500,000-600,000 ms, 64 Kbps: 40,000-50,000 ms ) [ITU] ( suggested, 15,000 ms ) [JT]"
    ::= { ptMTPLinksetEntry 17 }

ptMTPLinksetL2T2 OBJECT-TYPE
    SYNTAX          INTEGER { default(-1) }
    MAX-ACCESS      read-create
    STATUS          current
    DESCRIPTION     
            "Not Aligned ( 11,500 - 23,000 ms ) [ANSI], ( 5,000 - 150,000 ms) [ITU] ( suggested, 480,000 ms ) [JT]"
    ::= { ptMTPLinksetEntry 18 }

ptMTPLinksetL2T3 OBJECT-TYPE
    SYNTAX          INTEGER { default(-1) }
    MAX-ACCESS      read-create
    STATUS          current
    DESCRIPTION     
            "Aligned ( 11,500 ms ) [ANSI], ( 1,500 ms ) [ITU], ( suggested, 3,000 ms ) [JT]"
    ::= { ptMTPLinksetEntry 19 }

ptMTPLinksetL2T4e OBJECT-TYPE
    SYNTAX          INTEGER { default(-1) }
    MAX-ACCESS      read-create
    STATUS          current
    DESCRIPTION     
            "Proving period ( 2^12 octets, 600 ms ) [ANSI] Proving period ( 2^12 octets, 4.8 Kbps: 6000-8000 ms, 64 Kbps: 400-600 ms ) [ITU] ( suggested, 3,000 ms ) [JT]"
    ::= { ptMTPLinksetEntry 20 }

ptMTPLinksetL2T4n OBJECT-TYPE
    SYNTAX          INTEGER { default(-1) }
    MAX-ACCESS      read-create
    STATUS          current
    DESCRIPTION     
            "Proving period ( 2^14 octets, 2300 ms) [ANSI] ( 2^16 octets, 4.8 Kbps: 100,000-120,000 ms, 64 Kbps: 7500-9500 ms) [ITU] N/A [JT]"
    ::= { ptMTPLinksetEntry 21 }

ptMTPLinksetL2T5 OBJECT-TYPE
    SYNTAX          INTEGER { default(-1) }
    MAX-ACCESS      read-create
    STATUS          current
    DESCRIPTION     
            "Sending SIB ( 80 - 120 ms ) [ANSI/ITU] (suggested, 200 ms ) [JT]"
    ::= { ptMTPLinksetEntry 22 }

ptMTPLinksetL2T6 OBJECT-TYPE
    SYNTAX          INTEGER { default(-1) }
    MAX-ACCESS      read-create
    STATUS          current
    DESCRIPTION     
            "Remote Congestion ( 4.8 Kbps: 8000 - 12000 ms, 64 Kbps: 3000 - 6000 ms ) [ANSI/ITU] ( suggested, 3,000 ms ) [JT]"
    ::= { ptMTPLinksetEntry 23 }

ptMTPLinksetL2T7 OBJECT-TYPE
    SYNTAX          INTEGER { default(-1) }
    MAX-ACCESS      read-create
    STATUS          current
    DESCRIPTION     
            "Excessive delay of ACK ( 4.8 Kbps: 4000 - 6000 ms, 64 Kbps: 500 - 2000 ms ) [ANSI/ITU] ( suggested, 2,000 ms ) [JT]"
    ::= { ptMTPLinksetEntry 24 }

ptMTPLinksetSLTMT1 OBJECT-TYPE
    SYNTAX          INTEGER { default(-1) }
    MAX-ACCESS      read-create
    STATUS          current
    DESCRIPTION     
            "SLTM Timer 1 defines interval (4 - 12 sec) that Signalling Link Test Message (SLTM) [ANSI/ITU] or Signaling Routing Test message (SRT) [TTC/NTT] message must be acknowledged. A value of 0 shuts off the timer and SLTM/SRT signaling."
    ::= { ptMTPLinksetEntry 25 }

ptMTPLinksetSLTMT2 OBJECT-TYPE
    SYNTAX          INTEGER { default(-1) }
    MAX-ACCESS      read-create
    STATUS          current
    DESCRIPTION     
            "SLTM Timer 2 defines interval (30-90 sec) when Signalling Link Test Message (SLTM) [ANSI/ITU] or Signaling Routing Test (SRT) message [TTC/NTT] is periodically repeated. A value of 0 shuts off the timer and SLTM/SRT signaling"
    ::= { ptMTPLinksetEntry 26 }

ptMTPLinksetTXAbatementL1 OBJECT-TYPE
    SYNTAX          Integer32
    MAX-ACCESS      read-create
    STATUS          current
    DESCRIPTION     
            "Congestion Abatement Level 1 (% of buffer usage)"
    ::= { ptMTPLinksetEntry 27 }

ptMTPLinksetTXOnsetL1 OBJECT-TYPE
    SYNTAX          Integer32
    MAX-ACCESS      read-create
    STATUS          current
    DESCRIPTION     
            "Congestion Onset Level 1 (% of buffer usage)"
    ::= { ptMTPLinksetEntry 28 }

ptMTPLinksetTXAbatementL2 OBJECT-TYPE
    SYNTAX          Integer32
    MAX-ACCESS      read-create
    STATUS          current
    DESCRIPTION     
            "Congestion Abatement Level 2 (% of buffer usage)"
    ::= { ptMTPLinksetEntry 29 }

ptMTPLinksetTXOnsetL2 OBJECT-TYPE
    SYNTAX          Integer32
    MAX-ACCESS      read-create
    STATUS          current
    DESCRIPTION     
            "Congestion Onset Level 2 (% of buffer usage)"
    ::= { ptMTPLinksetEntry 30 }

ptMTPLinksetTXAbatementL3 OBJECT-TYPE
    SYNTAX          Integer32
    MAX-ACCESS      read-create
    STATUS          current
    DESCRIPTION     
            "Congestion Abatement Level 3 (% of buffer usage)"
    ::= { ptMTPLinksetEntry 31 }

ptMTPLinksetTXOnsetL3 OBJECT-TYPE
    SYNTAX          Integer32
    MAX-ACCESS      read-create
    STATUS          current
    DESCRIPTION     
            "Congestion Onset Level 3 (% of buffer usage)"
    ::= { ptMTPLinksetEntry 32 }

ptMTPLinksetErrorCorrectionMode OBJECT-TYPE
    SYNTAX          INTEGER { basic(0), pcr(1) }
    MAX-ACCESS      read-create
    STATUS          current
    DESCRIPTION     
            "Error Correction Mode (BASIC, Preventive Cyclic Retransmission (PCR))"
    ::= { ptMTPLinksetEntry 33 }

ptMTPLinksetNAERM OBJECT-TYPE
    SYNTAX          Integer32 (0..2147483647)
    MAX-ACCESS      read-create
    STATUS          current
    DESCRIPTION     
            "Normal Alignment Error Rate Monitor Threshold"
    ::= { ptMTPLinksetEntry 34 }

ptMTPLinksetEAERM OBJECT-TYPE
    SYNTAX          Integer32 (0..2147483647)
    MAX-ACCESS      read-create
    STATUS          current
    DESCRIPTION     
            "Emergency Alignment Error Rate Monitor Threshold"
    ::= { ptMTPLinksetEntry 35 }

ptMTPLinksetSUERM OBJECT-TYPE
    SYNTAX          Integer32 (0..2147483647)
    MAX-ACCESS      read-create
    STATUS          current
    DESCRIPTION     
            "Signal Unit Error Rate Monitor Threshold"
    ::= { ptMTPLinksetEntry 36 }

ptMTPLinksetMaximumMSUsRTB OBJECT-TYPE
    SYNTAX          Integer32 (0..2147483647)
    MAX-ACCESS      read-create
    STATUS          current
    DESCRIPTION     
            "Maximum MSUs in Retransmit Buffer before forced retransmission (PCR only) \nThe default value for this attribute is 127. \nFor Low speed TDM links, values above 127 equate to 127. \nFor High speed TDM links, values above 4095 equate to 4095."
    ::= { ptMTPLinksetEntry 37 }

ptMTPLinksetMaximumOctetsRTB OBJECT-TYPE
    SYNTAX          Integer32 (0..2147483647)
    MAX-ACCESS      read-create
    STATUS          current
    DESCRIPTION     
            "Maximum Octets in Retransmit Buffer before forced retransmission (PCR only)"
    ::= { ptMTPLinksetEntry 38 }

ptMTPLinksetSLTSI OBJECT-TYPE
    SYNTAX          INTEGER { nodeValue(0), ntmRegular(1), ntmSpecial(2) }
    MAX-ACCESS      read-create
    STATUS          current
    DESCRIPTION     
            "The SI used for SLT messages. NODE_VALUE sets the value based on Node Value NTM_REGULAR uses the SI value 1 NTM_SPECIAL uses the SI value 2"
    ::= { ptMTPLinksetEntry 39 }

ptMTPLinksetSLTMPattern OBJECT-TYPE
    SYNTAX          DisplayString (SIZE(0..255))
    MAX-ACCESS      read-create
    STATUS          current
    DESCRIPTION     
            "The Test Pattern Used for SLTM messages (hex format) Enter as a string representing the hex value (for example, AABBCCDD)"
    ::= { ptMTPLinksetEntry 40 }

ptMTPLinksetUsagePercentage OBJECT-TYPE
    SYNTAX          Integer32 (-2147483648..2147483647)
    MAX-ACCESS      read-create
    STATUS          current
    DESCRIPTION     
            "Link usage alarm is triggered when average traffic in percentage exceeds the value entered in this attribute. The average is calculated over period of time defined in Usage Interval Minutes and Usage Interval Seconds"
    ::= { ptMTPLinksetEntry 41 }

ptMTPLinksetUsageIntervalMinutes OBJECT-TYPE
    SYNTAX          Integer32 (-2147483648..2147483647)
    MAX-ACCESS      read-only
    STATUS          current
    DESCRIPTION     
            "Link Usage Interval Minutes defines time interval in minutes used for calculating average traffic load"
    ::= { ptMTPLinksetEntry 42 }

ptMTPLinksetUsageIntervalSeconds OBJECT-TYPE
    SYNTAX          Integer32 (-2147483648..2147483647)
    MAX-ACCESS      read-only
    STATUS          current
    DESCRIPTION     
            "Link Usage Interval Seconds defines time interval in seconds used for calculating average traffic load"
    ::= { ptMTPLinksetEntry 43 }

ptMTPLinksetRoutesetListName OBJECT-TYPE
    SYNTAX          DisplayString (SIZE(0..255))
    MAX-ACCESS      read-create
    STATUS          current
    DESCRIPTION     
            "Name of the Routeset List used to route MSUs received by this linkset. Routeset Lists are represented by Routeset List objects. Changing this value while traffic is running will likely cause MSU missequencing."
    ::= { ptMTPLinksetEntry 44 }

ptMTPLinksetIMFSupport OBJECT-TYPE
    SYNTAX          INTEGER { disabled(0), enabled(1) }
    MAX-ACCESS      read-create
    STATUS          current
    DESCRIPTION     
            "Integrated Monitoring Feed feature support for this linkset. \nIMF must be licensed to enable this attribute. All the linkset IMF Support attributes can be cleared simultaneously by using the Reset IMF action in the Linksets object."
    ::= { ptMTPLinksetEntry 45 }

ptMTPLinksetAlarms OBJECT-TYPE
    SYNTAX          INTEGER { disabled(0), enabled(1) }
    MAX-ACCESS      read-create
    STATUS          current
    DESCRIPTION     
            "Alarms affect the alarms associated with the Linkset. DISABLED mode: Alarms will not be raised. ENABLED mode: Alarms will be raised. \nValid values: ENABLED and DISABLED. \nDefault value: ENABLED."
    ::= { ptMTPLinksetEntry 46 }

ptMTPLinksetPCMappingTableName OBJECT-TYPE
    SYNTAX          DisplayString (SIZE(0..255))
    MAX-ACCESS      read-create
    STATUS          current
    DESCRIPTION     
            "An existing NA PC Mapping table name. (up to 32 characters). \nDefault value: Empty, no mapping is applied."
    ::= { ptMTPLinksetEntry 48 }

ptMTPLinksetRFC4165T1 OBJECT-TYPE
    SYNTAX          INTEGER { default(-1) }
    MAX-ACCESS      read-create
    STATUS          current
    DESCRIPTION     
            "Alignment Ready. References: \n - Q.703 Timer T1 \n - T1.111.3 Timer T1 \n - M2PA RFC 4165 (www.ietf.org) \n - draft-bidulock-sigtran-m2pa-test-06.txt \n The default value is taken from draft-bidulock-sigtran-m2pa-test-06.txt and is consistent with Q.703."
    ::= { ptMTPLinksetEntry 55 }

ptMTPLinksetRFC4165T2 OBJECT-TYPE
    SYNTAX          INTEGER { default(-1) }
    MAX-ACCESS      read-create
    STATUS          current
    DESCRIPTION     
            "Timer Not Aligned. References: \n - Q.703 Timer T2 \n - T1.111.3 Timer T2 \n - M2PA RFC 4165 (www.ietf.org) \n - draft-bidulock-sigtran-m2pa-test-06.txt \n The default value is taken from draft-bidulock-sigtran-m2pa-test-06.txt and is consistent with Q.703."
    ::= { ptMTPLinksetEntry 56 }

ptMTPLinksetRFC4165T3 OBJECT-TYPE
    SYNTAX          INTEGER { default(-1) }
    MAX-ACCESS      read-create
    STATUS          current
    DESCRIPTION     
            "Timer Aligned. References: \n - Q.703 Timer T3 \n - T1.111.3 Timer T3 \n - M2PA RFC 4165 (www.ietf.org) \n - draft-bidulock-sigtran-m2pa-test-06.txt \n The default value is taken from draft-bidulock-sigtran-m2pa-test-06.txt and is consistent with Q.703."
    ::= { ptMTPLinksetEntry 57 }

ptMTPLinksetRFC4165T4n OBJECT-TYPE
    SYNTAX          INTEGER { default(-1) }
    MAX-ACCESS      read-create
    STATUS          current
    DESCRIPTION     
            "Timer Proving Normal. References: \n - Q.703 Timer T4n \n - T1.111.3 Timer T4n \n - M2PA RFC 4165 (www.ietf.org) \n - draft-bidulock-sigtran-m2pa-test-06.txt \n The default value is taken from \n draft-bidulock-sigtran-m2pa-test-06.txt and is consistent with Q.703."
    ::= { ptMTPLinksetEntry 58 }

ptMTPLinksetRFC4165T4e OBJECT-TYPE
    SYNTAX          INTEGER { default(-1) }
    MAX-ACCESS      read-create
    STATUS          current
    DESCRIPTION     
            "Timer Proving Emergency. References: \n - Q.703 Timer T4e \n - T1.111.3 Timer T4e \n - M2PA RFC 4165 (www.ietf.org) \n - draft-bidulock-sigtran-m2pa-test-06.txt \n The default value is taken from draft-bidulock-sigtran-m2pa-test-06.txt and is consistent with Q.703."
    ::= { ptMTPLinksetEntry 59 }

ptMTPLinksetRFC4165T6 OBJECT-TYPE
    SYNTAX          INTEGER { default(-1) }
    MAX-ACCESS      read-create
    STATUS          current
    DESCRIPTION     
            "Timer Remote Congestion. References: \n - Q.703 Timer T6 \n - T1.111.3 Timer T6 \n - M2PA RFC 4165 (www.ietf.org) \n - draft-bidulock-sigtran-m2pa-test-06.txt \n The default value is taken from draft-bidulock-sigtran-m2pa-test-06.txt and is consistent with Q.703."
    ::= { ptMTPLinksetEntry 60 }

ptMTPLinksetRFC4165T7 OBJECT-TYPE
    SYNTAX          INTEGER { default(-1) }
    MAX-ACCESS      read-create
    STATUS          current
    DESCRIPTION     
            "Timer Excessive Delay of Acknowledgment. References: \n - Q.703 Timer T7 \n - T1.111.3 Timer T7 \n - M2PA RFC 4165 (www.ietf.org) \n - draft-bidulock-sigtran-m2pa-test-06.txt \n The default value is consistent with Q.703."
    ::= { ptMTPLinksetEntry 61 }

ptMTPLinksetRFC4165StatusInterval OBJECT-TYPE
    SYNTAX          INTEGER { default(-1) }
    MAX-ACCESS      read-create
    STATUS          current
    DESCRIPTION     
            "Status Interval \n The frequency with which LS Processor Outage messages are sent while LPO."
    ::= { ptMTPLinksetEntry 62 }

ptMTPLinksetRFC4165ProvingRate OBJECT-TYPE
    SYNTAX          INTEGER { default(-1) }
    MAX-ACCESS      read-create
    STATUS          current
    DESCRIPTION     
            "Proving Rate \n The frequency with which LS Proving messages are sent while proving."
    ::= { ptMTPLinksetEntry 63 }

ptMTPLinksetDraft6T1 OBJECT-TYPE
    SYNTAX          INTEGER { default(-1) }
    MAX-ACCESS      read-create
    STATUS          current
    DESCRIPTION     
            "Alignment - Range 1 - 60 seconds with default of 10 seconds. \n These values are taken from draft-ietf-sigtran-m2pa-06.txt."
    ::= { ptMTPLinksetEntry 64 }

ptMTPLinksetDraft6T3 OBJECT-TYPE
    SYNTAX          INTEGER { default(-1) }
    MAX-ACCESS      read-create
    STATUS          current
    DESCRIPTION     
            "Ready - Range 1 - 60 seconds with default of 10 seconds. \n These values are taken from draft-ietf-sigtran-m2pa-06.txt."
    ::= { ptMTPLinksetEntry 65 }

ptMTPLinksetDraft6T4n OBJECT-TYPE
    SYNTAX          INTEGER { default(-1) }
    MAX-ACCESS      read-create
    STATUS          current
    DESCRIPTION     
            "Proving Normal - Range 1-60 seconds with default of 10 seconds. \n These values are taken from draft-ietf-sigtran-m2pa-06.txt."
    ::= { ptMTPLinksetEntry 66 }

ptMTPLinksetDraft6T4e OBJECT-TYPE
    SYNTAX          INTEGER { default(-1) }
    MAX-ACCESS      read-create
    STATUS          current
    DESCRIPTION     
            "Proving Emergency - Range 400-600 ms with default of 500 ms. \n These values are taken from draft-ietf-sigtran-m2pa-06.txt."
    ::= { ptMTPLinksetEntry 67 }

ptMTPLinksetDraft6T6 OBJECT-TYPE
    SYNTAX          INTEGER { default(-1) }
    MAX-ACCESS      read-create
    STATUS          current
    DESCRIPTION     
            "Remote Congestion - Range 1-6 seconds with default of 3 seconds. \n The range is taken from draft-ietf-sigtran-m2pa-06.txt, the default value is implementation dependent."
    ::= { ptMTPLinksetEntry 68 }

ptMTPLinksetDraft6T7 OBJECT-TYPE
    SYNTAX          INTEGER { default(-1) }
    MAX-ACCESS      read-create
    STATUS          current
    DESCRIPTION     
            "Excessive Delay in Acknowledgment - Range 0.5 - 2 seconds with default of 2 seconds. \n The range is taken from draft-ietf-sigtran-m2pa-06.txt, the default value is implementation dependent."
    ::= { ptMTPLinksetEntry 69 }

ptMTPLinksetDraft6StatusInterval OBJECT-TYPE
    SYNTAX          INTEGER { default(-1) }
    MAX-ACCESS      read-create
    STATUS          current
    DESCRIPTION     
            "Status Interval - default 1 second, \n\nThe frequency with which LS Processor Outage messages are sent while LPO (implementation dependent)"
    ::= { ptMTPLinksetEntry 70 }

ptMTPLinksetDraft6ProvingRate OBJECT-TYPE
    SYNTAX          INTEGER { default(-1) }
    MAX-ACCESS      read-create
    STATUS          current
    DESCRIPTION     
            "Proving Rate- default 0.1 second, \n\nThe frequency with which LS Proving messages are sent while proving (implementation dependent)"
    ::= { ptMTPLinksetEntry 71 }

ptMTPLinksetDraft6AcknowledgementInterval OBJECT-TYPE
    SYNTAX          INTEGER { default(-1) }
    MAX-ACCESS      read-create
    STATUS          current
    DESCRIPTION     
            "Maximum time interval before explicitly acknowledging User Data. This can be important in the case of unidirectional or low traffic (implementation dependent)."
    ::= { ptMTPLinksetEntry 72 }

ptMTPLinksetRFC4165AcknowledgementInterval OBJECT-TYPE
    SYNTAX          INTEGER { default(-1) }
    MAX-ACCESS      read-create
    STATUS          current
    DESCRIPTION     
            "Maximum time interval before explicitly acknowledging User Data. This can be important in the case of unidirectional or low traffic."
    ::= { ptMTPLinksetEntry 73 }

ptMTPLinksetM2PARXAbatementBusy OBJECT-TYPE
    SYNTAX          Integer32 (0..2147483647)
    MAX-ACCESS      read-create
    STATUS          current
    DESCRIPTION     
            "Receive Congestion Abatement Busy (bytes per second). \nWhen the M2PA RX Abatement value is cleared (less than) on a given link and the link was previously set to locally busy, an M2PA LSBE message is sent on the link to notify the adjacent point code of the end of the local congestion. \nApplies to both the D6 and RFC-4165 M2PA versions."
    ::= { ptMTPLinksetEntry 86 }

ptMTPLinksetM2PARXOnsetBusy OBJECT-TYPE
    SYNTAX          Integer32 (0..2147483647)
    MAX-ACCESS      read-create
    STATUS          current
    DESCRIPTION     
            "Receive Congestion Onset Busy (bytes per second). \nWhen the M2PA RX Onset Busy value is reached on a given link, an M2PA LSB message is sent on the link to notify the adjacent point code of the local congestion. \nApplies to both the D6 and RFC-4165 M2PA versions."
    ::= { ptMTPLinksetEntry 87 }

ptMTPLinksetM2PATXQueueSize OBJECT-TYPE
    SYNTAX          Integer32 (4000..2147483647)
    MAX-ACCESS      read-create
    STATUS          current
    DESCRIPTION     
            "Size of the M2PA Transmit and Retransmit buffer (Bytes). \nThe M2PA TX Queue Size attribute is used to determine the congestion TX percentage based on the current transmit and retransmit buffer size and maps the value to the appropriate TX Abatement and Onset congestion levels. The congestion level will be updated and displayed on a per link basis in the M2PA Link Congestion Level attribute as required. \nIf an outgoing M2PA message has its message length + the retransmit buffer and the transmit buffer exceed the M2PA TX Queue Size, the message is discarded. \nApplies to both the D6 and RFC-4165 M2PA versions."
    ::= { ptMTPLinksetEntry 88 }

ptMTPLinksetM2PARTBSize OBJECT-TYPE
    SYNTAX          Integer32 (4000..500000)
    MAX-ACCESS      read-create
    STATUS          current
    DESCRIPTION     
            "Size of the M2PA Retransmit buffer (Bytes).\n A larger RTB generally improves throughput but decreases responsiveness. More specifically, with a larger RTB the other end may need to wait longer for M2PA Data Acknowledgment. This value is only used with RFC 4165 links."
    ::= { ptMTPLinksetEntry 89 }

ptMTPLinksetHeartbeat OBJECT-TYPE
    SYNTAX          INTEGER { disabled(0), enabled(1) }
    MAX-ACCESS      read-create
    STATUS          current
    DESCRIPTION     
            "Enable or disable the Heartbeat Feature."
    ::= { ptMTPLinksetEntry 96 }

ptMTPLinksetHeartbeatInterval OBJECT-TYPE
    SYNTAX          Integer32 (0..65535)
    MAX-ACCESS      read-create
    STATUS          current
    DESCRIPTION     
            "Heartbeat interval (ms)."
    ::= { ptMTPLinksetEntry 97 }

ptMTPLinksetRTOInitial OBJECT-TYPE
    SYNTAX          Integer32 (0..2147483647)
    MAX-ACCESS      read-create
    STATUS          current
    DESCRIPTION     
            "RTO Initial (ms)."
    ::= { ptMTPLinksetEntry 98 }

ptMTPLinksetRTOMinimum OBJECT-TYPE
    SYNTAX          Integer32 (0..2147483647)
    MAX-ACCESS      read-create
    STATUS          current
    DESCRIPTION     
            "RTO Minimum (ms)."
    ::= { ptMTPLinksetEntry 99 }

ptMTPLinksetRTOMaximum OBJECT-TYPE
    SYNTAX          Integer32 (0..2147483647)
    MAX-ACCESS      read-create
    STATUS          current
    DESCRIPTION     
            "RTO Maximum (ms)."
    ::= { ptMTPLinksetEntry 100 }

ptMTPLinksetMaximumPathRetrans OBJECT-TYPE
    SYNTAX          Integer32 (0..2147483647)
    MAX-ACCESS      read-create
    STATUS          current
    DESCRIPTION     
            "Maximum path retransmissions."
    ::= { ptMTPLinksetEntry 101 }

ptMTPLinksetMaximumAssocRetrans OBJECT-TYPE
    SYNTAX          Integer32 (0..2147483647)
    MAX-ACCESS      read-create
    STATUS          current
    DESCRIPTION     
            "Maximum association retransmissions."
    ::= { ptMTPLinksetEntry 102 }

ptMTPLinksetBundling OBJECT-TYPE
    SYNTAX          INTEGER { disabled(0), enabled(1) }
    MAX-ACCESS      read-create
    STATUS          current
    DESCRIPTION     
            "Enable or disable Bundling."
    ::= { ptMTPLinksetEntry 103 }

ptMTPLinksetBundlingTO OBJECT-TYPE
    SYNTAX          Integer32 (0..2147483647)
    MAX-ACCESS      read-create
    STATUS          current
    DESCRIPTION     
            "Bundling TO (ms)."
    ::= { ptMTPLinksetEntry 104 }

ptMTPLinksetDelayedACKTO OBJECT-TYPE
    SYNTAX          Integer32 (0..2147483647)
    MAX-ACCESS      read-create
    STATUS          current
    DESCRIPTION     
            "Delayed ACK TO (ms)."
    ::= { ptMTPLinksetEntry 105 }

ptMTPLinksetFastRetransThreshold OBJECT-TYPE
    SYNTAX          Integer32 (0..2147483647)
    MAX-ACCESS      read-create
    STATUS          current
    DESCRIPTION     
            "Fast Retransmit Threshold."
    ::= { ptMTPLinksetEntry 106 }

ptMTPLinksetChecksum OBJECT-TYPE
    SYNTAX          INTEGER { crc32c(0), adler32(1), none(2), auto(3) }
    MAX-ACCESS      read-only
    STATUS          current
    DESCRIPTION     
            "SCTP Checksum"
    ::= { ptMTPLinksetEntry 107 }

ptMTPLinksetBytesBeforeAck OBJECT-TYPE
    SYNTAX          Integer32 (0..2147483647)
    MAX-ACCESS      read-create
    STATUS          current
    DESCRIPTION     
            "Acknowledgment Threshold (Bytes) - If this many bytes of User Data have been received but not acknowledged then an explicit acknowledgment is generated."
    ::= { ptMTPLinksetEntry 112 }

ptMTPLinksetMessagesBeforeAck OBJECT-TYPE
    SYNTAX          Integer32 (0..2147483647)
    MAX-ACCESS      read-create
    STATUS          current
    DESCRIPTION     
            "Acknowledgment Threshold (Message Count) - If this many User Data messages have been received but not acknowledged then an explicit acknowledgment is generated."
    ::= { ptMTPLinksetEntry 113 }

ptMTPLinksetReverseRotateSLS OBJECT-TYPE
    SYNTAX          INTEGER { disabled(0), enabled(1) }
    MAX-ACCESS      read-create
    STATUS          current
    DESCRIPTION     
            "Reverse rotate the SLS of incoming MSUs.\nSetting this parameter with traffic running may result in MSU missequencing.\nSLS Rotation is commonly used in ANSI networks. In some network configurations though SLS rotation can be detrimental, such as when routes via an STP have no cross links.\nOne option in such configurations is to disable SLS rotation on pertinent linksets. If the adjacent node does not support disabling SLS rotation, we can fake it for them by enabling this feature.\nThis feature performs a reverse rotation on the SLS of incoming MSUs before routing/loadsharing decisions or SLS rotation are performed. This modification affects the SLS of the outgoing MSU.\nIf SLS rotation is disabled for the node (via the 'MTP3 NA' 'Rotate SLS' attribute) then this parameter has no effect. \nReverse rotation of the SLS is only applied to MSUs with SI at least 3 (it does not apply to MTP3 management messages)."
    ::= { ptMTPLinksetEntry 114 }

ptMTPLinksetAnnexAT1 OBJECT-TYPE
    SYNTAX          INTEGER { default(-1) }
    MAX-ACCESS      read-create
    STATUS          current
    DESCRIPTION     
            "Aligned/Ready For Annex A links (Q.703) range 25-350s default 300000 ms"
    ::= { ptMTPLinksetEntry 116 }

ptMTPLinksetAnnexAT4n OBJECT-TYPE
    SYNTAX          INTEGER { default(-1) }
    MAX-ACCESS      read-create
    STATUS          current
    DESCRIPTION     
            "Proving Period for Annex A links (Q.703) range 3-70s, default 30000 ms"
    ::= { ptMTPLinksetEntry 117 }

ptMTPLinksetOPCVerification OBJECT-TYPE
    SYNTAX          INTEGER { lpcMatePc(0), enabled(1), none(2), lpc(3) }
    MAX-ACCESS      read-create
    STATUS          current
    DESCRIPTION     
            "OPC Verification \n \nPlease do not change this attribute unless instructed by customer support. \n \nOPC Verification is defined in GR82CORE Issue 10 Section 4.2.7 'OPC Verification' to provide some protection against an entity transmitting an MSU using an OPC that is valid but does not belong to that entity (OPC Spoofing). \n \nThe behaviour is slightly different for MSUs received on a C-link linkset compared to another linkset type. MSUs with the OPC of the Mate STP are accepted from a C-link linkset regardless of the value in this attribute. \n \nFor a linkset other than the linkset to the Mate STP (not a C-linkset): \n* If the 'OPC Verification' attribute is set to ENABLED then the DSC discards MSUs received on this linkset that have OPC set to the Local Point Code (LPC), the point code of the Mate STP (Mate STP PC) or the point code of a VNode. \n* When 'OPC Verification' is set to LPC_MATEPC then the DSC discards MSUs received on this linkset that have OPC set to the LPC or the Mate STP PC. \n* When 'OPC Verification' is set to LPC then the DSC discards MSUs received on this linkset that have OPC set to the LPC. \n* When 'OPC Verification' is set to NONE then no OPC Verification is performed. \n \nFor a linkset to the Mate STP (a C-linkset), MSUs with the OPC set to the Mate STP PC always pass OPC Verification. Hence the OPC Verification checks on a C-linkset are as follows: \n* When the 'OPC Verification' attribute is set to ENABLED the STP discards MSUs received on this linkset that have OPC set to the LPC or the point code of a VNode. An MSU received with the OPC set to the Mate STP PC is not discarded. \n* When 'OPC Verification' is set to LPC_MATEPC MSUs received on this linkset and an MSU is received on this linkset that has OPC set to the LPC of the DSC then the MSU is discarded. An MSU received with the OPC set to the Mate STP PC is not discarded. \n* When 'OPC Verification' is set to LPC and an MSU is received on this linkset that has OPC set to the LPC of the DSC then the MSU is discarded. \n* When 'OPC Verification' is set to NONE, no OPC verification is performed. \n \nOPC Verification failures are typically caused by either a circular route or by OPC Spoofing. Either case can cause problems on its own. For instance, OPC spoofing can make network troubleshooting more difficult and may impair the effectiveness of MTP Transfer Controlled procedures (for managing congestion). \n \nIt is strongly recommended to address the root cause of OPC Verification failures rather than disabling this attribute. \n \nThis attribute defaults to ENABLED for all linksets except C-link linksets. This attribute defaults to LPC_MATEPC for C-link linksets to support configurations with a protocol converter or PCE where R4-8 compliance at the Mate STP may have been disabled. "
    ::= { ptMTPLinksetEntry 118 }

ptMTPLinksetLongMSUSupport OBJECT-TYPE
    SYNTAX          INTEGER { disabled(0), enabled(1) }
    MAX-ACCESS      read-create
    STATUS          current
    DESCRIPTION     
            "Enable or Disable support for MSUs greater than 273 bytes. \nThis attribute defaults to DISABLED "
    ::= { ptMTPLinksetEntry 119 }

ptMTPLinksetLinksetName OBJECT-TYPE
    SYNTAX          DisplayString (SIZE(0..255))
    MAX-ACCESS      read-create
    STATUS          current
    DESCRIPTION     
            "An NA unique linkset name between 2 and 16 characters."
    ::= { ptMTPLinksetEntry 120 }

ptMTPLinksetLongMSUProving OBJECT-TYPE
    SYNTAX          INTEGER { disabled(0), enabled(1) }
    MAX-ACCESS      read-create
    STATUS          current
    DESCRIPTION     
            "Enable or Disable support proving with long MSUs greater than 273 bytes. \nThis attribute defaults to ENABLED. Long MSU proving messages are only sent if the Long MSU Support feature is ENABLED. The length of the proving messages is defined by the Maximum MSU Length value for the NA"
    ::= { ptMTPLinksetEntry 121 }

ptMTPLinksetSCTPClient OBJECT-TYPE
    SYNTAX          INTEGER { disabled(0), enabled(1) }
    MAX-ACCESS      read-create
    STATUS          current
    DESCRIPTION     
            "All links in the linkset operate as an SCTP Client if enabled. \n This attribute is used for Generic Links only. \nIt determines if the links in the linkset operate as SCTP client or server. \nThe Client is the process that initiates establishing the SCTP association. \nWhen disabled the links will respond to SCTP assoc association requests. \nM3UA Server and IPSP links support both client and server operation. \nM3UA SG and M3UA MG links support client operation."
    ::= { ptMTPLinksetEntry 128 }

ptMTPLinksetM3UAClient OBJECT-TYPE
    SYNTAX          INTEGER { disabled(0), enabled(1) }
    MAX-ACCESS      read-create
    STATUS          current
    DESCRIPTION     
            "All links in the linkset operate as an M3UA Client if enabled. \nThis attribute is used for Generic Links only. \nIt determines if links in the linkset operate as \nM3UA ASPs or M3UA SGPs (M3UA client or server). \nWhen enabled the links function as M3UA ASPs. \nWhen disabled the links function as M3UA SGPs. \nOnly IPSP links support both ASP and SGP operation. \nM3UA SG and MG links support ASP functionality. \nM3UA Server links function as SGPs"
    ::= { ptMTPLinksetEntry 129 }

ptMTPLinksetM3UAMGSharedPC OBJECT-TYPE
    SYNTAX          INTEGER { disabled(0), enabled(1) }
    MAX-ACCESS      read-create
    STATUS          current
    DESCRIPTION     
            "All M3UA MG links in the linkset will operate as shared PCs"
    ::= { ptMTPLinksetEntry 130 }

ptMTPLinksetProvingMessageSize OBJECT-TYPE
    SYNTAX          Integer32
    MAX-ACCESS      read-create
    STATUS          current
    DESCRIPTION     
            "Proving Message Size (bytes) - Only applicable for M2PA links. If Long MSU proving is enabled, this value is ignored."
    ::= { ptMTPLinksetEntry 131 }

ptMTPLinksetNetworkIndicator OBJECT-TYPE
    SYNTAX          INTEGER { nodeValue(-1), ni00(0), ni01(1), ni10(2), 
                        ni11(3) }
    MAX-ACCESS      read-create
    STATUS          current
    DESCRIPTION     
            "Network Indicator override on a per linkset basis. \nBy default, the MTP3 NA attribute is used (NODE_VALUE). \nIf set to a value other than NODE_VALUE, the 2 bit value identifying the network in the MTP3 service indicator octet are overwritten to the specified value (NI_00, NI_01, NI_10, or NI_11) on incoming and outgoing MSUs from/to the associated links. \nModification requires the linkset to be inactive"
    ::= { ptMTPLinksetEntry 132 }

ptMTPLinksetABPlaneBit OBJECT-TYPE
    SYNTAX          INTEGER { a(0), b(1), slcEncoded(2) }
    MAX-ACCESS      read-create
    STATUS          current
    DESCRIPTION     
            "Sets the AB plane bit for TTC links. When set to A or B, the link's SLC value represents the 3-bit LSN in the SLS field. \nWhen set to SLC Encoded, the AB plane bit is encoded as part of the link's SLC value. \nYou must delete all the links within the linkset to modify this field. \nThe AB Plane Bit is always set to A for NTT F-links. \nDefault value: SLC Encoded."
    ::= { ptMTPLinksetEntry 133 }

ptMTPLinksetL3T1 OBJECT-TYPE
    SYNTAX          INTEGER { nodeValue(-1) }
    MAX-ACCESS      read-create
    STATUS          current
    DESCRIPTION     
            "Changeover delay ( 500 - 1200 ms ) [ANSI/ITU/JT] \nThe default value is NODE VALUE. \nSetting MTP Level 3 timers on the Linkset to a value other than NODE VALUE overrides the value from the NA and affects all links in the linkset. \nCAUTION: It is recommended that you do not change the timer default values unless instructed otherwise by Signalling Systems Customer Support. Timer values should be modified with care, especially on a live system. Interaction of timers trough the various MTP3 procedures is complex and changing them incorrectly can reduce system stability."
    ::= { ptMTPLinksetEntry 134 }

ptMTPLinksetL3T2 OBJECT-TYPE
    SYNTAX          INTEGER { nodeValue(-1) }
    MAX-ACCESS      read-create
    STATUS          current
    DESCRIPTION     
            "Waiting for COA ( 700 - 2000 ms ) [ANSI/ITU/JT] \nThe default value is NODE VALUE. \nSetting MTP Level 3 timers on the Linkset to a value other than NODE VALUE overrides the value from the NA and affects all links in the linkset. \nCAUTION: It is recommended that you do not change the timer default values unless instructed otherwise by Signalling Systems Customer Support. Timer values should be modified with care, especially on a live system. Interaction of timers trough the various MTP3 procedures is complex and changing them incorrectly can reduce system stability."
    ::= { ptMTPLinksetEntry 135 }

ptMTPLinksetL3T3 OBJECT-TYPE
    SYNTAX          INTEGER { nodeValue(-1) }
    MAX-ACCESS      read-create
    STATUS          current
    DESCRIPTION     
            "Changeback delay ( 500 - 1200 ms ) [ANSI/ITU/JT] \nThe default value is NODE VALUE. \nSetting MTP Level 3 timers on the Linkset to a value other than NODE VALUE overrides the value from the NA and affects all links in the linkset. \nCAUTION: It is recommended that you do not change the timer default values unless instructed otherwise by Signalling Systems Customer Support. Timer values should be modified with care, especially on a live system. Interaction of timers trough the various MTP3 procedures is complex and changing them incorrectly can reduce system stability."
    ::= { ptMTPLinksetEntry 136 }

ptMTPLinksetL3T4 OBJECT-TYPE
    SYNTAX          INTEGER { nodeValue(-1) }
    MAX-ACCESS      read-create
    STATUS          current
    DESCRIPTION     
            "Waiting for CBA: first attempt ( 500 - 1200 ms ) [ANSI/ITU/JT] \nThe default value is NODE VALUE. \nSetting MTP Level 3 timers on the Linkset to a value other than NODE VALUE overrides the value from the NA and affects all links in the linkset. \nCAUTION: It is recommended that you do not change the timer default values unless instructed otherwise by Signalling Systems Customer Support. Timer values should be modified with care, especially on a live system. Interaction of timers trough the various MTP3 procedures is complex and changing them incorrectly can reduce system stability."
    ::= { ptMTPLinksetEntry 137 }

ptMTPLinksetL3T6 OBJECT-TYPE
    SYNTAX          INTEGER { nodeValue(-1) }
    MAX-ACCESS      read-create
    STATUS          current
    DESCRIPTION     
            "Controlled rerouting delay ( 500 - 1200 ms ) [ANSI/ITU/JT] \nThe default value is NODE VALUE. \nSetting MTP Level 3 timers on the Linkset to a value other than NODE VALUE overrides the value from the NA and affects all links in the linkset. \nCAUTION: It is recommended that you do not change the timer default values unless instructed otherwise by Signalling Systems Customer Support. Timer values should be modified with care, especially on a live system. Interaction of timers trough the various MTP3 procedures is complex and changing them incorrectly can reduce system stability."
    ::= { ptMTPLinksetEntry 138 }

ptMTPLinksetMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPLinksetEntry 242 }

ptMTPLinksetMTP3NAIndex OBJECT-TYPE
    SYNTAX          Integer32 (-2147483648..2147483647)
    MAX-ACCESS      not-accessible
    STATUS          current
    DESCRIPTION     
            "This is the index of the parent type for this object.
             This parent type is MTP3NA."
    ::= { ptMTPLinksetEntry 243 }

ptMTPLinksetLinksetsIndex OBJECT-TYPE
    SYNTAX          Integer32 (-2147483648..2147483647)
    MAX-ACCESS      not-accessible
    STATUS          current
    DESCRIPTION     
            "This is the index of the parent type for this object.
             This parent type is Linksets."
    ::= { ptMTPLinksetEntry 244 }

ptMTPLinksetActions OBJECT-TYPE
    SYNTAX          INTEGER { activate(1), deactivate(2), 
                        restoreSCTPDefaults(3), restoreDebugDefaults(4) }
    MAX-ACCESS      read-create
    STATUS          current
    DESCRIPTION     
            "The OID of all possible actions for this instance"
    ::= { ptMTPLinksetEntry 252 }

ptMTPLinksetParentOID OBJECT-TYPE
    SYNTAX          OBJECT IDENTIFIER
    MAX-ACCESS      read-create
    STATUS          current
    DESCRIPTION     
            "The OID of the parent object for this instance"
    ::= { ptMTPLinksetEntry 253 }

ptMTPLinksetRowStatus OBJECT-TYPE
    SYNTAX          RowStatus
    MAX-ACCESS      read-create
    STATUS          current
    DESCRIPTION     
            "The row status for the MTPLinkset table"
    ::= { ptMTPLinksetEntry 254 }

ptMTPLinksetIndex OBJECT-TYPE
    SYNTAX          Integer32 (-2147483648..2147483647)
    MAX-ACCESS      not-accessible
    STATUS          current
    DESCRIPTION     
            "The row number for the MTPLinkset table"
    ::= { ptMTPLinksetEntry 255 }

ptMTPLinkLoadMonitoring OBJECT IDENTIFIER
    ::= { ptMTPLinkset 54 }

ptMTPLinkLoadMonitoringTable OBJECT-TYPE
    SYNTAX          SEQUENCE OF PtMTPLinkLoadMonitoringEntry
    MAX-ACCESS      not-accessible
    STATUS          current
    DESCRIPTION     
            "Monitors the Erlang on each link of the linkset."
    ::= { ptMTPLinkLoadMonitoring 1 }

ptMTPLinkLoadMonitoringEntry OBJECT-TYPE
    SYNTAX          PtMTPLinkLoadMonitoringEntry
    MAX-ACCESS      not-accessible
    STATUS          current
    DESCRIPTION     
            "A sequence of MTPLinkLoadMonitoring attributes."
    INDEX           { ptConnGroupIndex, 
                      ptMTPLinkLoadMonitoringMTP3NAManagerIndex, 
                      ptMTPLinkLoadMonitoringMTP3NAIndex, 
                      ptMTPLinkLoadMonitoringLinksetsIndex, 
                      ptMTPLinkLoadMonitoringLinksetIndex, 
                      ptMTPLinkLoadMonitoringIndex }
    ::= { ptMTPLinkLoadMonitoringTable 1 }

PtMTPLinkLoadMonitoringEntry ::=
    SEQUENCE {
        ptMTPLinkLoadMonitoringMonitoring INTEGER,
        ptMTPLinkLoadMonitoringSLC00Rx  DisplayString,
        ptMTPLinkLoadMonitoringSLC00Tx  DisplayString,
        ptMTPLinkLoadMonitoringSLC01Rx  DisplayString,
        ptMTPLinkLoadMonitoringSLC01Tx  DisplayString,
        ptMTPLinkLoadMonitoringSLC02Rx  DisplayString,
        ptMTPLinkLoadMonitoringSLC02Tx  DisplayString,
        ptMTPLinkLoadMonitoringSLC03Rx  DisplayString,
        ptMTPLinkLoadMonitoringSLC03Tx  DisplayString,
        ptMTPLinkLoadMonitoringSLC04Rx  DisplayString,
        ptMTPLinkLoadMonitoringSLC04Tx  DisplayString,
        ptMTPLinkLoadMonitoringSLC05Rx  DisplayString,
        ptMTPLinkLoadMonitoringSLC05Tx  DisplayString,
        ptMTPLinkLoadMonitoringSLC06Rx  DisplayString,
        ptMTPLinkLoadMonitoringSLC06Tx  DisplayString,
        ptMTPLinkLoadMonitoringSLC07Rx  DisplayString,
        ptMTPLinkLoadMonitoringSLC07Tx  DisplayString,
        ptMTPLinkLoadMonitoringSLC08Rx  DisplayString,
        ptMTPLinkLoadMonitoringSLC08Tx  DisplayString,
        ptMTPLinkLoadMonitoringSLC09Rx  DisplayString,
        ptMTPLinkLoadMonitoringSLC09Tx  DisplayString,
        ptMTPLinkLoadMonitoringSLC10Rx  DisplayString,
        ptMTPLinkLoadMonitoringSLC10Tx  DisplayString,
        ptMTPLinkLoadMonitoringSLC11Rx  DisplayString,
        ptMTPLinkLoadMonitoringSLC11Tx  DisplayString,
        ptMTPLinkLoadMonitoringSLC12Rx  DisplayString,
        ptMTPLinkLoadMonitoringSLC12Tx  DisplayString,
        ptMTPLinkLoadMonitoringSLC13Rx  DisplayString,
        ptMTPLinkLoadMonitoringSLC13Tx  DisplayString,
        ptMTPLinkLoadMonitoringSLC14Rx  DisplayString,
        ptMTPLinkLoadMonitoringSLC14Tx  DisplayString,
        ptMTPLinkLoadMonitoringSLC15Rx  DisplayString,
        ptMTPLinkLoadMonitoringSLC15Tx  DisplayString,
        ptMTPLinkLoadMonitoringMTP3NAManagerIndex         Integer32,
        ptMTPLinkLoadMonitoringMTP3NAIndex  Integer32,
        ptMTPLinkLoadMonitoringLinksetsIndex    Integer32,
        ptMTPLinkLoadMonitoringLinksetIndex   Integer32,
        ptMTPLinkLoadMonitoringActions  INTEGER,
        ptMTPLinkLoadMonitoringParentOID OBJECT IDENTIFIER,
        ptMTPLinkLoadMonitoringRowStatus RowStatus,
        ptMTPLinkLoadMonitoringIndex    Integer32
    }

ptMTPLinkLoadMonitoringMonitoring OBJECT-TYPE
    SYNTAX          INTEGER { disabled(0), enabled(1) }
    MAX-ACCESS      read-only
    STATUS          current
    DESCRIPTION     
            "Traffic Monitoring (ENABLED/DISABLED)"
    ::= { ptMTPLinkLoadMonitoringEntry 1 }

ptMTPLinkLoadMonitoringSLC00Rx OBJECT-TYPE
    SYNTAX          DisplayString (SIZE(0..255))
    MAX-ACCESS      read-only
    STATUS          current
    DESCRIPTION     
            "SLC 0 Rx Erlang"
    ::= { ptMTPLinkLoadMonitoringEntry 2 }

ptMTPLinkLoadMonitoringSLC00Tx OBJECT-TYPE
    SYNTAX          DisplayString (SIZE(0..255))
    MAX-ACCESS      read-only
    STATUS          current
    DESCRIPTION     
            "SLC 0 Tx Erlang"
    ::= { ptMTPLinkLoadMonitoringEntry 3 }

ptMTPLinkLoadMonitoringSLC01Rx OBJECT-TYPE
    SYNTAX          DisplayString (SIZE(0..255))
    MAX-ACCESS      read-only
    STATUS          current
    DESCRIPTION     
            "SLC 1 Rx Erlang"
    ::= { ptMTPLinkLoadMonitoringEntry 4 }

ptMTPLinkLoadMonitoringSLC01Tx OBJECT-TYPE
    SYNTAX          DisplayString (SIZE(0..255))
    MAX-ACCESS      read-only
    STATUS          current
    DESCRIPTION     
            "SLC 1 Tx Erlang"
    ::= { ptMTPLinkLoadMonitoringEntry 5 }

ptMTPLinkLoadMonitoringSLC02Rx OBJECT-TYPE
    SYNTAX          DisplayString (SIZE(0..255))
    MAX-ACCESS      read-only
    STATUS          current
    DESCRIPTION     
            "SLC 2 Rx Erlang"
    ::= { ptMTPLinkLoadMonitoringEntry 6 }

ptMTPLinkLoadMonitoringSLC02Tx OBJECT-TYPE
    SYNTAX          DisplayString (SIZE(0..255))
    MAX-ACCESS      read-only
    STATUS          current
    DESCRIPTION     
            "SLC 2 Tx Erlang"
    ::= { ptMTPLinkLoadMonitoringEntry 7 }

ptMTPLinkLoadMonitoringSLC03Rx OBJECT-TYPE
    SYNTAX          DisplayString (SIZE(0..255))
    MAX-ACCESS      read-only
    STATUS          current
    DESCRIPTION     
            "SLC 3 Rx Erlang"
    ::= { ptMTPLinkLoadMonitoringEntry 8 }

ptMTPLinkLoadMonitoringSLC03Tx OBJECT-TYPE
    SYNTAX          DisplayString (SIZE(0..255))
    MAX-ACCESS      read-only
    STATUS          current
    DESCRIPTION     
            "SLC 3 Tx Erlang"
    ::= { ptMTPLinkLoadMonitoringEntry 9 }

ptMTPLinkLoadMonitoringSLC04Rx OBJECT-TYPE
    SYNTAX          DisplayString (SIZE(0..255))
    MAX-ACCESS      read-only
    STATUS          current
    DESCRIPTION     
            "SLC 4 Rx Erlang"
    ::= { ptMTPLinkLoadMonitoringEntry 10 }

ptMTPLinkLoadMonitoringSLC04Tx OBJECT-TYPE
    SYNTAX          DisplayString (SIZE(0..255))
    MAX-ACCESS      read-only
    STATUS          current
    DESCRIPTION     
            "SLC 4 Tx Erlang"
    ::= { ptMTPLinkLoadMonitoringEntry 11 }

ptMTPLinkLoadMonitoringSLC05Rx OBJECT-TYPE
    SYNTAX          DisplayString (SIZE(0..255))
    MAX-ACCESS      read-only
    STATUS          current
    DESCRIPTION     
            "SLC 5 Rx Erlang"
    ::= { ptMTPLinkLoadMonitoringEntry 12 }

ptMTPLinkLoadMonitoringSLC05Tx OBJECT-TYPE
    SYNTAX          DisplayString (SIZE(0..255))
    MAX-ACCESS      read-only
    STATUS          current
    DESCRIPTION     
            "SLC 5 Tx Erlang"
    ::= { ptMTPLinkLoadMonitoringEntry 13 }

ptMTPLinkLoadMonitoringSLC06Rx OBJECT-TYPE
    SYNTAX          DisplayString (SIZE(0..255))
    MAX-ACCESS      read-only
    STATUS          current
    DESCRIPTION     
            "SLC 6 Rx Erlang"
    ::= { ptMTPLinkLoadMonitoringEntry 14 }

ptMTPLinkLoadMonitoringSLC06Tx OBJECT-TYPE
    SYNTAX          DisplayString (SIZE(0..255))
    MAX-ACCESS      read-only
    STATUS          current
    DESCRIPTION     
            "SLC 6 Tx Erlang"
    ::= { ptMTPLinkLoadMonitoringEntry 15 }

ptMTPLinkLoadMonitoringSLC07Rx OBJECT-TYPE
    SYNTAX          DisplayString (SIZE(0..255))
    MAX-ACCESS      read-only
    STATUS          current
    DESCRIPTION     
            "SLC 7 Rx Erlang"
    ::= { ptMTPLinkLoadMonitoringEntry 16 }

ptMTPLinkLoadMonitoringSLC07Tx OBJECT-TYPE
    SYNTAX          DisplayString (SIZE(0..255))
    MAX-ACCESS      read-only
    STATUS          current
    DESCRIPTION     
            "SLC 7 Tx Erlang"
    ::= { ptMTPLinkLoadMonitoringEntry 17 }

ptMTPLinkLoadMonitoringSLC08Rx OBJECT-TYPE
    SYNTAX          DisplayString (SIZE(0..255))
    MAX-ACCESS      read-only
    STATUS          current
    DESCRIPTION     
            "SLC 8 Rx Erlang"
    ::= { ptMTPLinkLoadMonitoringEntry 18 }

ptMTPLinkLoadMonitoringSLC08Tx OBJECT-TYPE
    SYNTAX          DisplayString (SIZE(0..255))
    MAX-ACCESS      read-only
    STATUS          current
    DESCRIPTION     
            "SLC 8 Tx Erlang"
    ::= { ptMTPLinkLoadMonitoringEntry 19 }

ptMTPLinkLoadMonitoringSLC09Rx OBJECT-TYPE
    SYNTAX          DisplayString (SIZE(0..255))
    MAX-ACCESS      read-only
    STATUS          current
    DESCRIPTION     
            "SLC 9 Rx Erlang"
    ::= { ptMTPLinkLoadMonitoringEntry 20 }

ptMTPLinkLoadMonitoringSLC09Tx OBJECT-TYPE
    SYNTAX          DisplayString (SIZE(0..255))
    MAX-ACCESS      read-only
    STATUS          current
    DESCRIPTION     
            "SLC 9 Tx Erlang"
    ::= { ptMTPLinkLoadMonitoringEntry 21 }

ptMTPLinkLoadMonitoringSLC10Rx OBJECT-TYPE
    SYNTAX          DisplayString (SIZE(0..255))
    MAX-ACCESS      read-only
    STATUS          current
    DESCRIPTION     
            "SLC 10 Rx Erlang"
    ::= { ptMTPLinkLoadMonitoringEntry 22 }

ptMTPLinkLoadMonitoringSLC10Tx OBJECT-TYPE
    SYNTAX          DisplayString (SIZE(0..255))
    MAX-ACCESS      read-only
    STATUS          current
    DESCRIPTION     
            "SLC 10 Tx Erlang"
    ::= { ptMTPLinkLoadMonitoringEntry 23 }

ptMTPLinkLoadMonitoringSLC11Rx OBJECT-TYPE
    SYNTAX          DisplayString (SIZE(0..255))
    MAX-ACCESS      read-only
    STATUS          current
    DESCRIPTION     
            "SLC 11 Rx Erlang"
    ::= { ptMTPLinkLoadMonitoringEntry 24 }

ptMTPLinkLoadMonitoringSLC11Tx OBJECT-TYPE
    SYNTAX          DisplayString (SIZE(0..255))
    MAX-ACCESS      read-only
    STATUS          current
    DESCRIPTION     
            "SLC 11 Tx Erlang"
    ::= { ptMTPLinkLoadMonitoringEntry 25 }

ptMTPLinkLoadMonitoringSLC12Rx OBJECT-TYPE
    SYNTAX          DisplayString (SIZE(0..255))
    MAX-ACCESS      read-only
    STATUS          current
    DESCRIPTION     
            "SLC 12 Rx Erlang"
    ::= { ptMTPLinkLoadMonitoringEntry 26 }

ptMTPLinkLoadMonitoringSLC12Tx OBJECT-TYPE
    SYNTAX          DisplayString (SIZE(0..255))
    MAX-ACCESS      read-only
    STATUS          current
    DESCRIPTION     
            "SLC 12 Tx Erlang"
    ::= { ptMTPLinkLoadMonitoringEntry 27 }

ptMTPLinkLoadMonitoringSLC13Rx OBJECT-TYPE
    SYNTAX          DisplayString (SIZE(0..255))
    MAX-ACCESS      read-only
    STATUS          current
    DESCRIPTION     
            "SLC 13 Rx Erlang"
    ::= { ptMTPLinkLoadMonitoringEntry 28 }

ptMTPLinkLoadMonitoringSLC13Tx OBJECT-TYPE
    SYNTAX          DisplayString (SIZE(0..255))
    MAX-ACCESS      read-only
    STATUS          current
    DESCRIPTION     
            "SLC 13 Tx Erlang"
    ::= { ptMTPLinkLoadMonitoringEntry 29 }

ptMTPLinkLoadMonitoringSLC14Rx OBJECT-TYPE
    SYNTAX          DisplayString (SIZE(0..255))
    MAX-ACCESS      read-only
    STATUS          current
    DESCRIPTION     
            "SLC 14 Rx Erlang"
    ::= { ptMTPLinkLoadMonitoringEntry 30 }

ptMTPLinkLoadMonitoringSLC14Tx OBJECT-TYPE
    SYNTAX          DisplayString (SIZE(0..255))
    MAX-ACCESS      read-only
    STATUS          current
    DESCRIPTION     
            "SLC 14 Tx Erlang"
    ::= { ptMTPLinkLoadMonitoringEntry 31 }

ptMTPLinkLoadMonitoringSLC15Rx OBJECT-TYPE
    SYNTAX          DisplayString (SIZE(0..255))
    MAX-ACCESS      read-only
    STATUS          current
    DESCRIPTION     
            "SLC 15 Rx Erlang"
    ::= { ptMTPLinkLoadMonitoringEntry 32 }

ptMTPLinkLoadMonitoringSLC15Tx OBJECT-TYPE
    SYNTAX          DisplayString (SIZE(0..255))
    MAX-ACCESS      read-only
    STATUS          current
    DESCRIPTION     
            "SLC 15 Tx Erlang"
    ::= { ptMTPLinkLoadMonitoringEntry 33 }

ptMTPLinkLoadMonitoringMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPLinkLoadMonitoringEntry 242 }

ptMTPLinkLoadMonitoringMTP3NAIndex OBJECT-TYPE
    SYNTAX          Integer32 (-2147483648..2147483647)
    MAX-ACCESS      not-accessible
    STATUS          current
    DESCRIPTION     
            "This is the index of the parent type for this object.
             This parent type is MTP3NA."
    ::= { ptMTPLinkLoadMonitoringEntry 243 }

ptMTPLinkLoadMonitoringLinksetsIndex OBJECT-TYPE
    SYNTAX          Integer32 (-2147483648..2147483647)
    MAX-ACCESS      not-accessible
    STATUS          current
    DESCRIPTION     
            "This is the index of the parent type for this object.
             This parent type is Linksets."
    ::= { ptMTPLinkLoadMonitoringEntry 244 }

ptMTPLinkLoadMonitoringLinksetIndex OBJECT-TYPE
    SYNTAX          Integer32 (-2147483648..2147483647)
    MAX-ACCESS      not-accessible
    STATUS          current
    DESCRIPTION     
            "This is the index of the parent type for this object.
             This parent type is Linkset."
    ::= { ptMTPLinkLoadMonitoringEntry 245 }

ptMTPLinkLoadMonitoringActions OBJECT-TYPE
    SYNTAX          INTEGER { startMonitoring(1), stopMonitoring(2) }
    MAX-ACCESS      read-create
    STATUS          current
    DESCRIPTION     
            "The OID of all possible actions for this instance"
    ::= { ptMTPLinkLoadMonitoringEntry 252 }

ptMTPLinkLoadMonitoringParentOID OBJECT-TYPE
    SYNTAX          OBJECT IDENTIFIER
    MAX-ACCESS      read-create
    STATUS          current
    DESCRIPTION     
            "The OID of the parent object for this instance"
    ::= { ptMTPLinkLoadMonitoringEntry 253 }

ptMTPLinkLoadMonitoringRowStatus OBJECT-TYPE
    SYNTAX          RowStatus
    MAX-ACCESS      read-create
    STATUS          current
    DESCRIPTION     
            "The row status for the MTPLinkLoadMonitoring table"
    ::= { ptMTPLinkLoadMonitoringEntry 254 }

ptMTPLinkLoadMonitoringIndex OBJECT-TYPE
    SYNTAX          Integer32 (-2147483648..2147483647)
    MAX-ACCESS      not-accessible
    STATUS          current
    DESCRIPTION     
            "The row number for the MTPLinkLoadMonitoring table"
    ::= { ptMTPLinkLoadMonitoringEntry 255 }

ptMTPLSLink OBJECT IDENTIFIER
    ::= { ptMTPLinkset 55 }

ptMTPLSLinkTable OBJECT-TYPE
    SYNTAX          SEQUENCE OF PtMTPLSLinkEntry
    MAX-ACCESS      not-accessible
    STATUS          current
    DESCRIPTION     
            "A sequence of Link attributes."
    ::= { ptMTPLSLink 1 }

ptMTPLSLinkEntry OBJECT-TYPE
    SYNTAX          PtMTPLSLinkEntry
    MAX-ACCESS      not-accessible
    STATUS          current
    DESCRIPTION     
            "A sequence of MTPLSLink attributes."
    INDEX           { ptConnGroupIndex, ptMTPLSLinkMTP3NAManagerIndex, 
                      ptMTPLSLinkMTP3NAIndex, ptMTPLSLinkLinksetsIndex, 
                      ptMTPLSLinkLinksetIndex, ptMTPLSLinkIndex }
    ::= { ptMTPLSLinkTable 1 }

PtMTPLSLinkEntry ::=
    SEQUENCE {
        ptMTPLSLinkContext              DisplayString,
        ptMTPLSLinkAPC                  Integer32,
        ptMTPLSLinkSLC                  Integer32,
        ptMTPLSLinkDREID                Integer32,
        ptMTPLSLinkCage                 Integer32,
        ptMTPLSLinkChassisSlot          Integer32,
        ptMTPLSLinkChannel              Integer32,
        ptMTPLSLinkL2State              INTEGER,
        ptMTPLSLinkL3State              INTEGER,
        ptMTPLSLinkCongestionLevel      INTEGER,
        ptMTPLSLinkDiagnosticMessage    DisplayString,
        ptMTPLSLinkL2DebugLevel         Integer32,
        ptMTPLSLinkUserActivated        INTEGER,
        ptMTPLSLinkLinkName             DisplayString,
        ptMTPLSLinkAlarms               INTEGER,
        ptMTPLSLinkRxMSUCount           Integer32,
        ptMTPLSLinkTxMSUCount           Integer32,
        ptMTPLSLinkMTP3NAManagerIndex   Integer32,
        ptMTPLSLinkMTP3NAIndex          Integer32,
        ptMTPLSLinkLinksetsIndex        Integer32,
        ptMTPLSLinkLinksetIndex         Integer32,
        ptMTPLSLinkActions              INTEGER,
        ptMTPLSLinkParentOID            OBJECT IDENTIFIER,
        ptMTPLSLinkRowStatus            RowStatus,
        ptMTPLSLinkIndex                Integer32
    }

ptMTPLSLinkContext OBJECT-TYPE
    SYNTAX          DisplayString (SIZE(0..255))
    MAX-ACCESS      read-only
    STATUS          current
    DESCRIPTION     
            "A condensed textual representation of the link object."
    ::= { ptMTPLSLinkEntry 1 }

ptMTPLSLinkAPC OBJECT-TYPE
    SYNTAX          Integer32 (-2147483648..2147483647)
    MAX-ACCESS      read-only
    STATUS          current
    DESCRIPTION     
            "Adjacent SS7 point code of this link."
    ::= { ptMTPLSLinkEntry 2 }

ptMTPLSLinkSLC OBJECT-TYPE
    SYNTAX          Integer32 (0..15)
    MAX-ACCESS      read-only
    STATUS          current
    DESCRIPTION     
            "Signaling Link Code for this link. \nIf AB Plane Bit is set to A or B, valid values are 0-7. \nIf AB Plane Bit is set to SLC ENCODED, valid values are 0-15."
    ::= { ptMTPLSLinkEntry 3 }

ptMTPLSLinkDREID OBJECT-TYPE
    SYNTAX          Integer32 (-2147483648..2147483647)
    MAX-ACCESS      read-only
    STATUS          current
    DESCRIPTION     
            "DRE to own this link."
    ::= { ptMTPLSLinkEntry 4 }

ptMTPLSLinkCage OBJECT-TYPE
    SYNTAX          Integer32 (-1..64)
    MAX-ACCESS      read-create
    STATUS          current
    DESCRIPTION     
            "Cage used by this link"
    ::= { ptMTPLSLinkEntry 5 }

ptMTPLSLinkChassisSlot OBJECT-TYPE
    SYNTAX          Integer32 (-1..255)
    MAX-ACCESS      read-create
    STATUS          current
    DESCRIPTION     
            "Chassis Slot used by this link"
    ::= { ptMTPLSLinkEntry 6 }

ptMTPLSLinkChannel OBJECT-TYPE
    SYNTAX          Integer32 (-1 | 1..65535)
    MAX-ACCESS      read-create
    STATUS          current
    DESCRIPTION     
            "Channel used by this link"
    ::= { ptMTPLSLinkEntry 7 }

ptMTPLSLinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of MTP Level 2 for this link. Deactivated, Proving, In-Service, Out of Service, Failed, Local Processor Outage, Remote Processor Outage, Both Processor Outage, Local Loopback mode, Not Enabled, Not Initialized"
    ::= { ptMTPLSLinkEntry 8 }

ptMTPLSLinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out of Service, Locally Inhibited, Remotely Inhibited, Both Inhibited, Blocked, Blocked and inhibited, Local Processor Outage"
    ::= { ptMTPLSLinkEntry 9 }

ptMTPLSLinkCongestionLevel OBJECT-TYPE
    SYNTAX          INTEGER { false(0), level1(1), level2(2), level3(3), 
                        true(4) }
    MAX-ACCESS      read-only
    STATUS          current
    DESCRIPTION     
            "Congestion level of this link. \n For ANSI, TTC and NTT networks the values range from 1 to 3 or FALSE if not congested. \n For ITU networks the value is either TRUE or FALSE."
    ::= { ptMTPLSLinkEntry 10 }

ptMTPLSLinkDiagnosticMessage OBJECT-TYPE
    SYNTAX          DisplayString (SIZE(0..255))
    MAX-ACCESS      read-only
    STATUS          current
    DESCRIPTION     
            "Link management diagnostic message"
    ::= { ptMTPLSLinkEntry 11 }

ptMTPLSLinkL2DebugLevel OBJECT-TYPE
    SYNTAX          Integer32 (0..3)
    MAX-ACCESS      read-create
    STATUS          current
    DESCRIPTION     
            "MTP Level 2 Debug Level. \nThe recommended value for this attribute is 0."
    ::= { ptMTPLSLinkEntry 12 }

ptMTPLSLinkUserActivated OBJECT-TYPE
    SYNTAX          INTEGER { disabled(0), enabled(1) }
    MAX-ACCESS      read-only
    STATUS          current
    DESCRIPTION     
            "Link activation flag. Used on stack restart for alignment attempt."
    ::= { ptMTPLSLinkEntry 13 }

ptMTPLSLinkLinkName OBJECT-TYPE
    SYNTAX          DisplayString (SIZE(0..255))
    MAX-ACCESS      read-only
    STATUS          current
    DESCRIPTION     
            "Link Name based on the Linkset Name."
    ::= { ptMTPLSLinkEntry 14 }

ptMTPLSLinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPLSLinkEntry 15 }

ptMTPLSLinkRxMSUCount OBJECT-TYPE
    SYNTAX          Integer32 (-2147483648..2147483647)
    MAX-ACCESS      read-only
    STATUS          current
    DESCRIPTION     
            "Received MSU count, per second."
    ::= { ptMTPLSLinkEntry 16 }

ptMTPLSLinkTxMSUCount OBJECT-TYPE
    SYNTAX          Integer32 (-2147483648..2147483647)
    MAX-ACCESS      read-only
    STATUS          current
    DESCRIPTION     
            "Transmitted MSU count, per second."
    ::= { ptMTPLSLinkEntry 17 }

ptMTPLSLinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPLSLinkEntry 242 }

ptMTPLSLinkMTP3NAIndex OBJECT-TYPE
    SYNTAX          Integer32 (-2147483648..2147483647)
    MAX-ACCESS      not-accessible
    STATUS          current
    DESCRIPTION     
            "This is the index of the parent type for this object.
             This parent type is MTP3NA."
    ::= { ptMTPLSLinkEntry 243 }

ptMTPLSLinkLinksetsIndex OBJECT-TYPE
    SYNTAX          Integer32 (-2147483648..2147483647)
    MAX-ACCESS      not-accessible
    STATUS          current
    DESCRIPTION     
            "This is the index of the parent type for this object.
             This parent type is Linksets."
    ::= { ptMTPLSLinkEntry 244 }

ptMTPLSLinkLinksetIndex OBJECT-TYPE
    SYNTAX          Integer32 (-2147483648..2147483647)
    MAX-ACCESS      not-accessible
    STATUS          current
    DESCRIPTION     
            "This is the index of the parent type for this object.
             This parent type is Linkset."
    ::= { ptMTPLSLinkEntry 245 }

ptMTPLSLinkActions OBJECT-TYPE
    SYNTAX          INTEGER { activate(1), deactivate(2), setLPO(3), 
                        clearLPO(4), inhibit(5), uninhibit(6), reset(7) }
    MAX-ACCESS      read-create
    STATUS          current
    DESCRIPTION     
            "The OID of all possible actions for this instance"
    ::= { ptMTPLSLinkEntry 252 }

ptMTPLSLinkParentOID OBJECT-TYPE
    SYNTAX          OBJECT IDENTIFIER
    MAX-ACCESS      read-create
    STATUS          current
    DESCRIPTION     
            "The OID of the parent object for this instance"
    ::= { ptMTPLSLinkEntry 253 }

ptMTPLSLinkRowStatus OBJECT-TYPE
    SYNTAX          RowStatus
    MAX-ACCESS      read-create
    STATUS          current
    DESCRIPTION     
            "The row status for the MTPLSLink table"
    ::= { ptMTPLSLinkEntry 254 }

ptMTPLSLinkIndex OBJECT-TYPE
    SYNTAX          Integer32 (-2147483648..2147483647)
    MAX-ACCESS      not-accessible
    STATUS          current
    DESCRIPTION     
            "The row number for the MTPLSLink table"
    ::= { ptMTPLSLinkEntry 255 }

ptMTPM2PALink OBJECT IDENTIFIER
    ::= { ptMTPLinkset 58 }

ptMTPM2PALinkTable OBJECT-TYPE
    SYNTAX          SEQUENCE OF PtMTPM2PALinkEntry
    MAX-ACCESS      not-accessible
    STATUS          current
    DESCRIPTION     
            "A sequence of Link attributes."
    ::= { ptMTPM2PALink 1 }

ptMTPM2PALinkEntry OBJECT-TYPE
    SYNTAX          PtMTPM2PALinkEntry
    MAX-ACCESS      not-accessible
    STATUS          current
    DESCRIPTION     
            "A sequence of MTPM2PALink attributes."
    INDEX           { ptConnGroupIndex, ptMTPM2PALinkMTP3NAManagerIndex, 
                      ptMTPM2PALinkMTP3NAIndex, 
                      ptMTPM2PALinkLinksetsIndex, 
                      ptMTPM2PALinkLinksetIndex, ptMTPM2PALinkIndex }
    ::= { ptMTPM2PALinkTable 1 }

PtMTPM2PALinkEntry ::=
    SEQUENCE {
        ptMTPM2PALinkContext            DisplayString,
        ptMTPM2PALinkAPC                Integer32,
        ptMTPM2PALinkSLC                Integer32,
        ptMTPM2PALinkDREID              Integer32,
        ptMTPM2PALinkLocalIPAddress1    DisplayString,
        ptMTPM2PALinkLocalIPAddress2    DisplayString,
        ptMTPM2PALinkLocalPort          Integer32,
        ptMTPM2PALinkRemoteIPAddress1   DisplayString,
        ptMTPM2PALinkRemoteIPAddress2   DisplayString,
        ptMTPM2PALinkRemotePort         Integer32,
        ptMTPM2PALinkL2State            INTEGER,
        ptMTPM2PALinkL3State            INTEGER,
        ptMTPM2PALinkCongestionLevel    INTEGER,
        ptMTPM2PALinkDiagnosticMessage  DisplayString,
        ptMTPM2PALinkDataDebugLevel     Integer32,
        ptMTPM2PALinkProtocolDebugLevel Integer32,
        ptMTPM2PALinkSoftwareDebugLevel Integer32,
        ptMTPM2PALinkSCTPDebugLevel     Integer32,
        ptMTPM2PALinkUserActivated      INTEGER,
        ptMTPM2PALinkTXAbatementL1      Integer32,
        ptMTPM2PALinkTXOnsetL1          Integer32,
        ptMTPM2PALinkTXAbatementL2      Integer32,
        ptMTPM2PALinkTXOnsetL2          Integer32,
        ptMTPM2PALinkTXAbatementL3      Integer32,
        ptMTPM2PALinkTXOnsetL3          Integer32,
        ptMTPM2PALinkRXAbatementBusy    Integer32,
        ptMTPM2PALinkRXOnsetBusy        Integer32,
        ptMTPM2PALinkTXQueueSize        Integer32,
        ptMTPM2PALinkLinksetSCTPValues  INTEGER,
        ptMTPM2PALinkHeartbeat          INTEGER,
        ptMTPM2PALinkHeartbeatInterval  Integer32,
        ptMTPM2PALinkRTOInitial         Integer32,
        ptMTPM2PALinkRTOMinimum         Integer32,
        ptMTPM2PALinkRTOMaximum         Integer32,
        ptMTPM2PALinkMaximumPathRetrans Integer32,
        ptMTPM2PALinkMaximumAssocRetrans Integer32,
        ptMTPM2PALinkBundling           INTEGER,
        ptMTPM2PALinkBundlingTO         Integer32,
        ptMTPM2PALinkDelayedACKTO       Integer32,
        ptMTPM2PALinkFastRetransThreshold Integer32,
        ptMTPM2PALinkChecksum           INTEGER,
        ptMTPM2PALinkM2PAVersion        INTEGER,
        ptMTPM2PALinkDataLinkBandwidth  Integer32,
        ptMTPM2PALinkLinkName           DisplayString,
        ptMTPM2PALinkGR310VirtualLink   INTEGER,
        ptMTPM2PALinkTxMSUCount         Integer32,
        ptMTPM2PALinkAlarms             INTEGER,
        ptMTPM2PALinkSendINIT           INTEGER,
        ptMTPM2PALinkRxMSUCount         Integer32,
        ptMTPM2PALinkMTP3NAManagerIndex Integer32,
        ptMTPM2PALinkMTP3NAIndex        Integer32,
        ptMTPM2PALinkLinksetsIndex      Integer32,
        ptMTPM2PALinkLinksetIndex       Integer32,
        ptMTPM2PALinkActions            INTEGER,
        ptMTPM2PALinkParentOID          OBJECT IDENTIFIER,
        ptMTPM2PALinkRowStatus          RowStatus,
        ptMTPM2PALinkIndex              Integer32
    }

ptMTPM2PALinkContext OBJECT-TYPE
    SYNTAX          DisplayString (SIZE(0..255))
    MAX-ACCESS      read-only
    STATUS          current
    DESCRIPTION     
            "A condensed textual representation of the link object."
    ::= { ptMTPM2PALinkEntry 1 }

ptMTPM2PALinkAPC OBJECT-TYPE
    SYNTAX          Integer32 (-2147483648..2147483647)
    MAX-ACCESS      read-only
    STATUS          current
    DESCRIPTION     
            "Adjacent SS7 point code of this link."
    ::= { ptMTPM2PALinkEntry 2 }

ptMTPM2PALinkSLC OBJECT-TYPE
    SYNTAX          Integer32 (0..15)
    MAX-ACCESS      read-only
    STATUS          current
    DESCRIPTION     
            "Signaling Link Code for this link. Value of 0-15."
    ::= { ptMTPM2PALinkEntry 3 }

ptMTPM2PALinkDREID OBJECT-TYPE
    SYNTAX          Integer32 (1..64)
    MAX-ACCESS      read-only
    STATUS          current
    DESCRIPTION     
            "DRE ID of the DRE that owns this link. Since the corresponding DRE process runs on a specific slot, this ID implies the slot where the M2PA terminates locally, and hence the choice of valid local IP addresses for this link."
    ::= { ptMTPM2PALinkEntry 4 }

ptMTPM2PALinkLocalIPAddress1 OBJECT-TYPE
    SYNTAX          DisplayString (SIZE(0..255))
    MAX-ACCESS      read-create
    STATUS          current
    DESCRIPTION     
            "Primary local address. This may be a hostname or an IP Address. If a hostname is used it must be provisioned in /etc/hosts and should resolve to a subset of the local IP Addresses configured for the slot where the link terminates. The slot where the link terminates is indirectly implied by the DRE ID."
    ::= { ptMTPM2PALinkEntry 5 }

ptMTPM2PALinkLocalIPAddress2 OBJECT-TYPE
    SYNTAX          DisplayString (SIZE(0..255))
    MAX-ACCESS      read-create
    STATUS          current
    DESCRIPTION     
            "Secondary local address. This may be a hostname or an IP Address. If a hostname is used it must be provisioned in /etc/hosts and should resolve to a subset of the local IP Addresses configured for the slot where the link terminates. The slot where the link terminates is indirectly implied by the DRE ID."
    ::= { ptMTPM2PALinkEntry 6 }

ptMTPM2PALinkLocalPort OBJECT-TYPE
    SYNTAX          Integer32 (0..65535)
    MAX-ACCESS      read-create
    STATUS          current
    DESCRIPTION     
            "M2PA Local Port."
    ::= { ptMTPM2PALinkEntry 7 }

ptMTPM2PALinkRemoteIPAddress1 OBJECT-TYPE
    SYNTAX          DisplayString (SIZE(0..255))
    MAX-ACCESS      read-create
    STATUS          current
    DESCRIPTION     
            "Primary remote address. This may be a hostname or an IP Address. If a hostname is used it must be provisioned in /etc/hosts. This value is used as the SCTP Primary path to the remote SCTP endpoint."
    ::= { ptMTPM2PALinkEntry 8 }

ptMTPM2PALinkRemoteIPAddress2 OBJECT-TYPE
    SYNTAX          DisplayString (SIZE(0..255))
    MAX-ACCESS      read-create
    STATUS          current
    DESCRIPTION     
            "Secondary remote address. This may be a hostname or an IP Address. If a hostname is used it must be provisioned in /etc/hosts."
    ::= { ptMTPM2PALinkEntry 9 }

ptMTPM2PALinkRemotePort OBJECT-TYPE
    SYNTAX          Integer32 (0..65535)
    MAX-ACCESS      read-create
    STATUS          current
    DESCRIPTION     
            "M2PA Remote Port."
    ::= { ptMTPM2PALinkEntry 10 }

ptMTPM2PALinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of M2PA for this link. Deactivated, Proving, In-Service, Out-of-service, Failed, Local Processor Outage, Remote Processor Outage, Both Processor Outage, Local Loopback mode, Not Enabled, Not Initialized, User Shutdown"
    ::= { ptMTPM2PALinkEntry 11 }

ptMTPM2PALinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out-of-Service, Locally Inhibited, Remotely Inhibited, Both Inhibited, Blocked, Blocked and Uninhibited, Local Processor Outage."
    ::= { ptMTPM2PALinkEntry 12 }

ptMTPM2PALinkCongestionLevel OBJECT-TYPE
    SYNTAX          INTEGER { false(0), level1(1), level2(2), level3(3), 
                        true(4) }
    MAX-ACCESS      read-only
    STATUS          current
    DESCRIPTION     
            "Congestion level of this link. From 1 to 3, or FALSE if not congested."
    ::= { ptMTPM2PALinkEntry 13 }

ptMTPM2PALinkDiagnosticMessage OBJECT-TYPE
    SYNTAX          DisplayString (SIZE(0..255))
    MAX-ACCESS      read-only
    STATUS          current
    DESCRIPTION     
            "Link management diagnostic message."
    ::= { ptMTPM2PALinkEntry 14 }

ptMTPM2PALinkDataDebugLevel OBJECT-TYPE
    SYNTAX          Integer32 (0..255)
    MAX-ACCESS      read-create
    STATUS          current
    DESCRIPTION     
            "Data Debug Level \n\nAmount of information displayed concerning MSU transfers. Higher is more information, 0 is DISABLED. \nThe recommended value for this attribute is 1."
    ::= { ptMTPM2PALinkEntry 15 }

ptMTPM2PALinkProtocolDebugLevel OBJECT-TYPE
    SYNTAX          Integer32 (0..255)
    MAX-ACCESS      read-create
    STATUS          current
    DESCRIPTION     
            "Protocol Debug Level \n\nAmount of information displayed concerning the M2PA protocol. This includes interaction with the M2PA Peer as well as with MTP3 and the SCTP. Higher values cause more logging, a value of 0 disables logging of M2PA Protocol related messages. \nThe recommended value for this attribute is 10."
    ::= { ptMTPM2PALinkEntry 16 }

ptMTPM2PALinkSoftwareDebugLevel OBJECT-TYPE
    SYNTAX          Integer32 (0..255)
    MAX-ACCESS      read-create
    STATUS          current
    DESCRIPTION     
            "Software Debug Level \n\nIndicates how much information to display concerning the internals of the software. A value of 0 indicates no software related information is to be displayed, 1 shows only errors, more than 1 shows more detail. \nThe recommended value for this attribute is 1."
    ::= { ptMTPM2PALinkEntry 17 }

ptMTPM2PALinkSCTPDebugLevel OBJECT-TYPE
    SYNTAX          Integer32 (0..255)
    MAX-ACCESS      read-create
    STATUS          current
    DESCRIPTION     
            "Debug: SCTP debug level for association debugging. \nThe recommended value for this attribute is 1."
    ::= { ptMTPM2PALinkEntry 18 }

ptMTPM2PALinkUserActivated OBJECT-TYPE
    SYNTAX          INTEGER { disabled(0), enabled(1) }
    MAX-ACCESS      read-only
    STATUS          current
    DESCRIPTION     
            "Link activation flag. Used on stack restart for alignment attempt. Only affected by link activation/deactivation."
    ::= { ptMTPM2PALinkEntry 19 }

ptMTPM2PALinkTXAbatementL1 OBJECT-TYPE
    SYNTAX          Integer32
    MAX-ACCESS      read-create
    STATUS          current
    DESCRIPTION     
            "Transmit Congestion Abatement Level 1 (% of buffer usage)"
    ::= { ptMTPM2PALinkEntry 20 }

ptMTPM2PALinkTXOnsetL1 OBJECT-TYPE
    SYNTAX          Integer32
    MAX-ACCESS      read-create
    STATUS          current
    DESCRIPTION     
            "Transmit Congestion Onset Level 1 (% of buffer usage)"
    ::= { ptMTPM2PALinkEntry 21 }

ptMTPM2PALinkTXAbatementL2 OBJECT-TYPE
    SYNTAX          Integer32
    MAX-ACCESS      read-create
    STATUS          current
    DESCRIPTION     
            "Transmit Congestion Abatement Level 2 (% of buffer usage)"
    ::= { ptMTPM2PALinkEntry 22 }

ptMTPM2PALinkTXOnsetL2 OBJECT-TYPE
    SYNTAX          Integer32
    MAX-ACCESS      read-create
    STATUS          current
    DESCRIPTION     
            "Transmit Congestion Onset Level 2 (% of buffer usage)"
    ::= { ptMTPM2PALinkEntry 23 }

ptMTPM2PALinkTXAbatementL3 OBJECT-TYPE
    SYNTAX          Integer32
    MAX-ACCESS      read-create
    STATUS          current
    DESCRIPTION     
            "Transmit Congestion Abatement Level 3 (% of buffer usage)"
    ::= { ptMTPM2PALinkEntry 24 }

ptMTPM2PALinkTXOnsetL3 OBJECT-TYPE
    SYNTAX          Integer32
    MAX-ACCESS      read-create
    STATUS          current
    DESCRIPTION     
            "Transmit Congestion Onset Level 3 (% of buffer usage)"
    ::= { ptMTPM2PALinkEntry 25 }

ptMTPM2PALinkRXAbatementBusy OBJECT-TYPE
    SYNTAX          Integer32 (0..2147483647)
    MAX-ACCESS      read-create
    STATUS          current
    DESCRIPTION     
            "Receive Congestion Abatement Busy (bytes per second). \nWhen the RX Abatement value is cleared (less than) on this link and the link was previously set to locally busy, an M2PA LSBE message is sent on the link to notify the adjacent point code of the end of the local congestion. \nApplies to both the D6 and RFC-4165 M2PA versions."
    ::= { ptMTPM2PALinkEntry 26 }

ptMTPM2PALinkRXOnsetBusy OBJECT-TYPE
    SYNTAX          Integer32 (0..2147483647)
    MAX-ACCESS      read-create
    STATUS          current
    DESCRIPTION     
            "Receive Congestion Onset Busy (bytes per second). \nWhen the RX Onset Busy value is reached on this link, an M2PA LSB message is sent on the link to notify the adjacent point code of the local congestion. \nApplies to both the D6 and RFC-4165 M2PA versions."
    ::= { ptMTPM2PALinkEntry 27 }

ptMTPM2PALinkTXQueueSize OBJECT-TYPE
    SYNTAX          Integer32 (0..2147483647)
    MAX-ACCESS      read-create
    STATUS          current
    DESCRIPTION     
            "Maximum M2PA TX Queue Size (number of bytes). \nThe TX Queue Size attribute is used to determine the congestion TX percentage based on the current transmit and retransmit buffer size and maps the value to the appropriate TX Abatement and Onset congestion levels. The congestion level will be updated and displayed in the Congestion Level attribute as required. \nIf an outgoing M2PA message has its message length + the retransmit buffer and the transmit buffer exceed the TX Queue Size, the message is discarded. \nApplies to both the D6 and RFC-4165 M2PA versions."
    ::= { ptMTPM2PALinkEntry 28 }

ptMTPM2PALinkLinksetSCTPValues OBJECT-TYPE
    SYNTAX          INTEGER { no(0), yes(1) }
    MAX-ACCESS      read-create
    STATUS          current
    DESCRIPTION     
            "When this is set, the link uses the M2PA Linkset SCTP values. In that case, the SCTP parameters may not be modified at the M2PA Link level."
    ::= { ptMTPM2PALinkEntry 29 }

ptMTPM2PALinkHeartbeat OBJECT-TYPE
    SYNTAX          INTEGER { disabled(0), enabled(1) }
    MAX-ACCESS      read-create
    STATUS          current
    DESCRIPTION     
            "On / Off Heartbeat Feature"
    ::= { ptMTPM2PALinkEntry 30 }

ptMTPM2PALinkHeartbeatInterval OBJECT-TYPE
    SYNTAX          Integer32 (0..65535)
    MAX-ACCESS      read-create
    STATUS          current
    DESCRIPTION     
            "Heartbeat interval (ms)"
    ::= { ptMTPM2PALinkEntry 31 }

ptMTPM2PALinkRTOInitial OBJECT-TYPE
    SYNTAX          Integer32 (0..2147483647)
    MAX-ACCESS      read-create
    STATUS          current
    DESCRIPTION     
            "RTO Initial (ms)"
    ::= { ptMTPM2PALinkEntry 32 }

ptMTPM2PALinkRTOMinimum OBJECT-TYPE
    SYNTAX          Integer32 (0..2147483647)
    MAX-ACCESS      read-create
    STATUS          current
    DESCRIPTION     
            "RTO Minimum (ms)"
    ::= { ptMTPM2PALinkEntry 33 }

ptMTPM2PALinkRTOMaximum OBJECT-TYPE
    SYNTAX          Integer32 (0..2147483647)
    MAX-ACCESS      read-create
    STATUS          current
    DESCRIPTION     
            "RTO Maximum (ms)"
    ::= { ptMTPM2PALinkEntry 34 }

ptMTPM2PALinkMaximumPathRetrans OBJECT-TYPE
    SYNTAX          Integer32 (0..2147483647)
    MAX-ACCESS      read-create
    STATUS          current
    DESCRIPTION     
            "Maximum path retransmissions"
    ::= { ptMTPM2PALinkEntry 35 }

ptMTPM2PALinkMaximumAssocRetrans OBJECT-TYPE
    SYNTAX          Integer32 (0..2147483647)
    MAX-ACCESS      read-create
    STATUS          current
    DESCRIPTION     
            "Maximum association retransmissions"
    ::= { ptMTPM2PALinkEntry 36 }

ptMTPM2PALinkBundling OBJECT-TYPE
    SYNTAX          INTEGER { disabled(0), enabled(1) }
    MAX-ACCESS      read-create
    STATUS          current
    DESCRIPTION     
            "Bundling On / Off"
    ::= { ptMTPM2PALinkEntry 37 }

ptMTPM2PALinkBundlingTO OBJECT-TYPE
    SYNTAX          Integer32 (0..2147483647)
    MAX-ACCESS      read-create
    STATUS          current
    DESCRIPTION     
            "Bundling TO (ms)"
    ::= { ptMTPM2PALinkEntry 38 }

ptMTPM2PALinkDelayedACKTO OBJECT-TYPE
    SYNTAX          Integer32 (0..2147483647)
    MAX-ACCESS      read-create
    STATUS          current
    DESCRIPTION     
            "Delayed ACK TO (ms)"
    ::= { ptMTPM2PALinkEntry 39 }

ptMTPM2PALinkFastRetransThreshold OBJECT-TYPE
    SYNTAX          Integer32 (0..2147483647)
    MAX-ACCESS      read-create
    STATUS          current
    DESCRIPTION     
            "Fast Retransmit Threshold"
    ::= { ptMTPM2PALinkEntry 40 }

ptMTPM2PALinkChecksum OBJECT-TYPE
    SYNTAX          INTEGER { crc32c(0), adler32(1), none(2), auto(3) }
    MAX-ACCESS      read-only
    STATUS          current
    DESCRIPTION     
            "SCTP Checksum"
    ::= { ptMTPM2PALinkEntry 41 }

ptMTPM2PALinkM2PAVersion OBJECT-TYPE
    SYNTAX          INTEGER { draft6(6), rfc4165(13) }
    MAX-ACCESS      read-create
    STATUS          current
    DESCRIPTION     
            "M2PA Version used to manage this link.\n\nTo change, make sure the link is deactivated."
    ::= { ptMTPM2PALinkEntry 42 }

ptMTPM2PALinkDataLinkBandwidth OBJECT-TYPE
    SYNTAX          Integer32 (1..2147483647)
    MAX-ACCESS      read-create
    STATUS          current
    DESCRIPTION     
            "M2PA DataLink Baud Rate in kbps used to calculate Erlang "
    ::= { ptMTPM2PALinkEntry 43 }

ptMTPM2PALinkLinkName OBJECT-TYPE
    SYNTAX          DisplayString (SIZE(0..255))
    MAX-ACCESS      read-only
    STATUS          current
    DESCRIPTION     
            "Link Name based on the Linkset Name."
    ::= { ptMTPM2PALinkEntry 44 }

ptMTPM2PALinkGR310VirtualLink OBJECT-TYPE
    SYNTAX          INTEGER { disabled(0), enabled(1) }
    MAX-ACCESS      read-create
    STATUS          current
    DESCRIPTION     
            "Indicates whether the M2PA Link represents GR-310-CORE M2PA virtual link (ENABLED/DISABLED).\n This attribute is only used for GR-310-CORE provisioning and is not relevant for non SNAMI licensed deployments. There is no impact on the CMU and TL1 provisioning interfaces.\n The GR-310-CORE provisioning model splits the creation of M2PA links into two entities, an M2PA virtual link (M2PAVLK) and a signaling link (SLK), where the M2PAVLK must be created first. In this implementation, the M2PAVLK parameters are stored in the M2PA Link object. In order to support the GR-310-CORE provisioning model, this attribute indicates whether this M2PA Link object should be treated as a full SLK with an associated M2PAVLK, or as simply an M2PAVLK. If this attribute is set to ENABLED then this object is not considered a full link from GR-310-CORE prespective.\n Default value: DISABLED."
    ::= { ptMTPM2PALinkEntry 45 }

ptMTPM2PALinkTxMSUCount OBJECT-TYPE
    SYNTAX          Integer32 (-2147483648..2147483647)
    MAX-ACCESS      read-only
    STATUS          current
    DESCRIPTION     
            "Transmitted MSU count, per second."
    ::= { ptMTPM2PALinkEntry 46 }

ptMTPM2PALinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPM2PALinkEntry 47 }

ptMTPM2PALinkSendINIT OBJECT-TYPE
    SYNTAX          INTEGER { disabled(0), enabled(1) }
    MAX-ACCESS      read-create
    STATUS          current
    DESCRIPTION     
            "When ENABLED, the local endpoint sends SCTP INIT to the remote endpoint. \n When DISABLED, the local endpoint does NOT send SCTP INIT to the remote endpoint. \n This attribute can be modified only when the SCTP association is down."
    ::= { ptMTPM2PALinkEntry 48 }

ptMTPM2PALinkRxMSUCount OBJECT-TYPE
    SYNTAX          Integer32 (-2147483648..2147483647)
    MAX-ACCESS      read-only
    STATUS          current
    DESCRIPTION     
            "Received MSU count, per second."
    ::= { ptMTPM2PALinkEntry 49 }

ptMTPM2PALinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPM2PALinkEntry 242 }

ptMTPM2PALinkMTP3NAIndex OBJECT-TYPE
    SYNTAX          Integer32 (-2147483648..2147483647)
    MAX-ACCESS      not-accessible
    STATUS          current
    DESCRIPTION     
            "This is the index of the parent type for this object.
             This parent type is MTP3NA."
    ::= { ptMTPM2PALinkEntry 243 }

ptMTPM2PALinkLinksetsIndex OBJECT-TYPE
    SYNTAX          Integer32 (-2147483648..2147483647)
    MAX-ACCESS      not-accessible
    STATUS          current
    DESCRIPTION     
            "This is the index of the parent type for this object.
             This parent type is Linksets."
    ::= { ptMTPM2PALinkEntry 244 }

ptMTPM2PALinkLinksetIndex OBJECT-TYPE
    SYNTAX          Integer32 (-2147483648..2147483647)
    MAX-ACCESS      not-accessible
    STATUS          current
    DESCRIPTION     
            "This is the index of the parent type for this object.
             This parent type is Linkset."
    ::= { ptMTPM2PALinkEntry 245 }

ptMTPM2PALinkActions OBJECT-TYPE
    SYNTAX          INTEGER { activate(1), deactivate(2), setLPO(3), 
                        clearLPO(4), inhibit(5), uninhibit(6), 
                        shutdown(7), connect(8), reset(9) }
    MAX-ACCESS      read-create
    STATUS          current
    DESCRIPTION     
            "The OID of all possible actions for this instance"
    ::= { ptMTPM2PALinkEntry 252 }

ptMTPM2PALinkParentOID OBJECT-TYPE
    SYNTAX          OBJECT IDENTIFIER
    MAX-ACCESS      read-create
    STATUS          current
    DESCRIPTION     
            "The OID of the parent object for this instance"
    ::= { ptMTPM2PALinkEntry 253 }

ptMTPM2PALinkRowStatus OBJECT-TYPE
    SYNTAX          RowStatus
    MAX-ACCESS      read-create
    STATUS          current
    DESCRIPTION     
            "The row status for the MTPM2PALink table"
    ::= { ptMTPM2PALinkEntry 254 }

ptMTPM2PALinkIndex OBJECT-TYPE
    SYNTAX          Integer32 (-2147483648..2147483647)
    MAX-ACCESS      not-accessible
    STATUS          current
    DESCRIPTION     
            "The row number for the MTPM2PALink table"
    ::= { ptMTPM2PALinkEntry 255 }

ptMTPM2UALink OBJECT IDENTIFIER
    ::= { ptMTPLinkset 70 }

ptMTPM2UALinkTable OBJECT-TYPE
    SYNTAX          SEQUENCE OF PtMTPM2UALinkEntry
    MAX-ACCESS      not-accessible
    STATUS          current
    DESCRIPTION     
            "A sequence of Link attributes."
    ::= { ptMTPM2UALink 1 }

ptMTPM2UALinkEntry OBJECT-TYPE
    SYNTAX          PtMTPM2UALinkEntry
    MAX-ACCESS      not-accessible
    STATUS          current
    DESCRIPTION     
            "A sequence of MTPM2UALink attributes."
    INDEX           { ptConnGroupIndex, ptMTPM2UALinkMTP3NAManagerIndex, 
                      ptMTPM2UALinkMTP3NAIndex, 
                      ptMTPM2UALinkLinksetsIndex, 
                      ptMTPM2UALinkLinksetIndex, ptMTPM2UALinkIndex }
    ::= { ptMTPM2UALinkTable 1 }

PtMTPM2UALinkEntry ::=
    SEQUENCE {
        ptMTPM2UALinkContext            DisplayString,
        ptMTPM2UALinkAPC                Integer32,
        ptMTPM2UALinkSLC                Integer32,
        ptMTPM2UALinkDREID              Integer32,
        ptMTPM2UALinkCage               Integer32,
        ptMTPM2UALinkIID                Integer32,
        ptMTPM2UALinkL2State            INTEGER,
        ptMTPM2UALinkL3State            INTEGER,
        ptMTPM2UALinkCongestionLevel    INTEGER,
        ptMTPM2UALinkDiagnosticMessage  DisplayString,
        ptMTPM2UALinkL2DebugLevel       Integer32,
        ptMTPM2UALinkUserActivated      INTEGER,
        ptMTPM2UALinkLinkName           DisplayString,
        ptMTPM2UALinkAlarms             INTEGER,
        ptMTPM2UALinkLinkOscillationFilter  INTEGER,
        ptMTPM2UALinkDataLinkBandwidth  INTEGER,
        ptMTPM2UALinkRxMSUCount         Integer32,
        ptMTPM2UALinkTxMSUCount         Integer32,
        ptMTPM2UALinkMTP3NAManagerIndex Integer32,
        ptMTPM2UALinkMTP3NAIndex        Integer32,
        ptMTPM2UALinkLinksetsIndex      Integer32,
        ptMTPM2UALinkLinksetIndex       Integer32,
        ptMTPM2UALinkActions            INTEGER,
        ptMTPM2UALinkParentOID          OBJECT IDENTIFIER,
        ptMTPM2UALinkRowStatus          RowStatus,
        ptMTPM2UALinkIndex              Integer32
    }

ptMTPM2UALinkContext OBJECT-TYPE
    SYNTAX          DisplayString (SIZE(0..255))
    MAX-ACCESS      read-only
    STATUS          current
    DESCRIPTION     
            "A condensed textual representation of the link object."
    ::= { ptMTPM2UALinkEntry 1 }

ptMTPM2UALinkAPC OBJECT-TYPE
    SYNTAX          Integer32 (-2147483648..2147483647)
    MAX-ACCESS      read-only
    STATUS          current
    DESCRIPTION     
            "Adjacent SS7 point code of this link"
    ::= { ptMTPM2UALinkEntry 2 }

ptMTPM2UALinkSLC OBJECT-TYPE
    SYNTAX          Integer32 (0..15)
    MAX-ACCESS      read-only
    STATUS          current
    DESCRIPTION     
            "Signaling Link Code for this link. Value of 0-15"
    ::= { ptMTPM2UALinkEntry 3 }

ptMTPM2UALinkDREID OBJECT-TYPE
    SYNTAX          Integer32 (-2147483648..2147483647)
    MAX-ACCESS      read-only
    STATUS          current
    DESCRIPTION     
            "DRE to own this link."
    ::= { ptMTPM2UALinkEntry 4 }

ptMTPM2UALinkCage OBJECT-TYPE
    SYNTAX          Integer32 (-1..127)
    MAX-ACCESS      read-create
    STATUS          current
    DESCRIPTION     
            "Cage used by this link"
    ::= { ptMTPM2UALinkEntry 5 }

ptMTPM2UALinkIID OBJECT-TYPE
    SYNTAX          Integer32 (-1 | 1..65534)
    MAX-ACCESS      read-create
    STATUS          current
    DESCRIPTION     
            "Channel used by this link"
    ::= { ptMTPM2UALinkEntry 7 }

ptMTPM2UALinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of MTP Level 2 for this link. Deactivated, Proving, In-Service, Out of Service, Failed, Local Processor Outage, Remote Processor Outage, Both Processor Outage, Local Loopback mode, Not Enabled, Not Initialized"
    ::= { ptMTPM2UALinkEntry 8 }

ptMTPM2UALinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out of Service, Locally Inhibited, Remotely Inhibited, Both Inhibited, Blocked, Blocked and Uninhibited, Local Processor Outage"
    ::= { ptMTPM2UALinkEntry 9 }

ptMTPM2UALinkCongestionLevel OBJECT-TYPE
    SYNTAX          INTEGER { false(0), level1(1), level2(2), level3(3), 
                        true(4) }
    MAX-ACCESS      read-only
    STATUS          current
    DESCRIPTION     
            "Congestion level of this link. For ANSI, from 1 to 3, or FALSE if not congested. For ITU, TRUE or FALSE."
    ::= { ptMTPM2UALinkEntry 10 }

ptMTPM2UALinkDiagnosticMessage OBJECT-TYPE
    SYNTAX          DisplayString (SIZE(0..255))
    MAX-ACCESS      read-only
    STATUS          current
    DESCRIPTION     
            "Link management diagnostic message"
    ::= { ptMTPM2UALinkEntry 11 }

ptMTPM2UALinkL2DebugLevel OBJECT-TYPE
    SYNTAX          Integer32 (0..3)
    MAX-ACCESS      read-create
    STATUS          current
    DESCRIPTION     
            "MTP Level 2 Debug Level. \nThe recommended value for this attribute is 0."
    ::= { ptMTPM2UALinkEntry 12 }

ptMTPM2UALinkUserActivated OBJECT-TYPE
    SYNTAX          INTEGER { disabled(0), enabled(1) }
    MAX-ACCESS      read-only
    STATUS          current
    DESCRIPTION     
            "Link activation flag. Used on stack restart for alignment attempt. Only affected by link activation/deactivation."
    ::= { ptMTPM2UALinkEntry 13 }

ptMTPM2UALinkLinkName OBJECT-TYPE
    SYNTAX          DisplayString (SIZE(0..255))
    MAX-ACCESS      read-only
    STATUS          current
    DESCRIPTION     
            "Link Name based on the Linkset Name."
    ::= { ptMTPM2UALinkEntry 14 }

ptMTPM2UALinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPM2UALinkEntry 15 }

ptMTPM2UALinkLinkOscillationFilter OBJECT-TYPE
    SYNTAX          INTEGER { disabled(0), enabled(1) }
    MAX-ACCESS      read-create
    STATUS          current
    DESCRIPTION     
            "Link Oscillation Filter. The timer can be enabled \n by setting this attribute to ENABLED. It can be disabled \n by setting this filed to DISABLED. The timer if enabled, \n prevents this M2UAlink from oscillating between \n aligned and non-aligned states repeatedly. It works \n in ANSI only using timer value from T32"
    ::= { ptMTPM2UALinkEntry 17 }

ptMTPM2UALinkDataLinkBandwidth OBJECT-TYPE
    SYNTAX          INTEGER { fiftySixKbps(56), sixtyFourKbps(64) }
    MAX-ACCESS      read-create
    STATUS          current
    DESCRIPTION     
            "Link Baud Rate used to calculate Erlang "
    ::= { ptMTPM2UALinkEntry 18 }

ptMTPM2UALinkRxMSUCount OBJECT-TYPE
    SYNTAX          Integer32 (-2147483648..2147483647)
    MAX-ACCESS      read-only
    STATUS          current
    DESCRIPTION     
            "Received MSU count, per second."
    ::= { ptMTPM2UALinkEntry 19 }

ptMTPM2UALinkTxMSUCount OBJECT-TYPE
    SYNTAX          Integer32 (-2147483648..2147483647)
    MAX-ACCESS      read-only
    STATUS          current
    DESCRIPTION     
            "Transmitted MSU count, per second."
    ::= { ptMTPM2UALinkEntry 20 }

ptMTPM2UALinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPM2UALinkEntry 242 }

ptMTPM2UALinkMTP3NAIndex OBJECT-TYPE
    SYNTAX          Integer32 (-2147483648..2147483647)
    MAX-ACCESS      not-accessible
    STATUS          current
    DESCRIPTION     
            "This is the index of the parent type for this object.
             This parent type is MTP3NA."
    ::= { ptMTPM2UALinkEntry 243 }

ptMTPM2UALinkLinksetsIndex OBJECT-TYPE
    SYNTAX          Integer32 (-2147483648..2147483647)
    MAX-ACCESS      not-accessible
    STATUS          current
    DESCRIPTION     
            "This is the index of the parent type for this object.
             This parent type is Linksets."
    ::= { ptMTPM2UALinkEntry 244 }

ptMTPM2UALinkLinksetIndex OBJECT-TYPE
    SYNTAX          Integer32 (-2147483648..2147483647)
    MAX-ACCESS      not-accessible
    STATUS          current
    DESCRIPTION     
            "This is the index of the parent type for this object.
             This parent type is Linkset."
    ::= { ptMTPM2UALinkEntry 245 }

ptMTPM2UALinkActions OBJECT-TYPE
    SYNTAX          INTEGER { activate(1), deactivate(2), setLPO(3), 
                        clearLPO(4), inhibit(5), uninhibit(6), reset(7) }
    MAX-ACCESS      read-create
    STATUS          current
    DESCRIPTION     
            "The OID of all possible actions for this instance"
    ::= { ptMTPM2UALinkEntry 252 }

ptMTPM2UALinkParentOID OBJECT-TYPE
    SYNTAX          OBJECT IDENTIFIER
    MAX-ACCESS      read-create
    STATUS          current
    DESCRIPTION     
            "The OID of the parent object for this instance"
    ::= { ptMTPM2UALinkEntry 253 }

ptMTPM2UALinkRowStatus OBJECT-TYPE
    SYNTAX          RowStatus
    MAX-ACCESS      read-create
    STATUS          current
    DESCRIPTION     
            "The row status for the MTPM2UALink table"
    ::= { ptMTPM2UALinkEntry 254 }

ptMTPM2UALinkIndex OBJECT-TYPE
    SYNTAX          Integer32 (-2147483648..2147483647)
    MAX-ACCESS      not-accessible
    STATUS          current
    DESCRIPTION     
            "The row number for the MTPM2UALink table"
    ::= { ptMTPM2UALinkEntry 255 }

ptMTPATMLink OBJECT IDENTIFIER
    ::= { ptMTPLinkset 72 }

ptMTPATMLinkTable OBJECT-TYPE
    SYNTAX          SEQUENCE OF PtMTPATMLinkEntry
    MAX-ACCESS      not-accessible
    STATUS          current
    DESCRIPTION     
            "A sequence of Link attributes."
    ::= { ptMTPATMLink 1 }

ptMTPATMLinkEntry OBJECT-TYPE
    SYNTAX          PtMTPATMLinkEntry
    MAX-ACCESS      not-accessible
    STATUS          current
    DESCRIPTION     
            "A sequence of MTPATMLink attributes."
    INDEX           { ptConnGroupIndex, ptMTPATMLinkMTP3NAManagerIndex, 
                      ptMTPATMLinkMTP3NAIndex, ptMTPATMLinkLinksetsIndex, 
                      ptMTPATMLinkLinksetIndex, ptMTPATMLinkIndex }
    ::= { ptMTPATMLinkTable 1 }

PtMTPATMLinkEntry ::=
    SEQUENCE {
        ptMTPATMLinkContext             DisplayString,
        ptMTPATMLinkAPC                 Integer32,
        ptMTPATMLinkSLC                 Integer32,
        ptMTPATMLinkDREID               Integer32,
        ptMTPATMLinkCage                Integer32,
        ptMTPATMLinkChannel             Integer32,
        ptMTPATMLinkL2State             INTEGER,
        ptMTPATMLinkL3State             INTEGER,
        ptMTPATMLinkCongestionLevel     INTEGER,
        ptMTPATMLinkDiagnosticMessage   DisplayString,
        ptMTPATMLinkL2DebugLevel        Integer32,
        ptMTPATMLinkUserActivated       INTEGER,
        ptMTPATMLinkLinkName            DisplayString,
        ptMTPATMLinkAlarms              INTEGER,
        ptMTPATMLinkRxMSUCount          Integer32,
        ptMTPATMLinkTxMSUCount          Integer32,
        ptMTPATMLinkMTP3NAManagerIndex  Integer32,
        ptMTPATMLinkMTP3NAIndex         Integer32,
        ptMTPATMLinkLinksetsIndex       Integer32,
        ptMTPATMLinkLinksetIndex        Integer32,
        ptMTPATMLinkActions             INTEGER,
        ptMTPATMLinkParentOID           OBJECT IDENTIFIER,
        ptMTPATMLinkRowStatus           RowStatus,
        ptMTPATMLinkIndex               Integer32
    }

ptMTPATMLinkContext OBJECT-TYPE
    SYNTAX          DisplayString (SIZE(0..255))
    MAX-ACCESS      read-only
    STATUS          current
    DESCRIPTION     
            "A condensed textual representation of the link object."
    ::= { ptMTPATMLinkEntry 1 }

ptMTPATMLinkAPC OBJECT-TYPE
    SYNTAX          Integer32 (-2147483648..2147483647)
    MAX-ACCESS      read-only
    STATUS          current
    DESCRIPTION     
            "Adjacent SS7 point code of this link."
    ::= { ptMTPATMLinkEntry 2 }

ptMTPATMLinkSLC OBJECT-TYPE
    SYNTAX          Integer32 (0..15)
    MAX-ACCESS      read-only
    STATUS          current
    DESCRIPTION     
            "Signaling Link Code for this link. Value of 0-15"
    ::= { ptMTPATMLinkEntry 3 }

ptMTPATMLinkDREID OBJECT-TYPE
    SYNTAX          Integer32 (-2147483648..2147483647)
    MAX-ACCESS      read-only
    STATUS          current
    DESCRIPTION     
            "DRE to own this link."
    ::= { ptMTPATMLinkEntry 4 }

ptMTPATMLinkCage OBJECT-TYPE
    SYNTAX          Integer32 (-1..64)
    MAX-ACCESS      read-create
    STATUS          current
    DESCRIPTION     
            "Cage used by this link"
    ::= { ptMTPATMLinkEntry 5 }

ptMTPATMLinkChannel OBJECT-TYPE
    SYNTAX          Integer32 (-1 | 1..8)
    MAX-ACCESS      read-create
    STATUS          current
    DESCRIPTION     
            "Channel used by this link, valid values are 1 to 8"
    ::= { ptMTPATMLinkEntry 7 }

ptMTPATMLinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of MTP Level 2 for this link. Deactivated, Proving, In-Service, Out of Service, Failed, Local Processor Outage, Remote Processor Outage, Both Processor Outage, Local Loopback mode, Not Enabled, Not Initialized"
    ::= { ptMTPATMLinkEntry 8 }

ptMTPATMLinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out of Service, Locally Inhibited, Remotely Inhibited, Both Inhibited, Blocked, Blocked and Uninhibited, Local Processor Outage"
    ::= { ptMTPATMLinkEntry 9 }

ptMTPATMLinkCongestionLevel OBJECT-TYPE
    SYNTAX          INTEGER { false(0), level1(1), level2(2), level3(3), 
                        true(4) }
    MAX-ACCESS      read-only
    STATUS          current
    DESCRIPTION     
            "Congestion level of this link. \n For ANSI networks the values range from 1 to 3 or FALSE if not congested. \n For ITU networks the value is either TRUE or FALSE."
    ::= { ptMTPATMLinkEntry 10 }

ptMTPATMLinkDiagnosticMessage OBJECT-TYPE
    SYNTAX          DisplayString (SIZE(0..255))
    MAX-ACCESS      read-only
    STATUS          current
    DESCRIPTION     
            "Link management diagnostic message"
    ::= { ptMTPATMLinkEntry 11 }

ptMTPATMLinkL2DebugLevel OBJECT-TYPE
    SYNTAX          Integer32 (0..3)
    MAX-ACCESS      read-create
    STATUS          current
    DESCRIPTION     
            "MTP Level 2 Debug Level. \nThe recommended value for this attribute is 0."
    ::= { ptMTPATMLinkEntry 12 }

ptMTPATMLinkUserActivated OBJECT-TYPE
    SYNTAX          INTEGER { disabled(0), enabled(1) }
    MAX-ACCESS      read-only
    STATUS          current
    DESCRIPTION     
            "Link activation flag. Used on stack restart for alignment attempt."
    ::= { ptMTPATMLinkEntry 13 }

ptMTPATMLinkLinkName OBJECT-TYPE
    SYNTAX          DisplayString (SIZE(0..255))
    MAX-ACCESS      read-only
    STATUS          current
    DESCRIPTION     
            "Link Name based on the Linkset Name."
    ::= { ptMTPATMLinkEntry 14 }

ptMTPATMLinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPATMLinkEntry 15 }

ptMTPATMLinkRxMSUCount OBJECT-TYPE
    SYNTAX          Integer32 (-2147483648..2147483647)
    MAX-ACCESS      read-only
    STATUS          current
    DESCRIPTION     
            "Received MSU count, per second."
    ::= { ptMTPATMLinkEntry 16 }

ptMTPATMLinkTxMSUCount OBJECT-TYPE
    SYNTAX          Integer32 (-2147483648..2147483647)
    MAX-ACCESS      read-only
    STATUS          current
    DESCRIPTION     
            "Transmitted MSU count, per second."
    ::= { ptMTPATMLinkEntry 17 }

ptMTPATMLinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPATMLinkEntry 242 }

ptMTPATMLinkMTP3NAIndex OBJECT-TYPE
    SYNTAX          Integer32 (-2147483648..2147483647)
    MAX-ACCESS      not-accessible
    STATUS          current
    DESCRIPTION     
            "This is the index of the parent type for this object.
             This parent type is MTP3NA."
    ::= { ptMTPATMLinkEntry 243 }

ptMTPATMLinkLinksetsIndex OBJECT-TYPE
    SYNTAX          Integer32 (-2147483648..2147483647)
    MAX-ACCESS      not-accessible
    STATUS          current
    DESCRIPTION     
            "This is the index of the parent type for this object.
             This parent type is Linksets."
    ::= { ptMTPATMLinkEntry 244 }

ptMTPATMLinkLinksetIndex OBJECT-TYPE
    SYNTAX          Integer32 (-2147483648..2147483647)
    MAX-ACCESS      not-accessible
    STATUS          current
    DESCRIPTION     
            "This is the index of the parent type for this object.
             This parent type is Linkset."
    ::= { ptMTPATMLinkEntry 245 }

ptMTPATMLinkActions OBJECT-TYPE
    SYNTAX          INTEGER { activate(1), deactivate(2), inhibit(3), 
                        uninhibit(4), reset(5) }
    MAX-ACCESS      read-create
    STATUS          current
    DESCRIPTION     
            "The OID of all possible actions for this instance"
    ::= { ptMTPATMLinkEntry 252 }

ptMTPATMLinkParentOID OBJECT-TYPE
    SYNTAX          OBJECT IDENTIFIER
    MAX-ACCESS      read-create
    STATUS          current
    DESCRIPTION     
            "The OID of the parent object for this instance"
    ::= { ptMTPATMLinkEntry 253 }

ptMTPATMLinkRowStatus OBJECT-TYPE
    SYNTAX          RowStatus
    MAX-ACCESS      read-create
    STATUS          current
    DESCRIPTION     
            "The row status for the MTPATMLink table"
    ::= { ptMTPATMLinkEntry 254 }

ptMTPATMLinkIndex OBJECT-TYPE
    SYNTAX          Integer32 (-2147483648..2147483647)
    MAX-ACCESS      not-accessible
    STATUS          current
    DESCRIPTION     
            "The row number for the MTPATMLink table"
    ::= { ptMTPATMLinkEntry 255 }

ptMTPAnnexALink OBJECT IDENTIFIER
    ::= { ptMTPLinkset 73 }

ptMTPAnnexALinkTable OBJECT-TYPE
    SYNTAX          SEQUENCE OF PtMTPAnnexALinkEntry
    MAX-ACCESS      not-accessible
    STATUS          current
    DESCRIPTION     
            "A sequence of Link attributes."
    ::= { ptMTPAnnexALink 1 }

ptMTPAnnexALinkEntry OBJECT-TYPE
    SYNTAX          PtMTPAnnexALinkEntry
    MAX-ACCESS      not-accessible
    STATUS          current
    DESCRIPTION     
            "A sequence of MTPAnnexALink attributes."
    INDEX           { ptConnGroupIndex, 
                      ptMTPAnnexALinkMTP3NAManagerIndex, 
                      ptMTPAnnexALinkMTP3NAIndex, 
                      ptMTPAnnexALinkLinksetsIndex, 
                      ptMTPAnnexALinkLinksetIndex, ptMTPAnnexALinkIndex }
    ::= { ptMTPAnnexALinkTable 1 }

PtMTPAnnexALinkEntry ::=
    SEQUENCE {
        ptMTPAnnexALinkContext          DisplayString,
        ptMTPAnnexALinkAPC              Integer32,
        ptMTPAnnexALinkSLC              Integer32,
        ptMTPAnnexALinkDREID            Integer32,
        ptMTPAnnexALinkCage             Integer32,
        ptMTPAnnexALinkChassisSlot      Integer32,
        ptMTPAnnexALinkChannel          Integer32,
        ptMTPAnnexALinkL2State          INTEGER,
        ptMTPAnnexALinkL3State          INTEGER,
        ptMTPAnnexALinkCongestionLevel  INTEGER,
        ptMTPAnnexALinkDiagnosticMessage DisplayString,
        ptMTPAnnexALinkL2DebugLevel     Integer32,
        ptMTPAnnexALinkUserActivated    INTEGER,
        ptMTPAnnexALinkLinkName         DisplayString,
        ptMTPAnnexALinkAlarms           INTEGER,
        ptMTPAnnexALinkRxMSUCount       Integer32,
        ptMTPAnnexALinkTxMSUCount       Integer32,
        ptMTPAnnexALinkMTP3NAManagerIndex Integer32,
        ptMTPAnnexALinkMTP3NAIndex      Integer32,
        ptMTPAnnexALinkLinksetsIndex    Integer32,
        ptMTPAnnexALinkLinksetIndex     Integer32,
        ptMTPAnnexALinkActions          INTEGER,
        ptMTPAnnexALinkParentOID        OBJECT IDENTIFIER,
        ptMTPAnnexALinkRowStatus        RowStatus,
        ptMTPAnnexALinkIndex            Integer32
    }

ptMTPAnnexALinkContext OBJECT-TYPE
    SYNTAX          DisplayString (SIZE(0..255))
    MAX-ACCESS      read-only
    STATUS          current
    DESCRIPTION     
            "A condensed textual representation of the link object."
    ::= { ptMTPAnnexALinkEntry 1 }

ptMTPAnnexALinkAPC OBJECT-TYPE
    SYNTAX          Integer32 (-2147483648..2147483647)
    MAX-ACCESS      read-only
    STATUS          current
    DESCRIPTION     
            "Adjacent SS7 point code of this link."
    ::= { ptMTPAnnexALinkEntry 2 }

ptMTPAnnexALinkSLC OBJECT-TYPE
    SYNTAX          Integer32 (0..15)
    MAX-ACCESS      read-only
    STATUS          current
    DESCRIPTION     
            "Signaling Link Code for this link. Value of 0-15"
    ::= { ptMTPAnnexALinkEntry 3 }

ptMTPAnnexALinkDREID OBJECT-TYPE
    SYNTAX          Integer32 (-2147483648..2147483647)
    MAX-ACCESS      read-only
    STATUS          current
    DESCRIPTION     
            "DRE to own this link."
    ::= { ptMTPAnnexALinkEntry 4 }

ptMTPAnnexALinkCage OBJECT-TYPE
    SYNTAX          Integer32 (-1..64)
    MAX-ACCESS      read-create
    STATUS          current
    DESCRIPTION     
            "Cage used by this link"
    ::= { ptMTPAnnexALinkEntry 5 }

ptMTPAnnexALinkChassisSlot OBJECT-TYPE
    SYNTAX          Integer32 (-1..255)
    MAX-ACCESS      read-create
    STATUS          current
    DESCRIPTION     
            "Chassis Slot used by this link"
    ::= { ptMTPAnnexALinkEntry 6 }

ptMTPAnnexALinkChannel OBJECT-TYPE
    SYNTAX          Integer32 (-1 | 1..65535)
    MAX-ACCESS      read-create
    STATUS          current
    DESCRIPTION     
            "Channel used by this link"
    ::= { ptMTPAnnexALinkEntry 7 }

ptMTPAnnexALinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of MTP Level 2 for this link. Deactivated, Proving, In-Service, Out of Service, Failed, Local Processor Outage, Remote Processor Outage, Both Processor Outage, Local Loopback mode, Not Enabled, Not Initialized"
    ::= { ptMTPAnnexALinkEntry 8 }

ptMTPAnnexALinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out of Service, Locally Inhibited, Remotely Inhibited, Both Inhibited, Blocked, Blocked and Uninhibited, Local Processor Outage"
    ::= { ptMTPAnnexALinkEntry 9 }

ptMTPAnnexALinkCongestionLevel OBJECT-TYPE
    SYNTAX          INTEGER { false(0), level1(1), level2(2), level3(3), 
                        true(4) }
    MAX-ACCESS      read-only
    STATUS          current
    DESCRIPTION     
            "Congestion level of this link. \n For ANSI networks the values range from 1 to 3 or FALSE if not congested. \n For ITU networks the value is either TRUE or FALSE."
    ::= { ptMTPAnnexALinkEntry 10 }

ptMTPAnnexALinkDiagnosticMessage OBJECT-TYPE
    SYNTAX          DisplayString (SIZE(0..255))
    MAX-ACCESS      read-only
    STATUS          current
    DESCRIPTION     
            "Link management diagnostic message"
    ::= { ptMTPAnnexALinkEntry 11 }

ptMTPAnnexALinkL2DebugLevel OBJECT-TYPE
    SYNTAX          Integer32 (0..3)
    MAX-ACCESS      read-create
    STATUS          current
    DESCRIPTION     
            "MTP Level 2 Debug Level. \nThe recommended value for this attribute is 0."
    ::= { ptMTPAnnexALinkEntry 12 }

ptMTPAnnexALinkUserActivated OBJECT-TYPE
    SYNTAX          INTEGER { disabled(0), enabled(1) }
    MAX-ACCESS      read-only
    STATUS          current
    DESCRIPTION     
            "Link activation flag. Used on stack restart for alignment attempt."
    ::= { ptMTPAnnexALinkEntry 13 }

ptMTPAnnexALinkLinkName OBJECT-TYPE
    SYNTAX          DisplayString (SIZE(0..255))
    MAX-ACCESS      read-only
    STATUS          current
    DESCRIPTION     
            "Link Name based on the Linkset Name."
    ::= { ptMTPAnnexALinkEntry 14 }

ptMTPAnnexALinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPAnnexALinkEntry 15 }

ptMTPAnnexALinkRxMSUCount OBJECT-TYPE
    SYNTAX          Integer32 (-2147483648..2147483647)
    MAX-ACCESS      read-only
    STATUS          current
    DESCRIPTION     
            "Received MSU count, per second."
    ::= { ptMTPAnnexALinkEntry 16 }

ptMTPAnnexALinkTxMSUCount OBJECT-TYPE
    SYNTAX          Integer32 (-2147483648..2147483647)
    MAX-ACCESS      read-only
    STATUS          current
    DESCRIPTION     
            "Transmitted MSU count, per second."
    ::= { ptMTPAnnexALinkEntry 17 }

ptMTPAnnexALinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPAnnexALinkEntry 242 }

ptMTPAnnexALinkMTP3NAIndex OBJECT-TYPE
    SYNTAX          Integer32 (-2147483648..2147483647)
    MAX-ACCESS      not-accessible
    STATUS          current
    DESCRIPTION     
            "This is the index of the parent type for this object.
             This parent type is MTP3NA."
    ::= { ptMTPAnnexALinkEntry 243 }

ptMTPAnnexALinkLinksetsIndex OBJECT-TYPE
    SYNTAX          Integer32 (-2147483648..2147483647)
    MAX-ACCESS      not-accessible
    STATUS          current
    DESCRIPTION     
            "This is the index of the parent type for this object.
             This parent type is Linksets."
    ::= { ptMTPAnnexALinkEntry 244 }

ptMTPAnnexALinkLinksetIndex OBJECT-TYPE
    SYNTAX          Integer32 (-2147483648..2147483647)
    MAX-ACCESS      not-accessible
    STATUS          current
    DESCRIPTION     
            "This is the index of the parent type for this object.
             This parent type is Linkset."
    ::= { ptMTPAnnexALinkEntry 245 }

ptMTPAnnexALinkActions OBJECT-TYPE
    SYNTAX          INTEGER { activate(1), deactivate(2), setLPO(3), 
                        clearLPO(4), inhibit(5), uninhibit(6), reset(7) }
    MAX-ACCESS      read-create
    STATUS          current
    DESCRIPTION     
            "The OID of all possible actions for this instance"
    ::= { ptMTPAnnexALinkEntry 252 }

ptMTPAnnexALinkParentOID OBJECT-TYPE
    SYNTAX          OBJECT IDENTIFIER
    MAX-ACCESS      read-create
    STATUS          current
    DESCRIPTION     
            "The OID of the parent object for this instance"
    ::= { ptMTPAnnexALinkEntry 253 }

ptMTPAnnexALinkRowStatus OBJECT-TYPE
    SYNTAX          RowStatus
    MAX-ACCESS      read-create
    STATUS          current
    DESCRIPTION     
            "The row status for the MTPAnnexALink table"
    ::= { ptMTPAnnexALinkEntry 254 }

ptMTPAnnexALinkIndex OBJECT-TYPE
    SYNTAX          Integer32 (-2147483648..2147483647)
    MAX-ACCESS      not-accessible
    STATUS          current
    DESCRIPTION     
            "The row number for the MTPAnnexALink table"
    ::= { ptMTPAnnexALinkEntry 255 }

ptMTPGenericLink OBJECT IDENTIFIER
    ::= { ptMTPLinkset 80 }

ptMTPGenericLinkTable OBJECT-TYPE
    SYNTAX          SEQUENCE OF PtMTPGenericLinkEntry
    MAX-ACCESS      not-accessible
    STATUS          current
    DESCRIPTION     
            "A sequence of Link attributes."
    ::= { ptMTPGenericLink 1 }

ptMTPGenericLinkEntry OBJECT-TYPE
    SYNTAX          PtMTPGenericLinkEntry
    MAX-ACCESS      not-accessible
    STATUS          current
    DESCRIPTION     
            "A sequence of MTPGenericLink attributes."
    INDEX           { ptConnGroupIndex, 
                      ptMTPGenericLinkMTP3NAManagerIndex, 
                      ptMTPGenericLinkMTP3NAIndex, 
                      ptMTPGenericLinkLinksetsIndex, 
                      ptMTPGenericLinkLinksetIndex, 
                      ptMTPGenericLinkIndex }
    ::= { ptMTPGenericLinkTable 1 }

PtMTPGenericLinkEntry ::=
    SEQUENCE {
        ptMTPGenericLinkContext         DisplayString,
        ptMTPGenericLinkSLC             Integer32,
        ptMTPGenericLinkDREID           Integer32,
        ptMTPGenericLinkLocalIPAddress1 DisplayString,
        ptMTPGenericLinkLocalIPAddress2 DisplayString,
        ptMTPGenericLinkLocalPort       Integer32,
        ptMTPGenericLinkRemoteIPAddress1 DisplayString,
        ptMTPGenericLinkRemoteIPAddress2 DisplayString,
        ptMTPGenericLinkRemotePort      Integer32,
        ptMTPGenericLinkL2State         INTEGER,
        ptMTPGenericLinkL3State         INTEGER,
        ptMTPGenericLinkDiagnosticMessage DisplayString,
        ptMTPGenericLinkDataDebugLevel  Integer32,
        ptMTPGenericLinkSoftwareDebugLevel  Integer32,
        ptMTPGenericLinkSCTPDebugLevel  Integer32,
        ptMTPGenericLinkUserActivated   INTEGER,
        ptMTPGenericLinkLinksetSCTPValues INTEGER,
        ptMTPGenericLinkHeartbeat       INTEGER,
        ptMTPGenericLinkHeartbeatInterval Integer32,
        ptMTPGenericLinkRTOInitial      Integer32,
        ptMTPGenericLinkRTOMinimum      Integer32,
        ptMTPGenericLinkRTOMaximum      Integer32,
        ptMTPGenericLinkMaximumPathRetrans  Integer32,
        ptMTPGenericLinkMaximumAssocRetrans   Integer32,
        ptMTPGenericLinkBundling        INTEGER,
        ptMTPGenericLinkBundlingTO      Integer32,
        ptMTPGenericLinkDelayedACKTO    Integer32,
        ptMTPGenericLinkFastRetransThreshold    Integer32,
        ptMTPGenericLinkChecksum        INTEGER,
        ptMTPGenericLinkDataLinkBandwidth Integer32,
        ptMTPGenericLinkAlarms          INTEGER,
        ptMTPGenericLinkNetworkAppearance INTEGER,
        ptMTPGenericLinkRoutingContext  INTEGER,
        ptMTPGenericLinkInStreams       Integer32,
        ptMTPGenericLinkOutStreams      Integer32,
        ptMTPGenericLinkLinkType        INTEGER,
        ptMTPGenericLinkRxMSUCount      Integer32,
        ptMTPGenericLinkTxMSUCount      Integer32,
        ptMTPGenericLinkMTP3NAManagerIndex  Integer32,
        ptMTPGenericLinkMTP3NAIndex     Integer32,
        ptMTPGenericLinkLinksetsIndex   Integer32,
        ptMTPGenericLinkLinksetIndex    Integer32,
        ptMTPGenericLinkActions         INTEGER,
        ptMTPGenericLinkParentOID       OBJECT IDENTIFIER,
        ptMTPGenericLinkRowStatus       RowStatus,
        ptMTPGenericLinkIndex           Integer32
    }

ptMTPGenericLinkContext OBJECT-TYPE
    SYNTAX          DisplayString (SIZE(0..255))
    MAX-ACCESS      read-only
    STATUS          current
    DESCRIPTION     
            "A condensed textual representation of the link object."
    ::= { ptMTPGenericLinkEntry 1 }

ptMTPGenericLinkSLC OBJECT-TYPE
    SYNTAX          Integer32 (0..15)
    MAX-ACCESS      read-only
    STATUS          current
    DESCRIPTION     
            "Signaling Link Code for this link. Value of 0-15."
    ::= { ptMTPGenericLinkEntry 3 }

ptMTPGenericLinkDREID OBJECT-TYPE
    SYNTAX          Integer32 (1..64)
    MAX-ACCESS      read-only
    STATUS          current
    DESCRIPTION     
            "DRE ID of the DRE that owns this link. Since the corresponding DRE process runs on a specific slot, this ID implies the slot where the link terminates locally, and hence the choice of valid local IP addresses for this link."
    ::= { ptMTPGenericLinkEntry 4 }

ptMTPGenericLinkLocalIPAddress1 OBJECT-TYPE
    SYNTAX          DisplayString (SIZE(0..255))
    MAX-ACCESS      read-create
    STATUS          current
    DESCRIPTION     
            "Primary local address. This may be a hostname or an IP Address. If a hostname is used it must be provisioned in /etc/hosts and should resolve to a subset of the local IP Addresses configured for the slot where the link terminates. The slot where the link terminates is indirectly implied by the DRE ID."
    ::= { ptMTPGenericLinkEntry 5 }

ptMTPGenericLinkLocalIPAddress2 OBJECT-TYPE
    SYNTAX          DisplayString (SIZE(0..255))
    MAX-ACCESS      read-create
    STATUS          current
    DESCRIPTION     
            "Secondary local address. This may be a hostname or an IP Address. If a hostname is used it must be provisioned in /etc/hosts and should resolve to a subset of the local IP Addresses configured for the slot where the link terminates. The slot where the link terminates is indirectly implied by the DRE ID."
    ::= { ptMTPGenericLinkEntry 6 }

ptMTPGenericLinkLocalPort OBJECT-TYPE
    SYNTAX          Integer32 (0..65535)
    MAX-ACCESS      read-create
    STATUS          current
    DESCRIPTION     
            "Local Port."
    ::= { ptMTPGenericLinkEntry 7 }

ptMTPGenericLinkRemoteIPAddress1 OBJECT-TYPE
    SYNTAX          DisplayString (SIZE(0..255))
    MAX-ACCESS      read-create
    STATUS          current
    DESCRIPTION     
            "Primary remote address. This may be a hostname or an IP Address. If a hostname is used it must be provisioned in /etc/hosts. This value is used as the SCTP Primary path to the remote SCTP endpoint."
    ::= { ptMTPGenericLinkEntry 8 }

ptMTPGenericLinkRemoteIPAddress2 OBJECT-TYPE
    SYNTAX          DisplayString (SIZE(0..255))
    MAX-ACCESS      read-create
    STATUS          current
    DESCRIPTION     
            "Secondary remote address. This may be a hostname or an IP Address. If a hostname is used it must be provisioned in /etc/hosts."
    ::= { ptMTPGenericLinkEntry 9 }

ptMTPGenericLinkRemotePort OBJECT-TYPE
    SYNTAX          Integer32 (0..65535)
    MAX-ACCESS      read-create
    STATUS          current
    DESCRIPTION     
            "Remote Port."
    ::= { ptMTPGenericLinkEntry 10 }

ptMTPGenericLinkL2State OBJECT-TYPE
    SYNTAX          INTEGER { deactivated(0), proving(1), inService(2), 
                        outOfService(3), failed(4), localProcOutage(5), 
                        remProcOutage(6), boProcOutage(7), 
                        localLoopback(8), notEnabled(9), 
                        notInitialized(10), userShutdown(11) }
    MAX-ACCESS      read-only
    STATUS          current
    DESCRIPTION     
            "Status of this link. Deactivated, Proving, In-Service, Out-of-service, Failed, Local Processor Outage, Remote Processor Outage, Both Processor Outage, Local Loopback mode, Not Enabled Not Initialized"
    ::= { ptMTPGenericLinkEntry 11 }

ptMTPGenericLinkL3State OBJECT-TYPE
    SYNTAX          INTEGER { deactivated(0), proving(1), inService(2), 
                        outOfService(3), locallyInhibited(4), 
                        remInhibited(5), bothInhibited(6), blocked(7), 
                        blockedInhibited(8), localProcOutage(9) }
    MAX-ACCESS      read-only
    STATUS          current
    DESCRIPTION     
            "Status of MTP Level 3 for this link. Deactivated, Proving, In-Service, Out-of-Service, Locally Inhibited, Remotely Inhibited, Both Inhibited, Blocked, Blocked and Uninhibited, Local Processor Outage."
    ::= { ptMTPGenericLinkEntry 12 }

ptMTPGenericLinkDiagnosticMessage OBJECT-TYPE
    SYNTAX          DisplayString (SIZE(0..255))
    MAX-ACCESS      read-only
    STATUS          current
    DESCRIPTION     
            "Link management diagnostic message."
    ::= { ptMTPGenericLinkEntry 14 }

ptMTPGenericLinkDataDebugLevel OBJECT-TYPE
    SYNTAX          Integer32 (0..255)
    MAX-ACCESS      read-create
    STATUS          current
    DESCRIPTION     
            "Data Debug Level \n\nAmount of information displayed concerning MSU transfers. Higher is more information, 0 is DISABLED. \nThe recommended value for this attribute is 1."
    ::= { ptMTPGenericLinkEntry 15 }

ptMTPGenericLinkSoftwareDebugLevel OBJECT-TYPE
    SYNTAX          Integer32 (0..255)
    MAX-ACCESS      read-create
    STATUS          current
    DESCRIPTION     
            "Software Debug Level \n\nIndicates how much information to display concerning the internals of the software. A value of 0 indicates no software related information is to be displayed, 1 shows only errors, more than 1 shows more detail. \nThe recommended value for this attribute is 1."
    ::= { ptMTPGenericLinkEntry 17 }

ptMTPGenericLinkSCTPDebugLevel OBJECT-TYPE
    SYNTAX          Integer32 (0..255)
    MAX-ACCESS      read-create
    STATUS          current
    DESCRIPTION     
            "Debug: SCTP debug level for association debugging. \nThe recommended value for this attribute is 1."
    ::= { ptMTPGenericLinkEntry 18 }

ptMTPGenericLinkUserActivated OBJECT-TYPE
    SYNTAX          INTEGER { disabled(0), enabled(1) }
    MAX-ACCESS      read-only
    STATUS          current
    DESCRIPTION     
            "Link activation flag. Used on stack restart for alignment attempt. Only affected by link activation/deactivation."
    ::= { ptMTPGenericLinkEntry 19 }

ptMTPGenericLinkLinksetSCTPValues OBJECT-TYPE
    SYNTAX          INTEGER { no(0), yes(1) }
    MAX-ACCESS      read-create
    STATUS          current
    DESCRIPTION     
            "When this is set, the link uses the Linkset SCTP values. In that case, the SCTP parameters may not be modified at the Link level."
    ::= { ptMTPGenericLinkEntry 29 }

ptMTPGenericLinkHeartbeat OBJECT-TYPE
    SYNTAX          INTEGER { disabled(0), enabled(1) }
    MAX-ACCESS      read-create
    STATUS          current
    DESCRIPTION     
            "On / Off Heartbeat Feature"
    ::= { ptMTPGenericLinkEntry 30 }

ptMTPGenericLinkHeartbeatInterval OBJECT-TYPE
    SYNTAX          Integer32 (0..65535)
    MAX-ACCESS      read-create
    STATUS          current
    DESCRIPTION     
            "Heartbeat interval (ms)"
    ::= { ptMTPGenericLinkEntry 31 }

ptMTPGenericLinkRTOInitial OBJECT-TYPE
    SYNTAX          Integer32 (0..2147483647)
    MAX-ACCESS      read-create
    STATUS          current
    DESCRIPTION     
            "RTO Initial (ms)"
    ::= { ptMTPGenericLinkEntry 32 }

ptMTPGenericLinkRTOMinimum OBJECT-TYPE
    SYNTAX          Integer32 (0..2147483647)
    MAX-ACCESS      read-create
    STATUS          current
    DESCRIPTION     
            "RTO Minimum (ms)"
    ::= { ptMTPGenericLinkEntry 33 }

ptMTPGenericLinkRTOMaximum OBJECT-TYPE
    SYNTAX          Integer32 (0..2147483647)
    MAX-ACCESS      read-create
    STATUS          current
    DESCRIPTION     
            "RTO Maximum (ms)"
    ::= { ptMTPGenericLinkEntry 34 }

ptMTPGenericLinkMaximumPathRetrans OBJECT-TYPE
    SYNTAX          Integer32 (0..2147483647)
    MAX-ACCESS      read-create
    STATUS          current
    DESCRIPTION     
            "Maximum path retransmissions"
    ::= { ptMTPGenericLinkEntry 35 }

ptMTPGenericLinkMaximumAssocRetrans OBJECT-TYPE
    SYNTAX          Integer32 (0..2147483647)
    MAX-ACCESS      read-create
    STATUS          current
    DESCRIPTION     
            "Maximum association retransmissions"
    ::= { ptMTPGenericLinkEntry 36 }

ptMTPGenericLinkBundling OBJECT-TYPE
    SYNTAX          INTEGER { disabled(0), enabled(1) }
    MAX-ACCESS      read-create
    STATUS          current
    DESCRIPTION     
            "Bundling On / Off"
    ::= { ptMTPGenericLinkEntry 37 }

ptMTPGenericLinkBundlingTO OBJECT-TYPE
    SYNTAX          Integer32 (0..2147483647)
    MAX-ACCESS      read-create
    STATUS          current
    DESCRIPTION     
            "Bundling TO (ms)"
    ::= { ptMTPGenericLinkEntry 38 }

ptMTPGenericLinkDelayedACKTO OBJECT-TYPE
    SYNTAX          Integer32 (0..2147483647)
    MAX-ACCESS      read-create
    STATUS          current
    DESCRIPTION     
            "Delayed ACK TO (ms)"
    ::= { ptMTPGenericLinkEntry 39 }

ptMTPGenericLinkFastRetransThreshold OBJECT-TYPE
    SYNTAX          Integer32 (0..2147483647)
    MAX-ACCESS      read-create
    STATUS          current
    DESCRIPTION     
            "Fast Retransmit Threshold"
    ::= { ptMTPGenericLinkEntry 40 }

ptMTPGenericLinkChecksum OBJECT-TYPE
    SYNTAX          INTEGER { crc32c(0), adler32(1), none(2), auto(3) }
    MAX-ACCESS      read-only
    STATUS          current
    DESCRIPTION     
            "SCTP Checksum"
    ::= { ptMTPGenericLinkEntry 41 }

ptMTPGenericLinkDataLinkBandwidth OBJECT-TYPE
    SYNTAX          Integer32 (1..2147483647)
    MAX-ACCESS      read-create
    STATUS          current
    DESCRIPTION     
            "Generic DataLink Baud Rate in kbps used to calculate Erlang "
    ::= { ptMTPGenericLinkEntry 43 }

ptMTPGenericLinkAlarms OBJECT-TYPE
    SYNTAX          INTEGER { disabled(0), enabled(1) }
    MAX-ACCESS      read-create
    STATUS          current
    DESCRIPTION     
            "Alarms affect the alarms associated with the Link. DISABLED mode: Alarms will not be raised. ENABLED mode: Alarms will be raised. \nValid values: ENABLED and DISABLED. \nDefault value: ENABLED."
    ::= { ptMTPGenericLinkEntry 44 }

ptMTPGenericLinkNetworkAppearance OBJECT-TYPE
    SYNTAX          INTEGER { unset(-1) }
    MAX-ACCESS      read-create
    STATUS          current
    DESCRIPTION     
            "The Network Appearance in the M3UA SG and M3UA Server links is used to populate the network appearance parameter in the outgoing M3UA Data and any outgoing SSNM messages. The NA parameter may be used by the receiving SGP or ASP. The NA should be UNSET (-1) when NA parameter inclusion is not required. The valid range for this parameter is 1 to 32,767"
    ::= { ptMTPGenericLinkEntry 45 }

ptMTPGenericLinkRoutingContext OBJECT-TYPE
    SYNTAX          INTEGER { unset(-1) }
    MAX-ACCESS      read-create
    STATUS          current
    DESCRIPTION     
            "The Routing Context in the M3UA Server link is used to populate the outgoing M3UA Data message routing context parameter. The RC parameter may be required by the ASP receiving the M3UA Data. It is an optional attribute which does not have to be configured. The RC should be UNSET (-1) when RC parameter inclusion is not required. Additionaly if the RC paramter is configured for a link then it is expected that if an M3UA ASP Active message is received on the link and the message contains an RC parameter then that RC will match the parameter configured for the link. If an M3UA ASP Active message is received on the link and the message contains multiple RC parameters then at least one RC must match the parameter configured for the link. In the case where the RC matches or an RC is not configured for the link then the RC in the M3UA ASP Active message is accepted regardless and responded to with an M3UA ASP Active Ack and the link will transition to in service at L3. The valid range for this parameter is 0 to 214,748,367."
    ::= { ptMTPGenericLinkEntry 46 }

ptMTPGenericLinkInStreams OBJECT-TYPE
    SYNTAX          Integer32 (0..65355)
    MAX-ACCESS      read-create
    STATUS          current
    DESCRIPTION     
            "Number of in streams."
    ::= { ptMTPGenericLinkEntry 48 }

ptMTPGenericLinkOutStreams OBJECT-TYPE
    SYNTAX          Integer32 (0..65355)
    MAX-ACCESS      read-create
    STATUS          current
    DESCRIPTION     
            "Number of out streams."
    ::= { ptMTPGenericLinkEntry 49 }

ptMTPGenericLinkLinkType OBJECT-TYPE
    SYNTAX          INTEGER { ipsp(50), m3uaMg(51), m3uaSg(52), 
                        m3uaServer(53) }
    MAX-ACCESS      read-only
    STATUS          current
    DESCRIPTION     
            "Link Type."
    ::= { ptMTPGenericLinkEntry 51 }

ptMTPGenericLinkRxMSUCount OBJECT-TYPE
    SYNTAX          Integer32 (-2147483648..2147483647)
    MAX-ACCESS      read-only
    STATUS          current
    DESCRIPTION     
            "Received MSU count, per second."
    ::= { ptMTPGenericLinkEntry 52 }

ptMTPGenericLinkTxMSUCount OBJECT-TYPE
    SYNTAX          Integer32 (-2147483648..2147483647)
    MAX-ACCESS      read-only
    STATUS          current
    DESCRIPTION     
            "Transmitted MSU count, per second."
    ::= { ptMTPGenericLinkEntry 53 }

ptMTPGenericLinkMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPGenericLinkEntry 242 }

ptMTPGenericLinkMTP3NAIndex OBJECT-TYPE
    SYNTAX          Integer32 (-2147483648..2147483647)
    MAX-ACCESS      not-accessible
    STATUS          current
    DESCRIPTION     
            "This is the index of the parent type for this object.
             This parent type is MTP3NA."
    ::= { ptMTPGenericLinkEntry 243 }

ptMTPGenericLinkLinksetsIndex OBJECT-TYPE
    SYNTAX          Integer32 (-2147483648..2147483647)
    MAX-ACCESS      not-accessible
    STATUS          current
    DESCRIPTION     
            "This is the index of the parent type for this object.
             This parent type is Linksets."
    ::= { ptMTPGenericLinkEntry 244 }

ptMTPGenericLinkLinksetIndex OBJECT-TYPE
    SYNTAX          Integer32 (-2147483648..2147483647)
    MAX-ACCESS      not-accessible
    STATUS          current
    DESCRIPTION     
            "This is the index of the parent type for this object.
             This parent type is Linkset."
    ::= { ptMTPGenericLinkEntry 245 }

ptMTPGenericLinkActions OBJECT-TYPE
    SYNTAX          INTEGER { activate(1), deactivate(2), shutdown(3) }
    MAX-ACCESS      read-create
    STATUS          current
    DESCRIPTION     
            "The OID of all possible actions for this instance"
    ::= { ptMTPGenericLinkEntry 252 }

ptMTPGenericLinkParentOID OBJECT-TYPE
    SYNTAX          OBJECT IDENTIFIER
    MAX-ACCESS      read-create
    STATUS          current
    DESCRIPTION     
            "The OID of the parent object for this instance"
    ::= { ptMTPGenericLinkEntry 253 }

ptMTPGenericLinkRowStatus OBJECT-TYPE
    SYNTAX          RowStatus
    MAX-ACCESS      read-create
    STATUS          current
    DESCRIPTION     
            "The row status for the MTPGenericLink table"
    ::= { ptMTPGenericLinkEntry 254 }

ptMTPGenericLinkIndex OBJECT-TYPE
    SYNTAX          Integer32 (-2147483648..2147483647)
    MAX-ACCESS      not-accessible
    STATUS          current
    DESCRIPTION     
            "The row number for the MTPGenericLink table"
    ::= { ptMTPGenericLinkEntry 255 }

ptMTPL4Connections OBJECT IDENTIFIER
    ::= { ptMTPMTP3NA 66 }

ptMTPL4ConnectionsTable OBJECT-TYPE
    SYNTAX          SEQUENCE OF PtMTPL4ConnectionsEntry
    MAX-ACCESS      not-accessible
    STATUS          current
    DESCRIPTION     
            "No description supplied in the proxy config file."
    ::= { ptMTPL4Connections 1 }

ptMTPL4ConnectionsEntry OBJECT-TYPE
    SYNTAX          PtMTPL4ConnectionsEntry
    MAX-ACCESS      not-accessible
    STATUS          current
    DESCRIPTION     
            "A sequence of MTPL4Connections attributes."
    INDEX           { ptConnGroupIndex, 
                      ptMTPL4ConnectionsMTP3NAManagerIndex, 
                      ptMTPL4ConnectionsMTP3NAIndex, 
                      ptMTPL4ConnectionsIndex }
    ::= { ptMTPL4ConnectionsTable 1 }

PtMTPL4ConnectionsEntry ::=
    SEQUENCE {
        ptMTPL4ConnectionsCount         Integer32,
        ptMTPL4ConnectionsMTP3NAManagerIndex    Integer32,
        ptMTPL4ConnectionsMTP3NAIndex   Integer32,
        ptMTPL4ConnectionsParentOID     OBJECT IDENTIFIER,
        ptMTPL4ConnectionsRowStatus     RowStatus,
        ptMTPL4ConnectionsIndex         Integer32
    }

ptMTPL4ConnectionsCount OBJECT-TYPE
    SYNTAX          Integer32 (-2147483648..2147483647)
    MAX-ACCESS      read-only
    STATUS          current
    DESCRIPTION     
            "Number of MTP L4 Connections"
    ::= { ptMTPL4ConnectionsEntry 1 }

ptMTPL4ConnectionsMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPL4ConnectionsEntry 242 }

ptMTPL4ConnectionsMTP3NAIndex OBJECT-TYPE
    SYNTAX          Integer32 (-2147483648..2147483647)
    MAX-ACCESS      not-accessible
    STATUS          current
    DESCRIPTION     
            "This is the index of the parent type for this object.
             This parent type is MTP3NA."
    ::= { ptMTPL4ConnectionsEntry 243 }

ptMTPL4ConnectionsParentOID OBJECT-TYPE
    SYNTAX          OBJECT IDENTIFIER
    MAX-ACCESS      read-create
    STATUS          current
    DESCRIPTION     
            "The OID of the parent object for this instance"
    ::= { ptMTPL4ConnectionsEntry 253 }

ptMTPL4ConnectionsRowStatus OBJECT-TYPE
    SYNTAX          RowStatus
    MAX-ACCESS      read-create
    STATUS          current
    DESCRIPTION     
            "The row status for the MTPL4Connections table"
    ::= { ptMTPL4ConnectionsEntry 254 }

ptMTPL4ConnectionsIndex OBJECT-TYPE
    SYNTAX          Integer32 (-2147483648..2147483647)
    MAX-ACCESS      not-accessible
    STATUS          current
    DESCRIPTION     
            "The row number for the MTPL4Connections table"
    ::= { ptMTPL4ConnectionsEntry 255 }

ptMTPL4Connection OBJECT IDENTIFIER
    ::= { ptMTPL4Connections 59 }

ptMTPL4ConnectionTable OBJECT-TYPE
    SYNTAX          SEQUENCE OF PtMTPL4ConnectionEntry
    MAX-ACCESS      not-accessible
    STATUS          current
    DESCRIPTION     
            "A sequence of L4 connection attributes. These values are not 
             saved in the configuration file."
    ::= { ptMTPL4Connection 1 }

ptMTPL4ConnectionEntry OBJECT-TYPE
    SYNTAX          PtMTPL4ConnectionEntry
    MAX-ACCESS      not-accessible
    STATUS          current
    DESCRIPTION     
            "A sequence of MTPL4Connection attributes."
    INDEX           { ptConnGroupIndex, 
                      ptMTPL4ConnectionMTP3NAManagerIndex, 
                      ptMTPL4ConnectionMTP3NAIndex, 
                      ptMTPL4ConnectionL4ConnectionsIndex, 
                      ptMTPL4ConnectionIndex }
    ::= { ptMTPL4ConnectionTable 1 }

PtMTPL4ConnectionEntry ::=
    SEQUENCE {
        ptMTPL4ConnectionContext        DisplayString,
        ptMTPL4ConnectionIPAddress      DisplayString,
        ptMTPL4ConnectionDREID          Integer32,
        ptMTPL4ConnectionNumberOfUPs    Integer32,
        ptMTPL4ConnectionUAPVersion     Integer32,
        ptMTPL4ConnectionNumberOfAppIDs Integer32,
        ptMTPL4ConnectionPort           Integer32,
        ptMTPL4ConnectionMTP3NAManagerIndex   Integer32,
        ptMTPL4ConnectionMTP3NAIndex    Integer32,
        ptMTPL4ConnectionL4ConnectionsIndex   Integer32,
        ptMTPL4ConnectionActions        INTEGER,
        ptMTPL4ConnectionParentOID      OBJECT IDENTIFIER,
        ptMTPL4ConnectionRowStatus      RowStatus,
        ptMTPL4ConnectionIndex          Integer32
    }

ptMTPL4ConnectionContext OBJECT-TYPE
    SYNTAX          DisplayString (SIZE(0..255))
    MAX-ACCESS      read-only
    STATUS          current
    DESCRIPTION     
            "A condensed textual representation of the L4 connection object."
    ::= { ptMTPL4ConnectionEntry 1 }

ptMTPL4ConnectionIPAddress OBJECT-TYPE
    SYNTAX          DisplayString (SIZE(0..255))
    MAX-ACCESS      read-only
    STATUS          current
    DESCRIPTION     
            "IP Address of the L4 connection"
    ::= { ptMTPL4ConnectionEntry 2 }

ptMTPL4ConnectionDREID OBJECT-TYPE
    SYNTAX          Integer32 (1..64)
    MAX-ACCESS      read-only
    STATUS          current
    DESCRIPTION     
            "DRE ID of owner"
    ::= { ptMTPL4ConnectionEntry 3 }

ptMTPL4ConnectionNumberOfUPs OBJECT-TYPE
    SYNTAX          Integer32 (-2147483648..2147483647)
    MAX-ACCESS      read-only
    STATUS          current
    DESCRIPTION     
            "Number of User Parts associated with this L4 connection"
    ::= { ptMTPL4ConnectionEntry 4 }

ptMTPL4ConnectionUAPVersion OBJECT-TYPE
    SYNTAX          Integer32 (1..2147483647)
    MAX-ACCESS      read-only
    STATUS          current
    DESCRIPTION     
            "The MTP UAP Protocol version advertised by the remote application."
    ::= { ptMTPL4ConnectionEntry 5 }

ptMTPL4ConnectionNumberOfAppIDs OBJECT-TYPE
    SYNTAX          Integer32 (-2147483648..2147483647)
    MAX-ACCESS      read-only
    STATUS          current
    DESCRIPTION     
            "Number of AppIDs associated with this L4 connection"
    ::= { ptMTPL4ConnectionEntry 6 }

ptMTPL4ConnectionPort OBJECT-TYPE
    SYNTAX          Integer32 (-2147483648..2147483647)
    MAX-ACCESS      read-only
    STATUS          current
    DESCRIPTION     
            "Port of the L4 connection"
    ::= { ptMTPL4ConnectionEntry 7 }

ptMTPL4ConnectionMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPL4ConnectionEntry 242 }

ptMTPL4ConnectionMTP3NAIndex OBJECT-TYPE
    SYNTAX          Integer32 (-2147483648..2147483647)
    MAX-ACCESS      not-accessible
    STATUS          current
    DESCRIPTION     
            "This is the index of the parent type for this object.
             This parent type is MTP3NA."
    ::= { ptMTPL4ConnectionEntry 243 }

ptMTPL4ConnectionL4ConnectionsIndex OBJECT-TYPE
    SYNTAX          Integer32 (-2147483648..2147483647)
    MAX-ACCESS      not-accessible
    STATUS          current
    DESCRIPTION     
            "This is the index of the parent type for this object.
             This parent type is L4Connections."
    ::= { ptMTPL4ConnectionEntry 244 }

ptMTPL4ConnectionActions OBJECT-TYPE
    SYNTAX          INTEGER { terminate(1) }
    MAX-ACCESS      read-create
    STATUS          current
    DESCRIPTION     
            "The OID of all possible actions for this instance"
    ::= { ptMTPL4ConnectionEntry 252 }

ptMTPL4ConnectionParentOID OBJECT-TYPE
    SYNTAX          OBJECT IDENTIFIER
    MAX-ACCESS      read-create
    STATUS          current
    DESCRIPTION     
            "The OID of the parent object for this instance"
    ::= { ptMTPL4ConnectionEntry 253 }

ptMTPL4ConnectionRowStatus OBJECT-TYPE
    SYNTAX          RowStatus
    MAX-ACCESS      read-create
    STATUS          current
    DESCRIPTION     
            "The row status for the MTPL4Connection table"
    ::= { ptMTPL4ConnectionEntry 254 }

ptMTPL4ConnectionIndex OBJECT-TYPE
    SYNTAX          Integer32 (-2147483648..2147483647)
    MAX-ACCESS      not-accessible
    STATUS          current
    DESCRIPTION     
            "The row number for the MTPL4Connection table"
    ::= { ptMTPL4ConnectionEntry 255 }

ptMTPRegisteredUP OBJECT IDENTIFIER
    ::= { ptMTPL4Connection 60 }

ptMTPRegisteredUPTable OBJECT-TYPE
    SYNTAX          SEQUENCE OF PtMTPRegisteredUPEntry
    MAX-ACCESS      not-accessible
    STATUS          current
    DESCRIPTION     
            "A sequence of registered user part attributes. These values 
             are not saved in the configuration file."
    ::= { ptMTPRegisteredUP 1 }

ptMTPRegisteredUPEntry OBJECT-TYPE
    SYNTAX          PtMTPRegisteredUPEntry
    MAX-ACCESS      not-accessible
    STATUS          current
    DESCRIPTION     
            "A sequence of MTPRegisteredUP attributes."
    INDEX           { ptConnGroupIndex, 
                      ptMTPRegisteredUPMTP3NAManagerIndex, 
                      ptMTPRegisteredUPMTP3NAIndex, 
                      ptMTPRegisteredUPL4ConnectionsIndex, 
                      ptMTPRegisteredUPL4ConnectionIndex, 
                      ptMTPRegisteredUPIndex }
    ::= { ptMTPRegisteredUPTable 1 }

PtMTPRegisteredUPEntry ::=
    SEQUENCE {
        ptMTPRegisteredUPContext        DisplayString,
        ptMTPRegisteredUPName           DisplayString,
        ptMTPRegisteredUPPointCode      Integer32,
        ptMTPRegisteredUPSI             Integer32,
        ptMTPRegisteredUPLongMSUSupport INTEGER,
        ptMTPRegisteredUPMTP3NAManagerIndex   Integer32,
        ptMTPRegisteredUPMTP3NAIndex    Integer32,
        ptMTPRegisteredUPL4ConnectionsIndex   Integer32,
        ptMTPRegisteredUPL4ConnectionIndex  Integer32,
        ptMTPRegisteredUPParentOID      OBJECT IDENTIFIER,
        ptMTPRegisteredUPRowStatus      RowStatus,
        ptMTPRegisteredUPIndex          Integer32
    }

ptMTPRegisteredUPContext OBJECT-TYPE
    SYNTAX          DisplayString (SIZE(0..255))
    MAX-ACCESS      read-only
    STATUS          current
    DESCRIPTION     
            "A condensed textual representation of the registered user part object."
    ::= { ptMTPRegisteredUPEntry 1 }

ptMTPRegisteredUPName OBJECT-TYPE
    SYNTAX          DisplayString (SIZE(0..255))
    MAX-ACCESS      read-only
    STATUS          current
    DESCRIPTION     
            "Registered User part name as per MTP registration message"
    ::= { ptMTPRegisteredUPEntry 2 }

ptMTPRegisteredUPPointCode OBJECT-TYPE
    SYNTAX          Integer32 (-2147483648..2147483647)
    MAX-ACCESS      read-only
    STATUS          current
    DESCRIPTION     
            "Registered point code of the user part"
    ::= { ptMTPRegisteredUPEntry 3 }

ptMTPRegisteredUPSI OBJECT-TYPE
    SYNTAX          Integer32 (0..15)
    MAX-ACCESS      read-only
    STATUS          current
    DESCRIPTION     
            "Registered Signaling Indicator (SI) of the user part"
    ::= { ptMTPRegisteredUPEntry 4 }

ptMTPRegisteredUPLongMSUSupport OBJECT-TYPE
    SYNTAX          INTEGER { disabled(0), enabled(1) }
    MAX-ACCESS      read-only
    STATUS          current
    DESCRIPTION     
            "Registered Long MSU support for the user part"
    ::= { ptMTPRegisteredUPEntry 5 }

ptMTPRegisteredUPMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPRegisteredUPEntry 242 }

ptMTPRegisteredUPMTP3NAIndex OBJECT-TYPE
    SYNTAX          Integer32 (-2147483648..2147483647)
    MAX-ACCESS      not-accessible
    STATUS          current
    DESCRIPTION     
            "This is the index of the parent type for this object.
             This parent type is MTP3NA."
    ::= { ptMTPRegisteredUPEntry 243 }

ptMTPRegisteredUPL4ConnectionsIndex OBJECT-TYPE
    SYNTAX          Integer32 (-2147483648..2147483647)
    MAX-ACCESS      not-accessible
    STATUS          current
    DESCRIPTION     
            "This is the index of the parent type for this object.
             This parent type is L4Connections."
    ::= { ptMTPRegisteredUPEntry 244 }

ptMTPRegisteredUPL4ConnectionIndex OBJECT-TYPE
    SYNTAX          Integer32 (-2147483648..2147483647)
    MAX-ACCESS      not-accessible
    STATUS          current
    DESCRIPTION     
            "This is the index of the parent type for this object.
             This parent type is L4Connection."
    ::= { ptMTPRegisteredUPEntry 245 }

ptMTPRegisteredUPParentOID OBJECT-TYPE
    SYNTAX          OBJECT IDENTIFIER
    MAX-ACCESS      read-create
    STATUS          current
    DESCRIPTION     
            "The OID of the parent object for this instance"
    ::= { ptMTPRegisteredUPEntry 253 }

ptMTPRegisteredUPRowStatus OBJECT-TYPE
    SYNTAX          RowStatus
    MAX-ACCESS      read-create
    STATUS          current
    DESCRIPTION     
            "The row status for the MTPRegisteredUP table"
    ::= { ptMTPRegisteredUPEntry 254 }

ptMTPRegisteredUPIndex OBJECT-TYPE
    SYNTAX          Integer32 (-2147483648..2147483647)
    MAX-ACCESS      not-accessible
    STATUS          current
    DESCRIPTION     
            "The row number for the MTPRegisteredUP table"
    ::= { ptMTPRegisteredUPEntry 255 }

ptMTPRegisteredAppID OBJECT IDENTIFIER
    ::= { ptMTPL4Connection 74 }

ptMTPRegisteredAppIDTable OBJECT-TYPE
    SYNTAX          SEQUENCE OF PtMTPRegisteredAppIDEntry
    MAX-ACCESS      not-accessible
    STATUS          current
    DESCRIPTION     
            "A sequence of registered application ID attributes. These values 
             are not saved in the configuration file."
    ::= { ptMTPRegisteredAppID 1 }

ptMTPRegisteredAppIDEntry OBJECT-TYPE
    SYNTAX          PtMTPRegisteredAppIDEntry
    MAX-ACCESS      not-accessible
    STATUS          current
    DESCRIPTION     
            "A sequence of MTPRegisteredAppID attributes."
    INDEX           { ptConnGroupIndex, 
                      ptMTPRegisteredAppIDMTP3NAManagerIndex, 
                      ptMTPRegisteredAppIDMTP3NAIndex, 
                      ptMTPRegisteredAppIDL4ConnectionsIndex, 
                      ptMTPRegisteredAppIDL4ConnectionIndex, 
                      ptMTPRegisteredAppIDIndex }
    ::= { ptMTPRegisteredAppIDTable 1 }

PtMTPRegisteredAppIDEntry ::=
    SEQUENCE {
        ptMTPRegisteredAppIDName        DisplayString,
        ptMTPRegisteredAppIDLongMSUSupport  INTEGER,
        ptMTPRegisteredAppIDMTP3NAManagerIndex      Integer32,
        ptMTPRegisteredAppIDMTP3NAIndex Integer32,
        ptMTPRegisteredAppIDL4ConnectionsIndex      Integer32,
        ptMTPRegisteredAppIDL4ConnectionIndex     Integer32,
        ptMTPRegisteredAppIDParentOID   OBJECT IDENTIFIER,
        ptMTPRegisteredAppIDRowStatus   RowStatus,
        ptMTPRegisteredAppIDIndex       Integer32
    }

ptMTPRegisteredAppIDName OBJECT-TYPE
    SYNTAX          DisplayString (SIZE(0..255))
    MAX-ACCESS      read-only
    STATUS          current
    DESCRIPTION     
            "Registered Application ID name as per MTP registration message"
    ::= { ptMTPRegisteredAppIDEntry 1 }

ptMTPRegisteredAppIDLongMSUSupport OBJECT-TYPE
    SYNTAX          INTEGER { disabled(0), enabled(1) }
    MAX-ACCESS      read-only
    STATUS          current
    DESCRIPTION     
            "Registered Long MSU support for the AppID"
    ::= { ptMTPRegisteredAppIDEntry 2 }

ptMTPRegisteredAppIDMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPRegisteredAppIDEntry 242 }

ptMTPRegisteredAppIDMTP3NAIndex OBJECT-TYPE
    SYNTAX          Integer32 (-2147483648..2147483647)
    MAX-ACCESS      not-accessible
    STATUS          current
    DESCRIPTION     
            "This is the index of the parent type for this object.
             This parent type is MTP3NA."
    ::= { ptMTPRegisteredAppIDEntry 243 }

ptMTPRegisteredAppIDL4ConnectionsIndex OBJECT-TYPE
    SYNTAX          Integer32 (-2147483648..2147483647)
    MAX-ACCESS      not-accessible
    STATUS          current
    DESCRIPTION     
            "This is the index of the parent type for this object.
             This parent type is L4Connections."
    ::= { ptMTPRegisteredAppIDEntry 244 }

ptMTPRegisteredAppIDL4ConnectionIndex OBJECT-TYPE
    SYNTAX          Integer32 (-2147483648..2147483647)
    MAX-ACCESS      not-accessible
    STATUS          current
    DESCRIPTION     
            "This is the index of the parent type for this object.
             This parent type is L4Connection."
    ::= { ptMTPRegisteredAppIDEntry 245 }

ptMTPRegisteredAppIDParentOID OBJECT-TYPE
    SYNTAX          OBJECT IDENTIFIER
    MAX-ACCESS      read-create
    STATUS          current
    DESCRIPTION     
            "The OID of the parent object for this instance"
    ::= { ptMTPRegisteredAppIDEntry 253 }

ptMTPRegisteredAppIDRowStatus OBJECT-TYPE
    SYNTAX          RowStatus
    MAX-ACCESS      read-create
    STATUS          current
    DESCRIPTION     
            "The row status for the MTPRegisteredAppID table"
    ::= { ptMTPRegisteredAppIDEntry 254 }

ptMTPRegisteredAppIDIndex OBJECT-TYPE
    SYNTAX          Integer32 (-2147483648..2147483647)
    MAX-ACCESS      not-accessible
    STATUS          current
    DESCRIPTION     
            "The row number for the MTPRegisteredAppID table"
    ::= { ptMTPRegisteredAppIDEntry 255 }

ptMTPPCMappings OBJECT IDENTIFIER
    ::= { ptMTPMTP3NA 790 }

ptMTPPCMappingsTable OBJECT-TYPE
    SYNTAX          SEQUENCE OF PtMTPPCMappingsEntry
    MAX-ACCESS      not-accessible
    STATUS          current
    DESCRIPTION     
            "No description supplied in the proxy config file."
    ::= { ptMTPPCMappings 1 }

ptMTPPCMappingsEntry OBJECT-TYPE
    SYNTAX          PtMTPPCMappingsEntry
    MAX-ACCESS      not-accessible
    STATUS          current
    DESCRIPTION     
            "A sequence of MTPPCMappings attributes."
    INDEX           { ptConnGroupIndex, 
                      ptMTPPCMappingsMTP3NAManagerIndex, 
                      ptMTPPCMappingsMTP3NAIndex, ptMTPPCMappingsIndex }
    ::= { ptMTPPCMappingsTable 1 }

PtMTPPCMappingsEntry ::=
    SEQUENCE {
        ptMTPPCMappingsCount            Integer32,
        ptMTPPCMappingsMTP3NAManagerIndex Integer32,
        ptMTPPCMappingsMTP3NAIndex      Integer32,
        ptMTPPCMappingsParentOID        OBJECT IDENTIFIER,
        ptMTPPCMappingsRowStatus        RowStatus,
        ptMTPPCMappingsIndex            Integer32
    }

ptMTPPCMappingsCount OBJECT-TYPE
    SYNTAX          Integer32 (-2147483648..2147483647)
    MAX-ACCESS      read-only
    STATUS          current
    DESCRIPTION     
            "Number of PC Mappings"
    ::= { ptMTPPCMappingsEntry 1 }

ptMTPPCMappingsMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPPCMappingsEntry 242 }

ptMTPPCMappingsMTP3NAIndex OBJECT-TYPE
    SYNTAX          Integer32 (-2147483648..2147483647)
    MAX-ACCESS      not-accessible
    STATUS          current
    DESCRIPTION     
            "This is the index of the parent type for this object.
             This parent type is MTP3NA."
    ::= { ptMTPPCMappingsEntry 243 }

ptMTPPCMappingsParentOID OBJECT-TYPE
    SYNTAX          OBJECT IDENTIFIER
    MAX-ACCESS      read-create
    STATUS          current
    DESCRIPTION     
            "The OID of the parent object for this instance"
    ::= { ptMTPPCMappingsEntry 253 }

ptMTPPCMappingsRowStatus OBJECT-TYPE
    SYNTAX          RowStatus
    MAX-ACCESS      read-create
    STATUS          current
    DESCRIPTION     
            "The row status for the MTPPCMappings table"
    ::= { ptMTPPCMappingsEntry 254 }

ptMTPPCMappingsIndex OBJECT-TYPE
    SYNTAX          Integer32 (-2147483648..2147483647)
    MAX-ACCESS      not-accessible
    STATUS          current
    DESCRIPTION     
            "The row number for the MTPPCMappings table"
    ::= { ptMTPPCMappingsEntry 255 }

ptMTPPCMapping OBJECT IDENTIFIER
    ::= { ptMTPPCMappings 791 }

ptMTPPCMappingTable OBJECT-TYPE
    SYNTAX          SEQUENCE OF PtMTPPCMappingEntry
    MAX-ACCESS      not-accessible
    STATUS          current
    DESCRIPTION     
            "No description supplied in the proxy config file."
    ::= { ptMTPPCMapping 1 }

ptMTPPCMappingEntry OBJECT-TYPE
    SYNTAX          PtMTPPCMappingEntry
    MAX-ACCESS      not-accessible
    STATUS          current
    DESCRIPTION     
            "A sequence of MTPPCMapping attributes."
    INDEX           { ptConnGroupIndex, ptMTPPCMappingMTP3NAManagerIndex, 
                      ptMTPPCMappingMTP3NAIndex, 
                      ptMTPPCMappingPCMappingsIndex, ptMTPPCMappingIndex }
    ::= { ptMTPPCMappingTable 1 }

PtMTPPCMappingEntry ::=
    SEQUENCE {
        ptMTPPCMappingPCMappingName     DisplayString,
        ptMTPPCMappingMTP3NAManagerIndex Integer32,
        ptMTPPCMappingMTP3NAIndex       Integer32,
        ptMTPPCMappingPCMappingsIndex   Integer32,
        ptMTPPCMappingParentOID         OBJECT IDENTIFIER,
        ptMTPPCMappingRowStatus         RowStatus,
        ptMTPPCMappingIndex             Integer32
    }

ptMTPPCMappingPCMappingName OBJECT-TYPE
    SYNTAX          DisplayString (SIZE(0..255))
    MAX-ACCESS      read-only
    STATUS          current
    DESCRIPTION     
            "The name of the PC Mapping. This name is used to reference the PC Mapping from a linkset. It must be unique among the PC Mappings within the NA. It must consist of at most 32 alphanumeric characters, hyphens, and underscores"
    ::= { ptMTPPCMappingEntry 1 }

ptMTPPCMappingMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPPCMappingEntry 242 }

ptMTPPCMappingMTP3NAIndex OBJECT-TYPE
    SYNTAX          Integer32 (-2147483648..2147483647)
    MAX-ACCESS      not-accessible
    STATUS          current
    DESCRIPTION     
            "This is the index of the parent type for this object.
             This parent type is MTP3NA."
    ::= { ptMTPPCMappingEntry 243 }

ptMTPPCMappingPCMappingsIndex OBJECT-TYPE
    SYNTAX          Integer32 (-2147483648..2147483647)
    MAX-ACCESS      not-accessible
    STATUS          current
    DESCRIPTION     
            "This is the index of the parent type for this object.
             This parent type is PCMappings."
    ::= { ptMTPPCMappingEntry 244 }

ptMTPPCMappingParentOID OBJECT-TYPE
    SYNTAX          OBJECT IDENTIFIER
    MAX-ACCESS      read-create
    STATUS          current
    DESCRIPTION     
            "The OID of the parent object for this instance"
    ::= { ptMTPPCMappingEntry 253 }

ptMTPPCMappingRowStatus OBJECT-TYPE
    SYNTAX          RowStatus
    MAX-ACCESS      read-create
    STATUS          current
    DESCRIPTION     
            "The row status for the MTPPCMapping table"
    ::= { ptMTPPCMappingEntry 254 }

ptMTPPCMappingIndex OBJECT-TYPE
    SYNTAX          Integer32 (-2147483648..2147483647)
    MAX-ACCESS      not-accessible
    STATUS          current
    DESCRIPTION     
            "The row number for the MTPPCMapping table"
    ::= { ptMTPPCMappingEntry 255 }

ptMTPMigrationRecord OBJECT IDENTIFIER
    ::= { ptMTPPCMapping 792 }

ptMTPMigrationRecordTable OBJECT-TYPE
    SYNTAX          SEQUENCE OF PtMTPMigrationRecordEntry
    MAX-ACCESS      not-accessible
    STATUS          current
    DESCRIPTION     
            "No description supplied in the proxy config file."
    ::= { ptMTPMigrationRecord 1 }

ptMTPMigrationRecordEntry OBJECT-TYPE
    SYNTAX          PtMTPMigrationRecordEntry
    MAX-ACCESS      not-accessible
    STATUS          current
    DESCRIPTION     
            "A sequence of MTPMigrationRecord attributes."
    INDEX           { ptConnGroupIndex, 
                      ptMTPMigrationRecordMTP3NAManagerIndex, 
                      ptMTPMigrationRecordMTP3NAIndex, 
                      ptMTPMigrationRecordPCMappingsIndex, 
                      ptMTPMigrationRecordPCMappingIndex, 
                      ptMTPMigrationRecordIndex }
    ::= { ptMTPMigrationRecordTable 1 }

PtMTPMigrationRecordEntry ::=
    SEQUENCE {
        ptMTPMigrationRecordOPC         DisplayString,
        ptMTPMigrationRecordDPC         DisplayString,
        ptMTPMigrationRecordMessageCategory   INTEGER,
        ptMTPMigrationRecordNewDPC      DisplayString,
        ptMTPMigrationRecordInternalID  Integer32,
        ptMTPMigrationRecordMTP3NAManagerIndex      Integer32,
        ptMTPMigrationRecordMTP3NAIndex Integer32,
        ptMTPMigrationRecordPCMappingsIndex   Integer32,
        ptMTPMigrationRecordPCMappingIndex  Integer32,
        ptMTPMigrationRecordParentOID   OBJECT IDENTIFIER,
        ptMTPMigrationRecordRowStatus   RowStatus,
        ptMTPMigrationRecordIndex       Integer32
    }

ptMTPMigrationRecordOPC OBJECT-TYPE
    SYNTAX          DisplayString (SIZE(0..255))
    MAX-ACCESS      read-create
    STATUS          current
    DESCRIPTION     
            "Originating Point Code. \nA string that represents a point code, in the PC Display Format used by the NA."
    ::= { ptMTPMigrationRecordEntry 1 }

ptMTPMigrationRecordDPC OBJECT-TYPE
    SYNTAX          DisplayString (SIZE(0..255))
    MAX-ACCESS      read-create
    STATUS          current
    DESCRIPTION     
            "Destination Point Code. \nA string that represents a point code, in the PC Display Format used by the NA."
    ::= { ptMTPMigrationRecordEntry 2 }

ptMTPMigrationRecordMessageCategory OBJECT-TYPE
    SYNTAX          INTEGER { amMessages(0) }
    MAX-ACCESS      read-create
    STATUS          current
    DESCRIPTION     
            "Message Category. \nAn identifier for the class of messages that are affected by this record. Currently there is only one allowed value: AM Messages (MTP3 Adjacent Management Messages)."
    ::= { ptMTPMigrationRecordEntry 3 }

ptMTPMigrationRecordNewDPC OBJECT-TYPE
    SYNTAX          DisplayString (SIZE(0..255))
    MAX-ACCESS      read-create
    STATUS          current
    DESCRIPTION     
            "New Destination Point Code. \nA string that represents a point code, in the PC Display Format used by the NA. The special value ''Discard'' may also be used, indicating that a matching MSU should be discarded without sending a TFP."
    ::= { ptMTPMigrationRecordEntry 4 }

ptMTPMigrationRecordInternalID OBJECT-TYPE
    SYNTAX          Integer32 (-2147483648..2147483647)
    MAX-ACCESS      read-only
    STATUS          current
    DESCRIPTION     
            "Internal ID."
    ::= { ptMTPMigrationRecordEntry 5 }

ptMTPMigrationRecordMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPMigrationRecordEntry 242 }

ptMTPMigrationRecordMTP3NAIndex OBJECT-TYPE
    SYNTAX          Integer32 (-2147483648..2147483647)
    MAX-ACCESS      not-accessible
    STATUS          current
    DESCRIPTION     
            "This is the index of the parent type for this object.
             This parent type is MTP3NA."
    ::= { ptMTPMigrationRecordEntry 243 }

ptMTPMigrationRecordPCMappingsIndex OBJECT-TYPE
    SYNTAX          Integer32 (-2147483648..2147483647)
    MAX-ACCESS      not-accessible
    STATUS          current
    DESCRIPTION     
            "This is the index of the parent type for this object.
             This parent type is PCMappings."
    ::= { ptMTPMigrationRecordEntry 244 }

ptMTPMigrationRecordPCMappingIndex OBJECT-TYPE
    SYNTAX          Integer32 (-2147483648..2147483647)
    MAX-ACCESS      not-accessible
    STATUS          current
    DESCRIPTION     
            "This is the index of the parent type for this object.
             This parent type is PCMapping."
    ::= { ptMTPMigrationRecordEntry 245 }

ptMTPMigrationRecordParentOID OBJECT-TYPE
    SYNTAX          OBJECT IDENTIFIER
    MAX-ACCESS      read-create
    STATUS          current
    DESCRIPTION     
            "The OID of the parent object for this instance"
    ::= { ptMTPMigrationRecordEntry 253 }

ptMTPMigrationRecordRowStatus OBJECT-TYPE
    SYNTAX          RowStatus
    MAX-ACCESS      read-create
    STATUS          current
    DESCRIPTION     
            "The row status for the MTPMigrationRecord table"
    ::= { ptMTPMigrationRecordEntry 254 }

ptMTPMigrationRecordIndex OBJECT-TYPE
    SYNTAX          Integer32 (-2147483648..2147483647)
    MAX-ACCESS      not-accessible
    STATUS          current
    DESCRIPTION     
            "The row number for the MTPMigrationRecord table"
    ::= { ptMTPMigrationRecordEntry 255 }

ptMTPLocalRedirectRecord OBJECT IDENTIFIER
    ::= { ptMTPPCMapping 793 }

ptMTPLocalRedirectRecordTable OBJECT-TYPE
    SYNTAX          SEQUENCE OF PtMTPLocalRedirectRecordEntry
    MAX-ACCESS      not-accessible
    STATUS          current
    DESCRIPTION     
            "No description supplied in the proxy config file."
    ::= { ptMTPLocalRedirectRecord 1 }

ptMTPLocalRedirectRecordEntry OBJECT-TYPE
    SYNTAX          PtMTPLocalRedirectRecordEntry
    MAX-ACCESS      not-accessible
    STATUS          current
    DESCRIPTION     
            "A sequence of MTPLocalRedirectRecord attributes."
    INDEX           { ptConnGroupIndex, 
                      ptMTPLocalRedirectRecordMTP3NAManagerIndex, 
                      ptMTPLocalRedirectRecordMTP3NAIndex, 
                      ptMTPLocalRedirectRecordPCMappingsIndex, 
                      ptMTPLocalRedirectRecordPCMappingIndex, 
                      ptMTPLocalRedirectRecordIndex }
    ::= { ptMTPLocalRedirectRecordTable 1 }

PtMTPLocalRedirectRecordEntry ::=
    SEQUENCE {
        ptMTPLocalRedirectRecordDPC     DisplayString,
        ptMTPLocalRedirectRecordMessageCategory       INTEGER,
        ptMTPLocalRedirectRecordNewDPC  DisplayString,
        ptMTPLocalRedirectRecordModifier DisplayString,
        ptMTPLocalRedirectRecordInternalID  Integer32,
        ptMTPLocalRedirectRecordMTP3NAManagerIndex          Integer32,
        ptMTPLocalRedirectRecordMTP3NAIndex   Integer32,
        ptMTPLocalRedirectRecordPCMappingsIndex       Integer32,
        ptMTPLocalRedirectRecordPCMappingIndex      Integer32,
        ptMTPLocalRedirectRecordParentOID OBJECT IDENTIFIER,
        ptMTPLocalRedirectRecordRowStatus RowStatus,
        ptMTPLocalRedirectRecordIndex   Integer32
    }

ptMTPLocalRedirectRecordDPC OBJECT-TYPE
    SYNTAX          DisplayString (SIZE(0..255))
    MAX-ACCESS      read-create
    STATUS          current
    DESCRIPTION     
            "Destination Point Code. \nA string that represents a point code, in the PC Display Format used by the NA."
    ::= { ptMTPLocalRedirectRecordEntry 1 }

ptMTPLocalRedirectRecordMessageCategory OBJECT-TYPE
    SYNTAX          INTEGER { fcm(0), tfc(1), rct(2), ssp(3), ssa(4), 
                        sst(5), sccpData(6), scmg(7) }
    MAX-ACCESS      read-create
    STATUS          current
    DESCRIPTION     
            "Message Category. \nThe class of message affected by the local redirect. \nThe valid values are TFC, RCT, SSP, SSA, SST, SCCP Data, FCM, and SCMG. \nSCCP Data means SCCP messages other than SCMG messages (Called Party SSN is not 1). \nSCMG means any type of SCCP management message (e.g. SSA, SSP or SST). \nSST, SCMG and SCCP Data values may not be used with the Duplicate modifier. \nFCM means the flow control MTP management messages (TFC and RCT). \nDefault value: FCM."
    ::= { ptMTPLocalRedirectRecordEntry 2 }

ptMTPLocalRedirectRecordNewDPC OBJECT-TYPE
    SYNTAX          DisplayString (SIZE(0..255))
    MAX-ACCESS      read-create
    STATUS          current
    DESCRIPTION     
            "New Destination Point Code. \nA string that represents a point code, in the PC Display Format used by the NA."
    ::= { ptMTPLocalRedirectRecordEntry 3 }

ptMTPLocalRedirectRecordModifier OBJECT-TYPE
    SYNTAX          DisplayString (SIZE(0..255))
    MAX-ACCESS      read-create
    STATUS          current
    DESCRIPTION     
            "Modifier. \nThis is a string that describes any modification to the behaviour of this record. \nThis may be the empty string or the string ''Duplicate'' or a string of the form ''Duplicate <max>'' or of the form ''Duplicate <max> <overload behaviour>''. \nIf the max is specified, it must be a positive integer between 1 and 1000 that indicates the number of MSUs per second that may be duplicated. If the overload behaviour is specified, it must be one of the following strings: modify, original or alternate. If the number of duplicated MSUs exceeds the provisioned maximum for the record (per second) then the MSU is not duplicated, instead the behaviour depends on the provisioned overload behaviour. If the overload behaviour is set to ''modify'' then the MSU is modified and processed, if the overload behaviour is set to ''original'' then the MSU is processed unchanged and if the overload behavior is set to ''alternate'' then the behaviour alternates between ''modify'' and ''original''. \nIf the Modifier attribute is set to a Duplicate string form, the Message Category attribute cannot be set to SST, SCMG, or SCCP Data. \nThe default values for the max is 1000 and the default value for the overload behaviour is alternate. \nFor example, ''Duplicate'' is the same as ''Duplicate 1000 alternate''."
    ::= { ptMTPLocalRedirectRecordEntry 4 }

ptMTPLocalRedirectRecordInternalID OBJECT-TYPE
    SYNTAX          Integer32 (-2147483648..2147483647)
    MAX-ACCESS      read-only
    STATUS          current
    DESCRIPTION     
            "Internal ID."
    ::= { ptMTPLocalRedirectRecordEntry 5 }

ptMTPLocalRedirectRecordMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPLocalRedirectRecordEntry 242 }

ptMTPLocalRedirectRecordMTP3NAIndex OBJECT-TYPE
    SYNTAX          Integer32 (-2147483648..2147483647)
    MAX-ACCESS      not-accessible
    STATUS          current
    DESCRIPTION     
            "This is the index of the parent type for this object.
             This parent type is MTP3NA."
    ::= { ptMTPLocalRedirectRecordEntry 243 }

ptMTPLocalRedirectRecordPCMappingsIndex OBJECT-TYPE
    SYNTAX          Integer32 (-2147483648..2147483647)
    MAX-ACCESS      not-accessible
    STATUS          current
    DESCRIPTION     
            "This is the index of the parent type for this object.
             This parent type is PCMappings."
    ::= { ptMTPLocalRedirectRecordEntry 244 }

ptMTPLocalRedirectRecordPCMappingIndex OBJECT-TYPE
    SYNTAX          Integer32 (-2147483648..2147483647)
    MAX-ACCESS      not-accessible
    STATUS          current
    DESCRIPTION     
            "This is the index of the parent type for this object.
             This parent type is PCMapping."
    ::= { ptMTPLocalRedirectRecordEntry 245 }

ptMTPLocalRedirectRecordParentOID OBJECT-TYPE
    SYNTAX          OBJECT IDENTIFIER
    MAX-ACCESS      read-create
    STATUS          current
    DESCRIPTION     
            "The OID of the parent object for this instance"
    ::= { ptMTPLocalRedirectRecordEntry 253 }

ptMTPLocalRedirectRecordRowStatus OBJECT-TYPE
    SYNTAX          RowStatus
    MAX-ACCESS      read-create
    STATUS          current
    DESCRIPTION     
            "The row status for the MTPLocalRedirectRecord table"
    ::= { ptMTPLocalRedirectRecordEntry 254 }

ptMTPLocalRedirectRecordIndex OBJECT-TYPE
    SYNTAX          Integer32 (-2147483648..2147483647)
    MAX-ACCESS      not-accessible
    STATUS          current
    DESCRIPTION     
            "The row number for the MTPLocalRedirectRecord table"
    ::= { ptMTPLocalRedirectRecordEntry 255 }

ptMTPPCMappingRecord OBJECT IDENTIFIER
    ::= { ptMTPPCMapping 794 }

ptMTPPCMappingRecordTable OBJECT-TYPE
    SYNTAX          SEQUENCE OF PtMTPPCMappingRecordEntry
    MAX-ACCESS      not-accessible
    STATUS          current
    DESCRIPTION     
            "PC Mappings."
    ::= { ptMTPPCMappingRecord 1 }

ptMTPPCMappingRecordEntry OBJECT-TYPE
    SYNTAX          PtMTPPCMappingRecordEntry
    MAX-ACCESS      not-accessible
    STATUS          current
    DESCRIPTION     
            "A sequence of MTPPCMappingRecord attributes."
    INDEX           { ptConnGroupIndex, 
                      ptMTPPCMappingRecordMTP3NAManagerIndex, 
                      ptMTPPCMappingRecordMTP3NAIndex, 
                      ptMTPPCMappingRecordPCMappingsIndex, 
                      ptMTPPCMappingRecordPCMappingIndex, 
                      ptMTPPCMappingRecordIndex }
    ::= { ptMTPPCMappingRecordTable 1 }

PtMTPPCMappingRecordEntry ::=
    SEQUENCE {
        ptMTPPCMappingRecordDirection   INTEGER,
        ptMTPPCMappingRecordLocalPC     DisplayString,
        ptMTPPCMappingRecordRemotePC    DisplayString,
        ptMTPPCMappingRecordInternalID  Integer32,
        ptMTPPCMappingRecordMTP3NAManagerIndex      Integer32,
        ptMTPPCMappingRecordMTP3NAIndex Integer32,
        ptMTPPCMappingRecordPCMappingsIndex   Integer32,
        ptMTPPCMappingRecordPCMappingIndex  Integer32,
        ptMTPPCMappingRecordParentOID   OBJECT IDENTIFIER,
        ptMTPPCMappingRecordRowStatus   RowStatus,
        ptMTPPCMappingRecordIndex       Integer32
    }

ptMTPPCMappingRecordDirection OBJECT-TYPE
    SYNTAX          INTEGER { any(0), incoming(1), outgoing(2) }
    MAX-ACCESS      read-create
    STATUS          current
    DESCRIPTION     
            "Direction. \nAllowed values: ANY, INCOMING, and OUTGOING. \nDefault value: ANY."
    ::= { ptMTPPCMappingRecordEntry 1 }

ptMTPPCMappingRecordLocalPC OBJECT-TYPE
    SYNTAX          DisplayString (SIZE(0..255))
    MAX-ACCESS      read-create
    STATUS          current
    DESCRIPTION     
            "Local Point Code. \nA string representing a point code in the PC Display Format used by the Node. \nThis represents the point code as understood by the local node."
    ::= { ptMTPPCMappingRecordEntry 2 }

ptMTPPCMappingRecordRemotePC OBJECT-TYPE
    SYNTAX          DisplayString (SIZE(0..255))
    MAX-ACCESS      read-create
    STATUS          current
    DESCRIPTION     
            "Remote Point Code. \nA string representing a point code in the PC Display Format used by the Node. \nThis represents the point code as understood by the adjacent node."
    ::= { ptMTPPCMappingRecordEntry 3 }

ptMTPPCMappingRecordInternalID OBJECT-TYPE
    SYNTAX          Integer32 (-2147483648..2147483647)
    MAX-ACCESS      read-only
    STATUS          current
    DESCRIPTION     
            "Internal ID."
    ::= { ptMTPPCMappingRecordEntry 4 }

ptMTPPCMappingRecordMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPPCMappingRecordEntry 242 }

ptMTPPCMappingRecordMTP3NAIndex OBJECT-TYPE
    SYNTAX          Integer32 (-2147483648..2147483647)
    MAX-ACCESS      not-accessible
    STATUS          current
    DESCRIPTION     
            "This is the index of the parent type for this object.
             This parent type is MTP3NA."
    ::= { ptMTPPCMappingRecordEntry 243 }

ptMTPPCMappingRecordPCMappingsIndex OBJECT-TYPE
    SYNTAX          Integer32 (-2147483648..2147483647)
    MAX-ACCESS      not-accessible
    STATUS          current
    DESCRIPTION     
            "This is the index of the parent type for this object.
             This parent type is PCMappings."
    ::= { ptMTPPCMappingRecordEntry 244 }

ptMTPPCMappingRecordPCMappingIndex OBJECT-TYPE
    SYNTAX          Integer32 (-2147483648..2147483647)
    MAX-ACCESS      not-accessible
    STATUS          current
    DESCRIPTION     
            "This is the index of the parent type for this object.
             This parent type is PCMapping."
    ::= { ptMTPPCMappingRecordEntry 245 }

ptMTPPCMappingRecordParentOID OBJECT-TYPE
    SYNTAX          OBJECT IDENTIFIER
    MAX-ACCESS      read-create
    STATUS          current
    DESCRIPTION     
            "The OID of the parent object for this instance"
    ::= { ptMTPPCMappingRecordEntry 253 }

ptMTPPCMappingRecordRowStatus OBJECT-TYPE
    SYNTAX          RowStatus
    MAX-ACCESS      read-create
    STATUS          current
    DESCRIPTION     
            "The row status for the MTPPCMappingRecord table"
    ::= { ptMTPPCMappingRecordEntry 254 }

ptMTPPCMappingRecordIndex OBJECT-TYPE
    SYNTAX          Integer32 (-2147483648..2147483647)
    MAX-ACCESS      not-accessible
    STATUS          current
    DESCRIPTION     
            "The row number for the MTPPCMappingRecord table"
    ::= { ptMTPPCMappingRecordEntry 255 }

ptMTPDRELoadingManager OBJECT IDENTIFIER
    ::= { ptMTPMTP3NAManager 787 }

ptMTPDRELoadingManagerTable OBJECT-TYPE
    SYNTAX          SEQUENCE OF PtMTPDRELoadingManagerEntry
    MAX-ACCESS      not-accessible
    STATUS          current
    DESCRIPTION     
            "No description supplied in the proxy config file."
    ::= { ptMTPDRELoadingManager 1 }

ptMTPDRELoadingManagerEntry OBJECT-TYPE
    SYNTAX          PtMTPDRELoadingManagerEntry
    MAX-ACCESS      not-accessible
    STATUS          current
    DESCRIPTION     
            "A sequence of MTPDRELoadingManager attributes."
    INDEX           { ptConnGroupIndex, 
                      ptMTPDRELoadingManagerMTP3NAManagerIndex, 
                      ptMTPDRELoadingManagerIndex }
    ::= { ptMTPDRELoadingManagerTable 1 }

PtMTPDRELoadingManagerEntry ::=
    SEQUENCE {
        ptMTPDRELoadingManagerCount     Integer32,
        ptMTPDRELoadingManagerState     INTEGER,
        ptMTPDRELoadingManagerLSLRebalanceThreshold           Integer32,
        ptMTPDRELoadingManagerHSLRebalanceThreshold           Integer32,
        ptMTPDRELoadingManagerMTP3NAManagerIndex        Integer32,
        ptMTPDRELoadingManagerActions   INTEGER,
        ptMTPDRELoadingManagerParentOID OBJECT IDENTIFIER,
        ptMTPDRELoadingManagerRowStatus RowStatus,
        ptMTPDRELoadingManagerIndex     Integer32
    }

ptMTPDRELoadingManagerCount OBJECT-TYPE
    SYNTAX          Integer32 (-2147483648..2147483647)
    MAX-ACCESS      read-only
    STATUS          current
    DESCRIPTION     
            "Number of DRE Loading instances "
    ::= { ptMTPDRELoadingManagerEntry 1 }

ptMTPDRELoadingManagerState OBJECT-TYPE
    SYNTAX          INTEGER { inactive(0), active(1) }
    MAX-ACCESS      read-only
    STATUS          current
    DESCRIPTION     
            "Status for DRE loading rebalance audit"
    ::= { ptMTPDRELoadingManagerEntry 2 }

ptMTPDRELoadingManagerLSLRebalanceThreshold OBJECT-TYPE
    SYNTAX          Integer32 (-2147483648..2147483647)
    MAX-ACCESS      read-create
    STATUS          current
    DESCRIPTION     
            "The maximum difference between the DREs for number of low speed links"
    ::= { ptMTPDRELoadingManagerEntry 3 }

ptMTPDRELoadingManagerHSLRebalanceThreshold OBJECT-TYPE
    SYNTAX          Integer32 (-2147483648..2147483647)
    MAX-ACCESS      read-create
    STATUS          current
    DESCRIPTION     
            "The maximum difference between the DREs for number of high speed links"
    ::= { ptMTPDRELoadingManagerEntry 4 }

ptMTPDRELoadingManagerMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPDRELoadingManagerEntry 242 }

ptMTPDRELoadingManagerActions OBJECT-TYPE
    SYNTAX          INTEGER { deactivate(1), activate(2) }
    MAX-ACCESS      read-create
    STATUS          current
    DESCRIPTION     
            "The OID of all possible actions for this instance"
    ::= { ptMTPDRELoadingManagerEntry 252 }

ptMTPDRELoadingManagerParentOID OBJECT-TYPE
    SYNTAX          OBJECT IDENTIFIER
    MAX-ACCESS      read-create
    STATUS          current
    DESCRIPTION     
            "The OID of the parent object for this instance"
    ::= { ptMTPDRELoadingManagerEntry 253 }

ptMTPDRELoadingManagerRowStatus OBJECT-TYPE
    SYNTAX          RowStatus
    MAX-ACCESS      read-create
    STATUS          current
    DESCRIPTION     
            "The row status for the MTPDRELoadingManager table"
    ::= { ptMTPDRELoadingManagerEntry 254 }

ptMTPDRELoadingManagerIndex OBJECT-TYPE
    SYNTAX          Integer32 (-2147483648..2147483647)
    MAX-ACCESS      not-accessible
    STATUS          current
    DESCRIPTION     
            "The row number for the MTPDRELoadingManager table"
    ::= { ptMTPDRELoadingManagerEntry 255 }

ptMTPDRELoading OBJECT IDENTIFIER
    ::= { ptMTPDRELoadingManager 788 }

ptMTPDRELoadingTable OBJECT-TYPE
    SYNTAX          SEQUENCE OF PtMTPDRELoadingEntry
    MAX-ACCESS      not-accessible
    STATUS          current
    DESCRIPTION     
            "No description supplied in the proxy config file."
    ::= { ptMTPDRELoading 1 }

ptMTPDRELoadingEntry OBJECT-TYPE
    SYNTAX          PtMTPDRELoadingEntry
    MAX-ACCESS      not-accessible
    STATUS          current
    DESCRIPTION     
            "A sequence of MTPDRELoading attributes."
    INDEX           { ptConnGroupIndex, 
                      ptMTPDRELoadingMTP3NAManagerIndex, 
                      ptMTPDRELoadingDRELoadingManagerIndex, 
                      ptMTPDRELoadingIndex }
    ::= { ptMTPDRELoadingTable 1 }

PtMTPDRELoadingEntry ::=
    SEQUENCE {
        ptMTPDRELoadingDREID            Integer32,
        ptMTPDRELoadingLSLLinkCount     Integer32,
        ptMTPDRELoadingHSLLinkCount     Integer32,
        ptMTPDRELoadingMTP3NAManagerIndex Integer32,
        ptMTPDRELoadingDRELoadingManagerIndex     Integer32,
        ptMTPDRELoadingParentOID        OBJECT IDENTIFIER,
        ptMTPDRELoadingRowStatus        RowStatus,
        ptMTPDRELoadingIndex            Integer32
    }

ptMTPDRELoadingDREID OBJECT-TYPE
    SYNTAX          Integer32 (1..64)
    MAX-ACCESS      read-only
    STATUS          current
    DESCRIPTION     
            "A unique identifier for the DRE object. \n\nThe ID is set at creation time and cannot be modified after that."
    ::= { ptMTPDRELoadingEntry 1 }

ptMTPDRELoadingLSLLinkCount OBJECT-TYPE
    SYNTAX          Integer32 (0..100000)
    MAX-ACCESS      read-only
    STATUS          current
    DESCRIPTION     
            "This is the loading level to indicate the number of low speed links on this DRE."
    ::= { ptMTPDRELoadingEntry 2 }

ptMTPDRELoadingHSLLinkCount OBJECT-TYPE
    SYNTAX          Integer32 (0..100000)
    MAX-ACCESS      read-only
    STATUS          current
    DESCRIPTION     
            "This is the loading level to indicate the number of high speed links on this DRE."
    ::= { ptMTPDRELoadingEntry 3 }

ptMTPDRELoadingMTP3NAManagerIndex OBJECT-TYPE
    SYNTAX          Integer32 (-2147483648..2147483647)
    MAX-ACCESS      not-accessible
    STATUS          current
    DESCRIPTION     
            "This is the index of the parent type for this object.
             This parent type is MTP3NAManager."
    ::= { ptMTPDRELoadingEntry 242 }

ptMTPDRELoadingDRELoadingManagerIndex OBJECT-TYPE
    SYNTAX          Integer32 (-2147483648..2147483647)
    MAX-ACCESS      not-accessible
    STATUS          current
    DESCRIPTION     
            "This is the index of the parent type for this object.
             This parent type is DRELoadingManager."
    ::= { ptMTPDRELoadingEntry 243 }

ptMTPDRELoadingParentOID OBJECT-TYPE
    SYNTAX          OBJECT IDENTIFIER
    MAX-ACCESS      read-create
    STATUS          current
    DESCRIPTION     
            "The OID of the parent object for this instance"
    ::= { ptMTPDRELoadingEntry 253 }

ptMTPDRELoadingRowStatus OBJECT-TYPE
    SYNTAX          RowStatus
    MAX-ACCESS      read-create
    STATUS          current
    DESCRIPTION     
            "The row status for the MTPDRELoading table"
    ::= { ptMTPDRELoadingEntry 254 }

ptMTPDRELoadingIndex OBJECT-TYPE
    SYNTAX          Integer32 (-2147483648..2147483647)
    MAX-ACCESS      not-accessible
    STATUS          current
    DESCRIPTION     
            "The row number for the MTPDRELoading table"
    ::= { ptMTPDRELoadingEntry 255 }

ptSCCPSCCPNAManager OBJECT IDENTIFIER
    ::= { ptConnGroup 85 }

ptSCCPSCCPNAManagerTable OBJECT-TYPE
    SYNTAX          SEQUENCE OF PtSCCPSCCPNAManagerEntry
    MAX-ACCESS      not-accessible
    STATUS          current
    DESCRIPTION     
            "No description supplied in the proxy config file."
    ::= { ptSCCPSCCPNAManager 1 }

ptSCCPSCCPNAManagerEntry OBJECT-TYPE
    SYNTAX          PtSCCPSCCPNAManagerEntry
    MAX-ACCESS      not-accessible
    STATUS          current
    DESCRIPTION     
            "A sequence of SCCPSCCPNAManager attributes."
    INDEX           { ptConnGroupIndex, ptSCCPSCCPNAManagerIndex }
    ::= { ptSCCPSCCPNAManagerTable 1 }

PtSCCPSCCPNAManagerEntry ::=
    SEQUENCE {
        ptSCCPSCCPNAManagerNADebugLevel Integer32,
        ptSCCPSCCPNAManagerLDLDebugLevel Integer32,
        ptSCCPSCCPNAManagerSCTPDebugLevel Integer32,
        ptSCCPSCCPNAManagerActions      INTEGER,
        ptSCCPSCCPNAManagerParentOID    OBJECT IDENTIFIER,
        ptSCCPSCCPNAManagerRowStatus    RowStatus,
        ptSCCPSCCPNAManagerIndex        Integer32
    }

ptSCCPSCCPNAManagerNADebugLevel OBJECT-TYPE
    SYNTAX          Integer32 (-2147483648..2147483647)
    MAX-ACCESS      read-create
    STATUS          current
    DESCRIPTION     
            "SCCP NA Debug Level (0 - 255). \nSystem wide SCCP related events will be traced and logged to the Debug Log. \nPlease do not change the NA Debug Level attribute unless instructed by support as increased logging beyond default setting may adversly impact performance. \nDefault value: 0."
    ::= { ptSCCPSCCPNAManagerEntry 1 }

ptSCCPSCCPNAManagerLDLDebugLevel OBJECT-TYPE
    SYNTAX          Integer32 (-2147483648..2147483647)
    MAX-ACCESS      read-create
    STATUS          current
    DESCRIPTION     
            "SCCP LDL Debug Level (0 - 255). \nLayer Distribution Library (LDL) related events will be traced and logged to the Debug Log. \nPlease do not change the LDL Debug Level attribute unless instructed by support as increased logging beyond default setting may adversly impact performance. \nDefault value: 2."
    ::= { ptSCCPSCCPNAManagerEntry 2 }

ptSCCPSCCPNAManagerSCTPDebugLevel OBJECT-TYPE
    SYNTAX          Integer32 (-2147483648..2147483647)
    MAX-ACCESS      read-create
    STATUS          current
    DESCRIPTION     
            "SCCP SCTP Debug Level (0 - 255). \nFor Sonus SCTP deployments, SCTP related events will be traced and logged to the Debug Log. \nPlease do not change the SCTP Debug Level attribute unless instructed by support as increased logging beyond default setting may adversly impact performance. \nDefault value: 0. \nObsolete as of 15.1.0 for LK SCTP deployments."
    ::= { ptSCCPSCCPNAManagerEntry 3 }

ptSCCPSCCPNAManagerActions OBJECT-TYPE
    SYNTAX          INTEGER { restoreDebugDefaults(1) }
    MAX-ACCESS      read-create
    STATUS          current
    DESCRIPTION     
            "The OID of all possible actions for this instance"
    ::= { ptSCCPSCCPNAManagerEntry 252 }

ptSCCPSCCPNAManagerParentOID OBJECT-TYPE
    SYNTAX          OBJECT IDENTIFIER
    MAX-ACCESS      read-create
    STATUS          current
    DESCRIPTION     
            "The OID of the parent object for this instance"
    ::= { ptSCCPSCCPNAManagerEntry 253 }

ptSCCPSCCPNAManagerRowStatus OBJECT-TYPE
    SYNTAX          RowStatus
    MAX-ACCESS      read-create
    STATUS          current
    DESCRIPTION     
            "The row status for the SCCPSCCPNAManager table"
    ::= { ptSCCPSCCPNAManagerEntry 254 }

ptSCCPSCCPNAManagerIndex OBJECT-TYPE
    SYNTAX          Integer32 (-2147483648..2147483647)
    MAX-ACCESS      not-accessible
    STATUS          current
    DESCRIPTION     
            "The row number for the SCCPSCCPNAManager table"
    ::= { ptSCCPSCCPNAManagerEntry 255 }

ptSCCPSCCPNA OBJECT IDENTIFIER
    ::= { ptSCCPSCCPNAManager 87 }

ptSCCPSCCPNATable OBJECT-TYPE
    SYNTAX          SEQUENCE OF PtSCCPSCCPNAEntry
    MAX-ACCESS      not-accessible
    STATUS          current
    DESCRIPTION     
            "No description supplied in the proxy config file."
    ::= { ptSCCPSCCPNA 1 }

ptSCCPSCCPNAEntry OBJECT-TYPE
    SYNTAX          PtSCCPSCCPNAEntry
    MAX-ACCESS      not-accessible
    STATUS          current
    DESCRIPTION     
            "A sequence of SCCPSCCPNA attributes."
    INDEX           { ptConnGroupIndex, ptSCCPSCCPNASCCPNAManagerIndex, 
                      ptSCCPSCCPNAIndex }
    ::= { ptSCCPSCCPNATable 1 }

PtSCCPSCCPNAEntry ::=
    SEQUENCE {
        ptSCCPSCCPNAContext             DisplayString,
        ptSCCPSCCPNALocalPointCode      Integer32,
        ptSCCPSCCPNASS7Variant          INTEGER,
        ptSCCPSCCPNANetworkIndicator    INTEGER,
        ptSCCPSCCPNAMTP3HostName        DisplayString,
        ptSCCPSCCPNANetworkAppearance   Integer32,
        ptSCCPSCCPNATrafficStatus       INTEGER,
        ptSCCPSCCPNAErrors              INTEGER,
        ptSCCPSCCPNASetupManagement     INTEGER,
        ptSCCPSCCPNAExecutionTrace      INTEGER,
        ptSCCPSCCPNALayerCommunication  INTEGER,
        ptSCCPSCCPNAPeerManagement      INTEGER,
        ptSCCPSCCPNASS7Messages         INTEGER,
        ptSCCPSCCPNAMTP3Incoming        INTEGER,
        ptSCCPSCCPNAMTP3IncomingGTAI    INTEGER,
        ptSCCPSCCPNAMTP3IncomingGTZeroLength    INTEGER,
        ptSCCPSCCPNAMTP3IncomingDestination   INTEGER,
        ptSCCPSCCPNAUserIncoming        INTEGER,
        ptSCCPSCCPNAKeepAlive           INTEGER,
        ptSCCPSCCPNASSTDelay            Integer32,
        ptSCCPSCCPNAXUDTReassembly      Integer32,
        ptSCCPSCCPNAMTPAudit            INTEGER,
        ptSCCPSCCPNAMTPAuditLifetime    INTEGER,
        ptSCCPSCCPNAConnectionEstablish Integer32,
        ptSCCPSCCPNAConnectionRelease   Integer32,
        ptSCCPSCCPNAReceiveInactive     Integer32,
        ptSCCPSCCPNASendInactive        Integer32,
        ptSCCPSCCPNAReferenceFreeze     Integer32,
        ptSCCPSCCPNASLSIncrementation   INTEGER,
        ptSCCPSCCPNAOldEncodingOfAI     INTEGER,
        ptSCCPSCCPNAOldEncodingOfCLGPAPC INTEGER,
        ptSCCPSCCPNAOldMTPAvailability  INTEGER,
        ptSCCPSCCPNAOldPointCodeFormat  INTEGER,
        ptSCCPSCCPNASetOPCToLPCNonMgmt  INTEGER,
        ptSCCPSCCPNASetOPCToLPCMgmt     INTEGER,
        ptSCCPSCCPNANUNITDATAQoSSupport INTEGER,
        ptSCCPSCCPNASSNZeroUserSupport  INTEGER,
        ptSCCPSCCPNAGTTIncomingRerouting INTEGER,
        ptSCCPSCCPNAGTTIncomingCLGPC    INTEGER,
        ptSCCPSCCPNASSTOPCFromSSP       INTEGER,
        ptSCCPSCCPNASetOPCToLPC         INTEGER,
        ptSCCPSCCPNASetAffectedPCToLPC  INTEGER,
        ptSCCPSCCPNAEncodingOfCLGPAPC   INTEGER,
        ptSCCPSCCPNAForcedSegmentation  Integer32,
        ptSCCPSCCPNALPCRegistration     INTEGER,
        ptSCCPSCCPNAUnequippedUser      INTEGER,
        ptSCCPSCCPNASCCPNAManagerIndex  Integer32,
        ptSCCPSCCPNAActions             INTEGER,
        ptSCCPSCCPNAParentOID           OBJECT IDENTIFIER,
        ptSCCPSCCPNARowStatus           RowStatus,
        ptSCCPSCCPNAIndex               Integer32
    }

ptSCCPSCCPNAContext OBJECT-TYPE
    SYNTAX          DisplayString (SIZE(0..255))
    MAX-ACCESS      read-only
    STATUS          current
    DESCRIPTION     
            "This attribute contains system generated identifier that is used to identify this SCCP Network Appearance in log messages."
    ::= { ptSCCPSCCPNAEntry 1 }

ptSCCPSCCPNALocalPointCode OBJECT-TYPE
    SYNTAX          Integer32 (-2147483648..2147483647)
    MAX-ACCESS      read-only
    STATUS          current
    DESCRIPTION     
            "The local point code value is obtained from the MTP3 and is provided here for informational purposes only."
    ::= { ptSCCPSCCPNAEntry 2 }

ptSCCPSCCPNASS7Variant OBJECT-TYPE
    SYNTAX          INTEGER { undefined(255), ansi(0), itu(1), china(2), 
                        ntt(4), ttc(5) }
    MAX-ACCESS      read-only
    STATUS          current
    DESCRIPTION     
            "The SS7 Variant value is obtained from the MTP3."
    ::= { ptSCCPSCCPNAEntry 3 }

ptSCCPSCCPNANetworkIndicator OBJECT-TYPE
    SYNTAX          INTEGER { undefined(255), ni00(0), ni01(1), ni10(2), 
                        ni11(3) }
    MAX-ACCESS      read-only
    STATUS          current
    DESCRIPTION     
            "The network indicator value is obtained from the MTP3."
    ::= { ptSCCPSCCPNAEntry 4 }

ptSCCPSCCPNAMTP3HostName OBJECT-TYPE
    SYNTAX          DisplayString (SIZE(0..255))
    MAX-ACCESS      read-only
    STATUS          current
    DESCRIPTION     
            "This attribute provides the IP host name where this SCCP process will find its MTP Level 3 process. On current systems this is always the same CPU as the SCCP and this attribute is not modifiable. The default value is localhost."
    ::= { ptSCCPSCCPNAEntry 5 }

ptSCCPSCCPNANetworkAppearance OBJECT-TYPE
    SYNTAX          Integer32 (-2147483648..2147483647)
    MAX-ACCESS      read-only
    STATUS          current
    DESCRIPTION     
            "Each Network Appearance (NA) is given a number to distinguish it as you proceed through the various levels of the SS7 stack. Each NA is effectively a new node on the network with its own Local Point Code (LPC)."
    ::= { ptSCCPSCCPNAEntry 6 }

ptSCCPSCCPNATrafficStatus OBJECT-TYPE
    SYNTAX          INTEGER { inactive(0), active(1), unlicensed(2) }
    MAX-ACCESS      read-only
    STATUS          current
    DESCRIPTION     
            "This attribute indicates the current status of this SCCP. It must read ACTIVE to process messages. Use the action button to change its status. There are certain initial configuration tasks that require traffic to be inactive, however these should not be required on a running system. There should be no operational task that required you to halt traffic, other than an action which would impact traffic by its nature. i.e. Changing the variant from ITU to ANSI."
    ::= { ptSCCPSCCPNAEntry 8 }

ptSCCPSCCPNAErrors OBJECT-TYPE
    SYNTAX          INTEGER { notLogged(0), logged(1) }
    MAX-ACCESS      read-create
    STATUS          current
    DESCRIPTION     
            "This attribute allows you to Enable or Disable the logging of SCCP error messages to the Debug Log file. These error messages are sent to the SysLog file, regardless of the setting of this attribute. However having the Errors also in the debug log helps in providing context for other activity also logged in that file. \nThe logging of SCCP errors should be set to LOGGED for all production systems."
    ::= { ptSCCPSCCPNAEntry 9 }

ptSCCPSCCPNASetupManagement OBJECT-TYPE
    SYNTAX          INTEGER { notLogged(0), logged(1) }
    MAX-ACCESS      read-create
    STATUS          current
    DESCRIPTION     
            "This attribute allows you to Enable or Disable the logging of information concerning the process startup to the Debug Log. This data is only reported at process startup time, so has no impact on the performance of a running system. \nMost production systems should set this flag to LOGGED."
    ::= { ptSCCPSCCPNAEntry 10 }

ptSCCPSCCPNAExecutionTrace OBJECT-TYPE
    SYNTAX          INTEGER { notLogged(0), logged(1) }
    MAX-ACCESS      read-create
    STATUS          current
    DESCRIPTION     
            "This attribute allows you to Enable or Disable the logging of detailed information concerning internal execution of the SCCP software. The resultant messages are intended for Sonus Networks Engineering staff and are not intended to be customer readable. \nThe Execution Trace debug flag should be set to NOT_LOGGED on all production systems so that the CPU is not unduly taxed by spurious log messages."
    ::= { ptSCCPSCCPNAEntry 11 }

ptSCCPSCCPNALayerCommunication OBJECT-TYPE
    SYNTAX          INTEGER { notLogged(0), logged(1) }
    MAX-ACCESS      read-create
    STATUS          current
    DESCRIPTION     
            "This attribute allows you to Enable or Disable the logging of information concerning the library that handles peer interaction. The log messages will be sent to the Debug Log file. \nThe resultant messages are intended for Sonus Networks Engineering staff and are not intended for customer use. \nThis debug flag should be set to NOT_LOGGED on all production systems so that the CPU is not unduly taxed by spurious log messages."
    ::= { ptSCCPSCCPNAEntry 12 }

ptSCCPSCCPNAPeerManagement OBJECT-TYPE
    SYNTAX          INTEGER { notLogged(0), logged(1) }
    MAX-ACCESS      read-create
    STATUS          current
    DESCRIPTION     
            "This attribute allows you to Enable or Disable the sending of information concerning distribution management on the SCCP peer running on a different CPU. \nThe resultant messages are intended for Sonus Networks Engineering staff and are not intended for customer use. \nThis debug flag should be set to NOT_LOGGED on all production systems so that the CPU is not unduly taxed by spurious log messages."
    ::= { ptSCCPSCCPNAEntry 13 }

ptSCCPSCCPNASS7Messages OBJECT-TYPE
    SYNTAX          INTEGER { notLogged(0), logged(1) }
    MAX-ACCESS      read-create
    STATUS          current
    DESCRIPTION     
            "This attribute allows you to Enable or Disable the sending of the contents of all SS7 messages, in a hex-dump format, to the Debug Log. \nThis flag, more so than other debug flags, can produce a very high volume of data and should be used with caution. \nMuch of the resultant information is intended for Sonus Networks Engineering staff and is not intended for customer use. \nThis debug flag should be set to NOT_LOGGED on all production systems so that the CPU is not unduly taxed by spurious log messages."
    ::= { ptSCCPSCCPNAEntry 14 }

ptSCCPSCCPNAMTP3Incoming OBJECT-TYPE
    SYNTAX          INTEGER { noOverride(0), sendToGt(1), sendToSsn(2) }
    MAX-ACCESS      read-create
    STATUS          current
    DESCRIPTION     
            "Routing override of incoming MTP3 traffic (NO OVERRIDE/SEND TO SSN/SEND TO GT). \nThis flag allows you to override the setting of the Routing Indicator of the incoming message. \nBy default, there is no override. Setting this feature to either SENT TO SSN or SENT TO GT will cause MTP3 messages to be routed on PC/SSN to a user connection or to the Global Title process. \nIf this override for 'SEND TO GT' is used, the Routing Indicator bit of the Address Indicator will not be modified. The next flag on this screen (MTP3 Incoming GT AI) can be used to set the Routing Indicator bit of the Address Indicator to GT. \nThe Default value is NO OVERRIDE."
    ::= { ptSCCPSCCPNAEntry 15 }

ptSCCPSCCPNAMTP3IncomingGTAI OBJECT-TYPE
    SYNTAX          INTEGER { disabled(0), enabled(1) }
    MAX-ACCESS      read-create
    STATUS          current
    DESCRIPTION     
            "This flag is used in conjunction with the previous flag (MTP3 Incoming) and only if that flag is set to 'SEND TO GT'. It will determine if the Routing Indicator will be modified per the forced routing of messages to Global Title processing. \nThis flag will have no effect if the MTP3 Incoming flag is set to 'NO OVERRIDE', or to 'SEND TO SSN'. \nIf the messages are being force sent to the Global Title for processing, and this flag is DISABLED, then the Address Indicator will NOT be modified. \nThe Default value is Disabled"
    ::= { ptSCCPSCCPNAEntry 16 }

ptSCCPSCCPNAMTP3IncomingGTZeroLength OBJECT-TYPE
    SYNTAX          INTEGER { disabled(0), enabled(1) }
    MAX-ACCESS      read-create
    STATUS          current
    DESCRIPTION     
            "This flag is used in conjunction with the previous flag (MTP3 Incoming) and only if that flag is set to 'SEND TO GT'. Normally messages without any global title information are not sent to Global Title. However with this flag ENABLED, messages of Zero Length can also be force routed to the Global Title process, even if they contain no Global Title information. \nThe Default value is Disabled"
    ::= { ptSCCPSCCPNAEntry 17 }

ptSCCPSCCPNAMTP3IncomingDestination OBJECT-TYPE
    SYNTAX          INTEGER { noOverrideDpc(0), calledPartyPc(1) }
    MAX-ACCESS      read-create
    STATUS          current
    DESCRIPTION     
            "This flag is used for messages routed to a user connection. Normally the point code used for that determination is taken from the Destination PC of the routing label. However this flag can be set to CALLED and this will cause MTP3 messages to be routed to the User Connection based on their Called Party Address PC. \By default, Incoming MTP3 Destination is set to DPC."
    ::= { ptSCCPSCCPNAEntry 18 }

ptSCCPSCCPNAUserIncoming OBJECT-TYPE
    SYNTAX          INTEGER { noOverride(0), sendToGt(1) }
    MAX-ACCESS      read-create
    STATUS          current
    DESCRIPTION     
            "This flag is used to force messages coming from the Signaling Gateway SUA connection, to be GTT processed before sending to the SS7 Network. This is a very unusual requirement and this flag is only in place to support a legacy system. If you plan to use this feature, please inform Customer Support. \nThe Default value is 'NO OVERRIDE.'"
    ::= { ptSCCPSCCPNAEntry 19 }

ptSCCPSCCPNAKeepAlive OBJECT-TYPE
    SYNTAX          INTEGER { disabled(0) }
    MAX-ACCESS      read-create
    STATUS          current
    DESCRIPTION     
            "This timer sets the interval at which a check between the SCCP and its user connections and its GTT connections is sent over TCP. Having a Keep Alive Timer allows the SCCP to more quickly detect a lost connection. The connection check is not required if there is a current exchange of information, and is more useful in low traffic situations. \nThe timer is seconds and the valid range is 0..1800. Setting the timer to 0 seconds disables the keep alive feature. \nThe Default value is 5 seconds."
    ::= { ptSCCPSCCPNAEntry 20 }

ptSCCPSCCPNASSTDelay OBJECT-TYPE
    SYNTAX          Integer32 (1..1800)
    MAX-ACCESS      read-create
    STATUS          current
    DESCRIPTION     
            "The SST Delay Timer sets the time in seconds between subsystem test messages (SSTs) sent to remote switches with concerned prohibited SSNs. \nThe valid range is [1..1800]. \nThe Default value is 30 seconds."
    ::= { ptSCCPSCCPNAEntry 21 }

ptSCCPSCCPNAXUDTReassembly OBJECT-TYPE
    SYNTAX          Integer32 (1..1800)
    MAX-ACCESS      read-create
    STATUS          current
    DESCRIPTION     
            "The XUDT Reassembly Timer sets the time in seconds that the system will tolerate for all the XUDT segments to arrive. \nThe valid range is [1..1800 ]. \nThe Default value is 10 seconds."
    ::= { ptSCCPSCCPNAEntry 22 }

ptSCCPSCCPNAMTPAudit OBJECT-TYPE
    SYNTAX          INTEGER { disabled(0) }
    MAX-ACCESS      read-create
    STATUS          current
    DESCRIPTION     
            "The MTP Audit Timer sets the time in seconds between MTP_AUDIT messages sent to the MTP3 to probe a certain destination PC. The next flag on this screen is a lifetime Timer which will determine how long we will continue to send these checks before giving up. \nThe MTP Audit Timer is seconds and the valid range is 0..1800. Setting the timer to 0 seconds disables the feature. \nThe Default value is 30 seconds."
    ::= { ptSCCPSCCPNAEntry 23 }

ptSCCPSCCPNAMTPAuditLifetime OBJECT-TYPE
    SYNTAX          INTEGER { off(-1), thirtySeconds(30), 
                        twoMinutes(120), fiveMinutes(300), 
                        tenMinutes(600), thirtyMinutes(1800), 
                        oneHour(3600), twoHours(7200), threeHours(10800), 
                        fourHours(14400), sixHours(21600), 
                        twelveHours(43200), oneDay(86400), 
                        twoDays(172800) }
    MAX-ACCESS      read-create
    STATUS          current
    DESCRIPTION     
            "The MTP Audit Lifetime Timer is used in conjunction with the MTP Audit Timer. The Audit Timer determines how often we will check for the availability of a point code. The Audit Lifetime Timer determines how long we will continue to send out those checks. No more audit checks are sent after expiration. \nThe allowed values for MTP Audit Lifetime Timer are: \n - OFF (meaning no expiry), \n - THIRTY_SECONDS, \n - TWO_MINUTES, \n - FIVE_MINUTES, \n - TEN_MINUTES, \n - THIRTY_MINUTES, \n - ONE_HOUR, \n - TWO_HOURS, \n - THREE_HOURS, \n - FOUR_HOURS, \n - SIX_HOURS, \n - TWELVE_HOURS, \n - ONE_DAY, \n - TWO_DAYS. \nThe Default value is OFF."
    ::= { ptSCCPSCCPNAEntry 24 }

ptSCCPSCCPNAConnectionEstablish OBJECT-TYPE
    SYNTAX          Integer32 (1..1800)
    MAX-ACCESS      read-create
    STATUS          current
    DESCRIPTION     
            "The Connection Establish Timer sets the time in seconds that the system will wait for a virtual SCCP connection to be established before it disconnects. This flag is valid for Connection Oriented SCCP only. \nThe valid range is 1..1800 seconds and the default value is 180 seconds."
    ::= { ptSCCPSCCPNAEntry 25 }

ptSCCPSCCPNAConnectionRelease OBJECT-TYPE
    SYNTAX          Integer32 (1..1800)
    MAX-ACCESS      read-create
    STATUS          current
    DESCRIPTION     
            "The Connection Release Timer sets the time in seconds that the system will wait for a connection to be released before it disconnects. This avoid hanging virtual SCCP connections due to lost messages. This flag is valid for Connection Oriented SCCP only. \nThe valid range is 1..1800 seconds and the default value is 20 seconds."
    ::= { ptSCCPSCCPNAEntry 26 }

ptSCCPSCCPNAReceiveInactive OBJECT-TYPE
    SYNTAX          Integer32 (1..1800)
    MAX-ACCESS      read-create
    STATUS          current
    DESCRIPTION     
            "The Receive Inactivity Timer sets the time in seconds that the system will tolerate receiving no new messages before sending a test message to check the virtual SCCP conversation connection. This flag is valid for Connection Oriented SCCP only. \nThe valid range is 1..1800 seconds and the default value is 660 seconds."
    ::= { ptSCCPSCCPNAEntry 27 }

ptSCCPSCCPNASendInactive OBJECT-TYPE
    SYNTAX          Integer32 (1..1800)
    MAX-ACCESS      read-create
    STATUS          current
    DESCRIPTION     
            "The Send Inactivity Timer sets the time in seconds that the system will tolerate sending no messages out on a temporary virtual connection before sending a test message to check the connection. This flag is valid for Connection Oriented SCCP only. \nThe valid range is 1..1800 seconds and the default value is 300 seconds."
    ::= { ptSCCPSCCPNAEntry 28 }

ptSCCPSCCPNAReferenceFreeze OBJECT-TYPE
    SYNTAX          Integer32 (1..1800)
    MAX-ACCESS      read-create
    STATUS          current
    DESCRIPTION     
            "The Reference Freeze Timer sets the time in seconds that the system will wait before another connection is allowed with the same local reference ID for a new virtual connection. This flag is valid for Connection Oriented SCCP only. \nThe valid range is 1..1800 seconds and the default value is 20 seconds."
    ::= { ptSCCPSCCPNAEntry 29 }

ptSCCPSCCPNASLSIncrementation OBJECT-TYPE
    SYNTAX          INTEGER { disabled(0), enabled(1) }
    MAX-ACCESS      read-create
    STATUS          current
    DESCRIPTION     
            "Backward Compatibility of the SLS incrementation. \nBy default, set to DISABLED. \nIf enabled, the SLS inside a message will be incremented by one as that N-UNITDATA request is passed through the SCCP layer. This is only applied to messages of protocol class 0. \nIn ANSI systems the SLS manipulation is a rotation and is performed by the MTP Layer 3. MTP Layer 3 is now the preferred location to deal with SLS values. \nFlags on this screen are used for interaction with specific legacy systems and custom features. If you plan on using them please inform Customer Support."
    ::= { ptSCCPSCCPNAEntry 30 }

ptSCCPSCCPNAOldEncodingOfAI OBJECT-TYPE
    SYNTAX          INTEGER { disabled(0), enabled(1) }
    MAX-ACCESS      read-create
    STATUS          current
    DESCRIPTION     
            "Backward Compatibility of Address Indicator encoding. \nThis flag deals with settings of an older User Application Protocol (or API) between the SCCP layer and the User connection or the GTT connections. \nBy default, set to DISABLED. \nIf enabled, the calling and called party address indicators will be taken from the SS7 Variant used. This means that the SSN indicator and PC indicators can be in different positions from the current SCCP API. \nFlags on this screen are used for interaction with specific legacy systems and custom features. If you plan on using them please inform Customer Support."
    ::= { ptSCCPSCCPNAEntry 31 }

ptSCCPSCCPNAOldEncodingOfCLGPAPC OBJECT-TYPE
    SYNTAX          INTEGER { disabled(0), enabled(1) }
    MAX-ACCESS      read-create
    STATUS          current
    DESCRIPTION     
            "Obsolete as of 9.0. Backward Compatibility of the Calling Party Address Point Code. \nOnly applicable for service messages (UDTS and XUDTS). \nBy default, set to DISABLED. \nIf enabled, the MTP routing label OPC is inserted in the Calling Party Address Point Code when that PC has not been included in the Global Title as per the Address Indicator. \nFlags on this screen are used for interaction with specific legacy systems and custom features. If you plan on using them please inform Customer Support."
    ::= { ptSCCPSCCPNAEntry 32 }

ptSCCPSCCPNAOldMTPAvailability OBJECT-TYPE
    SYNTAX          INTEGER { disabled(0), enabled(1) }
    MAX-ACCESS      read-create
    STATUS          current
    DESCRIPTION     
            "Backward Compatibility of the MTP availability status information. \nBy default, set to DISABLED. \nIf enabled, PC_STATE_IND messages for the MTP local states (available and not available) are not sent to the user connections, because this information did not exist in the old SCCP API. \nFlags on this screen are used for interaction with specific legacy systems and custom features. If you plan on using them please inform Customer Support."
    ::= { ptSCCPSCCPNAEntry 33 }

ptSCCPSCCPNAOldPointCodeFormat OBJECT-TYPE
    SYNTAX          INTEGER { disabled(0), enabled(1) }
    MAX-ACCESS      read-create
    STATUS          current
    DESCRIPTION     
            "Backward Compatibility of the Point Code Format for PC encoding. \nBy default, set to DISABLED. \nIf enabled, the PC values in the SCCP API are encoded in the old 8.8.8 encoding format. \nFlags on this screen are used for interaction with specific legacy systems and custom features. If you plan on using them please inform Customer Support."
    ::= { ptSCCPSCCPNAEntry 34 }

ptSCCPSCCPNASetOPCToLPCNonMgmt OBJECT-TYPE
    SYNTAX          INTEGER { disabled(0), enabled(1) }
    MAX-ACCESS      read-create
    STATUS          current
    DESCRIPTION     
            "Obsolete as of 9.0. Set OPC to LPC for non-management messages. \nBy default, set to DISABLED. \nIf enabled, the OPC will be replaced with the Local Point Code rather than the virtual point code. This flag will affect all non-management messages. \nFlags on this screen are used for interaction with specific legacy systems and custom features. If you plan on using them please inform Customer Support."
    ::= { ptSCCPSCCPNAEntry 35 }

ptSCCPSCCPNASetOPCToLPCMgmt OBJECT-TYPE
    SYNTAX          INTEGER { disabled(0), enabled(1) }
    MAX-ACCESS      read-create
    STATUS          current
    DESCRIPTION     
            "Obsolete as of 9.0. Set OPC to LPC for SCMG management messages. \nBy default, set to DISABLED. \nIf enabled, the OPC will be replaced with the Local Point Code rather than the virtual point code. This will affect only SCMG Management Messages. \nFlags on this screen are used for interaction with specific legacy systems and custom features. If you plan on using them please inform Customer Support."
    ::= { ptSCCPSCCPNAEntry 36 }

ptSCCPSCCPNANUNITDATAQoSSupport OBJECT-TYPE
    SYNTAX          INTEGER { disabled(0), enabled(1) }
    MAX-ACCESS      read-create
    STATUS          current
    DESCRIPTION     
            "Unit Data Indicator messages include Quality of Service parameter. \nBy default, set to DISABLED. Must be enabled for SUA. \nIf enabled, the N-UNIT-DATA-IND API messages to the User Connections include the Quality Of Service information. \nIf disabled, the N-UNIT-DATA-IND API messages to the User Connections will exclude the Quality of Service only if the hop counter is 0. This exception is required to process UDT versus XUDT messages. \nFlags on this screen are used for interaction with specific legacy systems and features. If you plan on using them please inform Customer Support."
    ::= { ptSCCPSCCPNAEntry 37 }

ptSCCPSCCPNASSNZeroUserSupport OBJECT-TYPE
    SYNTAX          INTEGER { disabled(0), enabled(1) }
    MAX-ACCESS      read-create
    STATUS          current
    DESCRIPTION     
            "User connections support SSN zero registration. \nBy default, set to DISABLED as the SSN zero is reserved for management messages handled by SCCP. Registration to SSN zero is only allowed with this flag ENABLED. \nFlags on this screen are used for interaction with specific legacy systems and features. If you plan on using them please inform Customer Support."
    ::= { ptSCCPSCCPNAEntry 38 }

ptSCCPSCCPNAGTTIncomingRerouting OBJECT-TYPE
    SYNTAX          INTEGER { disabled(0), enabled(1) }
    MAX-ACCESS      read-create
    STATUS          current
    DESCRIPTION     
            "Enable or disable rerouting of incoming GTT traffic back to GTT. If disabled, a UDTS will be returned on rerouting failure. \nNOTE: If enabled, special consideration on the GTT provisioning is required to make sure no circular routing is configured. \nBy default, GTT Incoming Rerouting is set to DISABLED."
    ::= { ptSCCPSCCPNAEntry 39 }

ptSCCPSCCPNAGTTIncomingCLGPC OBJECT-TYPE
    SYNTAX          INTEGER { disabled(0), enabled(1) }
    MAX-ACCESS      read-create
    STATUS          current
    DESCRIPTION     
            "Enable or disable CLG PC addition on PC/SSN routing for incoming GTT traffic. If enabled and CLG is PC/SSN but has no PC, include the OPC in the CLG to conform with relay node requirements. \nBy default, GTT Incoming CLG PC is set to ENABLED. \nDisable only for non-relay node deployments or GT routed applications such as PCE."
    ::= { ptSCCPSCCPNAEntry 40 }

ptSCCPSCCPNASSTOPCFromSSP OBJECT-TYPE
    SYNTAX          INTEGER { disabled(0), enabled(1) }
    MAX-ACCESS      read-create
    STATUS          current
    DESCRIPTION     
            "Set the SST OPC to the DPC from the original SSP message. \nBy default, set to DISABLED. \nIf enabled, the OPC will be set with the Destination Point Code that was received in the original SSP. This will affect only SST Management Messages. \nFlags on this screen are used for interaction with specific legacy systems and custom features. If you plan on using them please inform Customer Support."
    ::= { ptSCCPSCCPNAEntry 41 }

ptSCCPSCCPNASetOPCToLPC OBJECT-TYPE
    SYNTAX          INTEGER { disabled(0), enabled(1), 
                        enabledUserOnly(2) }
    MAX-ACCESS      read-create
    STATUS          current
    DESCRIPTION     
            "Set OPC to LPC for SS7 destined messages. \nBy default, set to DISABLED. \nIf set to ENABLED, the OPC will be replaced with the Local Point Code rather than the virtual point code for all messages. \nIf set to ENABLED USER ONLY, the OPC will be replaced with the LPC rather than the virtual point code for user traffic only (excluding management messages (SCMG)). \nFormerly called Set OPC to LPC Non Mgmt prior to 9.0. \nFlags on this screen are used for interaction with specific legacy systems and custom features. If you plan on using them please inform Customer Support."
    ::= { ptSCCPSCCPNAEntry 42 }

ptSCCPSCCPNASetAffectedPCToLPC OBJECT-TYPE
    SYNTAX          INTEGER { disabled(0), enabled(1) }
    MAX-ACCESS      read-create
    STATUS          current
    DESCRIPTION     
            "Set Affected PC to LPC for SCMG messages. \nBy default, set to DISABLED. \nIf enabled, the Affected PC in the SCMG messages will be replaced with the Local Point Code. \nFormerly called Set OPC to LPC Mgmt prior to 9.0. \nFlags on this screen are used for interaction with specific legacy systems and custom features. If you plan on using them please inform Customer Support."
    ::= { ptSCCPSCCPNAEntry 43 }

ptSCCPSCCPNAEncodingOfCLGPAPC OBJECT-TYPE
    SYNTAX          INTEGER { disabled(0), enabledServiceOnly(1), 
                        enabledXudtOnly(2), enabledServiceXudt(3) }
    MAX-ACCESS      read-create
    STATUS          current
    DESCRIPTION     
            "Insert the MTP3 Routing Label OPC into the Calling Party \nAddress Point Code. \nOnly applicable for service messages (UDTS and XUDTS) and XUDT. \nBy default, set to DISABLED. \nIf enabled, the MTP3 routing label OPC is inserted in the Calling Party Address Point Code when that PC has not been included in the Global Title as per the Address Indicator. \nFlags on this screen are used for interaction with specific legacy systems and custom features. If you plan on using them please inform Customer Support."
    ::= { ptSCCPSCCPNAEntry 44 }

ptSCCPSCCPNAForcedSegmentation OBJECT-TYPE
    SYNTAX          Integer32 (250..273)
    MAX-ACCESS      read-create
    STATUS          current
    DESCRIPTION     
            "Max MSU size to MTP3, segment if MSU size exceeds maximum (default 273). \nOnly applicable for non-service messages (UDT and XUDT). \nSegment size cannot exceed the attribute value. \nBy default (273), no forced segmentation is applied. \nThis feature is useful if SCCP is deployed with L4Cvtr and conversion makes the MSU exceed standard MSU size. \nFlags on this screen are used for interaction with specific legacy systems and custom features. If you plan on using them please inform Customer Support."
    ::= { ptSCCPSCCPNAEntry 45 }

ptSCCPSCCPNALPCRegistration OBJECT-TYPE
    SYNTAX          INTEGER { disabled(0), enabled(1) }
    MAX-ACCESS      read-create
    STATUS          current
    DESCRIPTION     
            "This flag is used to control the registration of the LPC with MTP3. \By default, MTP3 LPC Registration is set to ENABLED. Disabling registration will not block users from registering the LPC with SCCP. These registrations will still work normally."
    ::= { ptSCCPSCCPNAEntry 46 }

ptSCCPSCCPNAUnequippedUser OBJECT-TYPE
    SYNTAX          INTEGER { disabled(0), enabled(1) }
    MAX-ACCESS      read-create
    STATUS          current
    DESCRIPTION     
            "Return error UNEQUIPPED USER (4) if PC-SSN is unavailable. \nBy default, set to DISABLED to return SUBSYSTEM FAIL (3) as the backward compatible value. \nFlags on this screen are used for interaction with specific legacy systems and features. If you plan on using them please inform Customer Support."
    ::= { ptSCCPSCCPNAEntry 47 }

ptSCCPSCCPNASCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPSCCPNAEntry 242 }

ptSCCPSCCPNAActions OBJECT-TYPE
    SYNTAX          INTEGER { activateTraffic(1), deactivateTraffic(2), 
                        restoreDebugDefaults(3) }
    MAX-ACCESS      read-create
    STATUS          current
    DESCRIPTION     
            "The OID of all possible actions for this instance"
    ::= { ptSCCPSCCPNAEntry 252 }

ptSCCPSCCPNAParentOID OBJECT-TYPE
    SYNTAX          OBJECT IDENTIFIER
    MAX-ACCESS      read-create
    STATUS          current
    DESCRIPTION     
            "The OID of the parent object for this instance"
    ::= { ptSCCPSCCPNAEntry 253 }

ptSCCPSCCPNARowStatus OBJECT-TYPE
    SYNTAX          RowStatus
    MAX-ACCESS      read-create
    STATUS          current
    DESCRIPTION     
            "The row status for the SCCPSCCPNA table"
    ::= { ptSCCPSCCPNAEntry 254 }

ptSCCPSCCPNAIndex OBJECT-TYPE
    SYNTAX          Integer32 (-2147483648..2147483647)
    MAX-ACCESS      not-accessible
    STATUS          current
    DESCRIPTION     
            "The row number for the SCCPSCCPNA table"
    ::= { ptSCCPSCCPNAEntry 255 }

ptSCCPConcernedPCs OBJECT IDENTIFIER
    ::= { ptSCCPSCCPNA 86 }

ptSCCPConcernedPCsTable OBJECT-TYPE
    SYNTAX          SEQUENCE OF PtSCCPConcernedPCsEntry
    MAX-ACCESS      not-accessible
    STATUS          current
    DESCRIPTION     
            "No description supplied in the proxy config file."
    ::= { ptSCCPConcernedPCs 1 }

ptSCCPConcernedPCsEntry OBJECT-TYPE
    SYNTAX          PtSCCPConcernedPCsEntry
    MAX-ACCESS      not-accessible
    STATUS          current
    DESCRIPTION     
            "A sequence of SCCPConcernedPCs attributes."
    INDEX           { ptConnGroupIndex, 
                      ptSCCPConcernedPCsSCCPNAManagerIndex, 
                      ptSCCPConcernedPCsSCCPNAIndex, 
                      ptSCCPConcernedPCsIndex }
    ::= { ptSCCPConcernedPCsTable 1 }

PtSCCPConcernedPCsEntry ::=
    SEQUENCE {
        ptSCCPConcernedPCsCount         Integer32,
        ptSCCPConcernedPCsSCCPNAManagerIndex    Integer32,
        ptSCCPConcernedPCsSCCPNAIndex   Integer32,
        ptSCCPConcernedPCsParentOID     OBJECT IDENTIFIER,
        ptSCCPConcernedPCsRowStatus     RowStatus,
        ptSCCPConcernedPCsIndex         Integer32
    }

ptSCCPConcernedPCsCount OBJECT-TYPE
    SYNTAX          Integer32 (-2147483648..2147483647)
    MAX-ACCESS      read-only
    STATUS          current
    DESCRIPTION     
            "Number of Concerned PCs."
    ::= { ptSCCPConcernedPCsEntry 1 }

ptSCCPConcernedPCsSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPConcernedPCsEntry 242 }

ptSCCPConcernedPCsSCCPNAIndex OBJECT-TYPE
    SYNTAX          Integer32 (-2147483648..2147483647)
    MAX-ACCESS      not-accessible
    STATUS          current
    DESCRIPTION     
            "This is the index of the parent type for this object.
             This parent type is SCCPNA."
    ::= { ptSCCPConcernedPCsEntry 243 }

ptSCCPConcernedPCsParentOID OBJECT-TYPE
    SYNTAX          OBJECT IDENTIFIER
    MAX-ACCESS      read-create
    STATUS          current
    DESCRIPTION     
            "The OID of the parent object for this instance"
    ::= { ptSCCPConcernedPCsEntry 253 }

ptSCCPConcernedPCsRowStatus OBJECT-TYPE
    SYNTAX          RowStatus
    MAX-ACCESS      read-create
    STATUS          current
    DESCRIPTION     
            "The row status for the SCCPConcernedPCs table"
    ::= { ptSCCPConcernedPCsEntry 254 }

ptSCCPConcernedPCsIndex OBJECT-TYPE
    SYNTAX          Integer32 (-2147483648..2147483647)
    MAX-ACCESS      not-accessible
    STATUS          current
    DESCRIPTION     
            "The row number for the SCCPConcernedPCs table"
    ::= { ptSCCPConcernedPCsEntry 255 }

ptSCCPConcernedPC OBJECT IDENTIFIER
    ::= { ptSCCPConcernedPCs 88 }

ptSCCPConcernedPCTable OBJECT-TYPE
    SYNTAX          SEQUENCE OF PtSCCPConcernedPCEntry
    MAX-ACCESS      not-accessible
    STATUS          current
    DESCRIPTION     
            "No description supplied in the proxy config file."
    ::= { ptSCCPConcernedPC 1 }

ptSCCPConcernedPCEntry OBJECT-TYPE
    SYNTAX          PtSCCPConcernedPCEntry
    MAX-ACCESS      not-accessible
    STATUS          current
    DESCRIPTION     
            "A sequence of SCCPConcernedPC attributes."
    INDEX           { ptConnGroupIndex, 
                      ptSCCPConcernedPCSCCPNAManagerIndex, 
                      ptSCCPConcernedPCSCCPNAIndex, 
                      ptSCCPConcernedPCConcernedPCsIndex, 
                      ptSCCPConcernedPCIndex }
    ::= { ptSCCPConcernedPCTable 1 }

PtSCCPConcernedPCEntry ::=
    SEQUENCE {
        ptSCCPConcernedPCPointCode      Integer32,
        ptSCCPConcernedPCStatus         INTEGER,
        ptSCCPConcernedPCConcernedSSNs  Integer32,
        ptSCCPConcernedPCSCCPNAManagerIndex   Integer32,
        ptSCCPConcernedPCSCCPNAIndex    Integer32,
        ptSCCPConcernedPCConcernedPCsIndex  Integer32,
        ptSCCPConcernedPCParentOID      OBJECT IDENTIFIER,
        ptSCCPConcernedPCRowStatus      RowStatus,
        ptSCCPConcernedPCIndex          Integer32
    }

ptSCCPConcernedPCPointCode OBJECT-TYPE
    SYNTAX          Integer32 (-2147483648..2147483647)
    MAX-ACCESS      read-only
    STATUS          current
    DESCRIPTION     
            "Point Code SCCP defines as known."
    ::= { ptSCCPConcernedPCEntry 1 }

ptSCCPConcernedPCStatus OBJECT-TYPE
    SYNTAX          INTEGER { unavailable(0), available(1) }
    MAX-ACCESS      read-only
    STATUS          current
    DESCRIPTION     
            "Concerned PC status (AVAILABLE/UNAVAILABLE)."
    ::= { ptSCCPConcernedPCEntry 2 }

ptSCCPConcernedPCConcernedSSNs OBJECT-TYPE
    SYNTAX          Integer32 (-2147483648..2147483647)
    MAX-ACCESS      read-only
    STATUS          current
    DESCRIPTION     
            "Number of Concerned SSNs."
    ::= { ptSCCPConcernedPCEntry 3 }

ptSCCPConcernedPCSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPConcernedPCEntry 242 }

ptSCCPConcernedPCSCCPNAIndex OBJECT-TYPE
    SYNTAX          Integer32 (-2147483648..2147483647)
    MAX-ACCESS      not-accessible
    STATUS          current
    DESCRIPTION     
            "This is the index of the parent type for this object.
             This parent type is SCCPNA."
    ::= { ptSCCPConcernedPCEntry 243 }

ptSCCPConcernedPCConcernedPCsIndex OBJECT-TYPE
    SYNTAX          Integer32 (-2147483648..2147483647)
    MAX-ACCESS      not-accessible
    STATUS          current
    DESCRIPTION     
            "This is the index of the parent type for this object.
             This parent type is ConcernedPCs."
    ::= { ptSCCPConcernedPCEntry 244 }

ptSCCPConcernedPCParentOID OBJECT-TYPE
    SYNTAX          OBJECT IDENTIFIER
    MAX-ACCESS      read-create
    STATUS          current
    DESCRIPTION     
            "The OID of the parent object for this instance"
    ::= { ptSCCPConcernedPCEntry 253 }

ptSCCPConcernedPCRowStatus OBJECT-TYPE
    SYNTAX          RowStatus
    MAX-ACCESS      read-create
    STATUS          current
    DESCRIPTION     
            "The row status for the SCCPConcernedPC table"
    ::= { ptSCCPConcernedPCEntry 254 }

ptSCCPConcernedPCIndex OBJECT-TYPE
    SYNTAX          Integer32 (-2147483648..2147483647)
    MAX-ACCESS      not-accessible
    STATUS          current
    DESCRIPTION     
            "The row number for the SCCPConcernedPC table"
    ::= { ptSCCPConcernedPCEntry 255 }

ptSCCPConcernedSSN OBJECT IDENTIFIER
    ::= { ptSCCPConcernedPC 89 }

ptSCCPConcernedSSNTable OBJECT-TYPE
    SYNTAX          SEQUENCE OF PtSCCPConcernedSSNEntry
    MAX-ACCESS      not-accessible
    STATUS          current
    DESCRIPTION     
            "No description supplied in the proxy config file."
    ::= { ptSCCPConcernedSSN 1 }

ptSCCPConcernedSSNEntry OBJECT-TYPE
    SYNTAX          PtSCCPConcernedSSNEntry
    MAX-ACCESS      not-accessible
    STATUS          current
    DESCRIPTION     
            "A sequence of SCCPConcernedSSN attributes."
    INDEX           { ptConnGroupIndex, 
                      ptSCCPConcernedSSNSCCPNAManagerIndex, 
                      ptSCCPConcernedSSNSCCPNAIndex, 
                      ptSCCPConcernedSSNConcernedPCsIndex, 
                      ptSCCPConcernedSSNConcernedPCIndex, 
                      ptSCCPConcernedSSNIndex }
    ::= { ptSCCPConcernedSSNTable 1 }

PtSCCPConcernedSSNEntry ::=
    SEQUENCE {
        ptSCCPConcernedSSNSSN           Integer32,
        ptSCCPConcernedSSNStatus        INTEGER,
        ptSCCPConcernedSSNSCCPNAManagerIndex    Integer32,
        ptSCCPConcernedSSNSCCPNAIndex   Integer32,
        ptSCCPConcernedSSNConcernedPCsIndex   Integer32,
        ptSCCPConcernedSSNConcernedPCIndex  Integer32,
        ptSCCPConcernedSSNParentOID     OBJECT IDENTIFIER,
        ptSCCPConcernedSSNRowStatus     RowStatus,
        ptSCCPConcernedSSNIndex         Integer32
    }

ptSCCPConcernedSSNSSN OBJECT-TYPE
    SYNTAX          Integer32 (-2147483648..2147483647)
    MAX-ACCESS      read-only
    STATUS          current
    DESCRIPTION     
            "Subsystem Number for the Concerned PC."
    ::= { ptSCCPConcernedSSNEntry 1 }

ptSCCPConcernedSSNStatus OBJECT-TYPE
    SYNTAX          INTEGER { prohibited(0), allowed(1) }
    MAX-ACCESS      read-only
    STATUS          current
    DESCRIPTION     
            "Concerned SSN status (ALLOWED/PROHIBITED)."
    ::= { ptSCCPConcernedSSNEntry 2 }

ptSCCPConcernedSSNSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPConcernedSSNEntry 242 }

ptSCCPConcernedSSNSCCPNAIndex OBJECT-TYPE
    SYNTAX          Integer32 (-2147483648..2147483647)
    MAX-ACCESS      not-accessible
    STATUS          current
    DESCRIPTION     
            "This is the index of the parent type for this object.
             This parent type is SCCPNA."
    ::= { ptSCCPConcernedSSNEntry 243 }

ptSCCPConcernedSSNConcernedPCsIndex OBJECT-TYPE
    SYNTAX          Integer32 (-2147483648..2147483647)
    MAX-ACCESS      not-accessible
    STATUS          current
    DESCRIPTION     
            "This is the index of the parent type for this object.
             This parent type is ConcernedPCs."
    ::= { ptSCCPConcernedSSNEntry 244 }

ptSCCPConcernedSSNConcernedPCIndex OBJECT-TYPE
    SYNTAX          Integer32 (-2147483648..2147483647)
    MAX-ACCESS      not-accessible
    STATUS          current
    DESCRIPTION     
            "This is the index of the parent type for this object.
             This parent type is ConcernedPC."
    ::= { ptSCCPConcernedSSNEntry 245 }

ptSCCPConcernedSSNParentOID OBJECT-TYPE
    SYNTAX          OBJECT IDENTIFIER
    MAX-ACCESS      read-create
    STATUS          current
    DESCRIPTION     
            "The OID of the parent object for this instance"
    ::= { ptSCCPConcernedSSNEntry 253 }

ptSCCPConcernedSSNRowStatus OBJECT-TYPE
    SYNTAX          RowStatus
    MAX-ACCESS      read-create
    STATUS          current
    DESCRIPTION     
            "The row status for the SCCPConcernedSSN table"
    ::= { ptSCCPConcernedSSNEntry 254 }

ptSCCPConcernedSSNIndex OBJECT-TYPE
    SYNTAX          Integer32 (-2147483648..2147483647)
    MAX-ACCESS      not-accessible
    STATUS          current
    DESCRIPTION     
            "The row number for the SCCPConcernedSSN table"
    ::= { ptSCCPConcernedSSNEntry 255 }

ptSCCPUserConnections OBJECT IDENTIFIER
    ::= { ptSCCPSCCPNA 90 }

ptSCCPUserConnectionsTable OBJECT-TYPE
    SYNTAX          SEQUENCE OF PtSCCPUserConnectionsEntry
    MAX-ACCESS      not-accessible
    STATUS          current
    DESCRIPTION     
            "No description supplied in the proxy config file."
    ::= { ptSCCPUserConnections 1 }

ptSCCPUserConnectionsEntry OBJECT-TYPE
    SYNTAX          PtSCCPUserConnectionsEntry
    MAX-ACCESS      not-accessible
    STATUS          current
    DESCRIPTION     
            "A sequence of SCCPUserConnections attributes."
    INDEX           { ptConnGroupIndex, 
                      ptSCCPUserConnectionsSCCPNAManagerIndex, 
                      ptSCCPUserConnectionsSCCPNAIndex, 
                      ptSCCPUserConnectionsIndex }
    ::= { ptSCCPUserConnectionsTable 1 }

PtSCCPUserConnectionsEntry ::=
    SEQUENCE {
        ptSCCPUserConnectionsCount      Integer32,
        ptSCCPUserConnectionsSCCPNAManagerIndex       Integer32,
        ptSCCPUserConnectionsSCCPNAIndex Integer32,
        ptSCCPUserConnectionsParentOID  OBJECT IDENTIFIER,
        ptSCCPUserConnectionsRowStatus  RowStatus,
        ptSCCPUserConnectionsIndex      Integer32
    }

ptSCCPUserConnectionsCount OBJECT-TYPE
    SYNTAX          Integer32 (-2147483648..2147483647)
    MAX-ACCESS      read-only
    STATUS          current
    DESCRIPTION     
            "Number of User Connections"
    ::= { ptSCCPUserConnectionsEntry 1 }

ptSCCPUserConnectionsSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPUserConnectionsEntry 242 }

ptSCCPUserConnectionsSCCPNAIndex OBJECT-TYPE
    SYNTAX          Integer32 (-2147483648..2147483647)
    MAX-ACCESS      not-accessible
    STATUS          current
    DESCRIPTION     
            "This is the index of the parent type for this object.
             This parent type is SCCPNA."
    ::= { ptSCCPUserConnectionsEntry 243 }

ptSCCPUserConnectionsParentOID OBJECT-TYPE
    SYNTAX          OBJECT IDENTIFIER
    MAX-ACCESS      read-create
    STATUS          current
    DESCRIPTION     
            "The OID of the parent object for this instance"
    ::= { ptSCCPUserConnectionsEntry 253 }

ptSCCPUserConnectionsRowStatus OBJECT-TYPE
    SYNTAX          RowStatus
    MAX-ACCESS      read-create
    STATUS          current
    DESCRIPTION     
            "The row status for the SCCPUserConnections table"
    ::= { ptSCCPUserConnectionsEntry 254 }

ptSCCPUserConnectionsIndex OBJECT-TYPE
    SYNTAX          Integer32 (-2147483648..2147483647)
    MAX-ACCESS      not-accessible
    STATUS          current
    DESCRIPTION     
            "The row number for the SCCPUserConnections table"
    ::= { ptSCCPUserConnectionsEntry 255 }

ptSCCPUserConnection OBJECT IDENTIFIER
    ::= { ptSCCPUserConnections 91 }

ptSCCPUserConnectionTable OBJECT-TYPE
    SYNTAX          SEQUENCE OF PtSCCPUserConnectionEntry
    MAX-ACCESS      not-accessible
    STATUS          current
    DESCRIPTION     
            "No description supplied in the proxy config file."
    ::= { ptSCCPUserConnection 1 }

ptSCCPUserConnectionEntry OBJECT-TYPE
    SYNTAX          PtSCCPUserConnectionEntry
    MAX-ACCESS      not-accessible
    STATUS          current
    DESCRIPTION     
            "A sequence of SCCPUserConnection attributes."
    INDEX           { ptConnGroupIndex, 
                      ptSCCPUserConnectionSCCPNAManagerIndex, 
                      ptSCCPUserConnectionSCCPNAIndex, 
                      ptSCCPUserConnectionUserConnectionsIndex, 
                      ptSCCPUserConnectionIndex }
    ::= { ptSCCPUserConnectionTable 1 }

PtSCCPUserConnectionEntry ::=
    SEQUENCE {
        ptSCCPUserConnectionPeerID      Integer32,
        ptSCCPUserConnectionContext     DisplayString,
        ptSCCPUserConnectionConnectionID Integer32,
        ptSCCPUserConnectionRegisteredPCSSNs    Integer32,
        ptSCCPUserConnectionRegisteredAppIDs    Integer32,
        ptSCCPUserConnectionReassemblySupport     INTEGER,
        ptSCCPUserConnectionUAPVersion  Integer32,
        ptSCCPUserConnectionSCCPNAManagerIndex      Integer32,
        ptSCCPUserConnectionSCCPNAIndex Integer32,
        ptSCCPUserConnectionUserConnectionsIndex        Integer32,
        ptSCCPUserConnectionActions     INTEGER,
        ptSCCPUserConnectionParentOID   OBJECT IDENTIFIER,
        ptSCCPUserConnectionRowStatus   RowStatus,
        ptSCCPUserConnectionIndex       Integer32
    }

ptSCCPUserConnectionPeerID OBJECT-TYPE
    SYNTAX          Integer32 (-2147483648..2147483647)
    MAX-ACCESS      read-only
    STATUS          current
    DESCRIPTION     
            "Peer Identifier from LDL configuration."
    ::= { ptSCCPUserConnectionEntry 1 }

ptSCCPUserConnectionContext OBJECT-TYPE
    SYNTAX          DisplayString (SIZE(0..255))
    MAX-ACCESS      read-only
    STATUS          current
    DESCRIPTION     
            "IP and port of this User Connection."
    ::= { ptSCCPUserConnectionEntry 2 }

ptSCCPUserConnectionConnectionID OBJECT-TYPE
    SYNTAX          Integer32 (-2147483648..2147483647)
    MAX-ACCESS      read-only
    STATUS          current
    DESCRIPTION     
            "Unique User Connection identifier for this peer ID."
    ::= { ptSCCPUserConnectionEntry 3 }

ptSCCPUserConnectionRegisteredPCSSNs OBJECT-TYPE
    SYNTAX          Integer32 (-2147483648..2147483647)
    MAX-ACCESS      read-only
    STATUS          current
    DESCRIPTION     
            "Number of Registered PC-SSNs on this User Connection."
    ::= { ptSCCPUserConnectionEntry 4 }

ptSCCPUserConnectionRegisteredAppIDs OBJECT-TYPE
    SYNTAX          Integer32 (-2147483648..2147483647)
    MAX-ACCESS      read-only
    STATUS          current
    DESCRIPTION     
            "Number of Registered AppIDs on this User Connection."
    ::= { ptSCCPUserConnectionEntry 5 }

ptSCCPUserConnectionReassemblySupport OBJECT-TYPE
    SYNTAX          INTEGER { disabled(0), enabled(1) }
    MAX-ACCESS      read-only
    STATUS          current
    DESCRIPTION     
            "XUDT segment reassembly support feature."
    ::= { ptSCCPUserConnectionEntry 6 }

ptSCCPUserConnectionUAPVersion OBJECT-TYPE
    SYNTAX          Integer32 (-2147483648..2147483647)
    MAX-ACCESS      read-only
    STATUS          current
    DESCRIPTION     
            "UAP protocol version received on this User Connection."
    ::= { ptSCCPUserConnectionEntry 7 }

ptSCCPUserConnectionSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPUserConnectionEntry 242 }

ptSCCPUserConnectionSCCPNAIndex OBJECT-TYPE
    SYNTAX          Integer32 (-2147483648..2147483647)
    MAX-ACCESS      not-accessible
    STATUS          current
    DESCRIPTION     
            "This is the index of the parent type for this object.
             This parent type is SCCPNA."
    ::= { ptSCCPUserConnectionEntry 243 }

ptSCCPUserConnectionUserConnectionsIndex OBJECT-TYPE
    SYNTAX          Integer32 (-2147483648..2147483647)
    MAX-ACCESS      not-accessible
    STATUS          current
    DESCRIPTION     
            "This is the index of the parent type for this object.
             This parent type is UserConnections."
    ::= { ptSCCPUserConnectionEntry 244 }

ptSCCPUserConnectionActions OBJECT-TYPE
    SYNTAX          INTEGER { terminate(1) }
    MAX-ACCESS      read-create
    STATUS          current
    DESCRIPTION     
            "The OID of all possible actions for this instance"
    ::= { ptSCCPUserConnectionEntry 252 }

ptSCCPUserConnectionParentOID OBJECT-TYPE
    SYNTAX          OBJECT IDENTIFIER
    MAX-ACCESS      read-create
    STATUS          current
    DESCRIPTION     
            "The OID of the parent object for this instance"
    ::= { ptSCCPUserConnectionEntry 253 }

ptSCCPUserConnectionRowStatus OBJECT-TYPE
    SYNTAX          RowStatus
    MAX-ACCESS      read-create
    STATUS          current
    DESCRIPTION     
            "The row status for the SCCPUserConnection table"
    ::= { ptSCCPUserConnectionEntry 254 }

ptSCCPUserConnectionIndex OBJECT-TYPE
    SYNTAX          Integer32 (-2147483648..2147483647)
    MAX-ACCESS      not-accessible
    STATUS          current
    DESCRIPTION     
            "The row number for the SCCPUserConnection table"
    ::= { ptSCCPUserConnectionEntry 255 }

ptSCCPRegisteredPCSSN OBJECT IDENTIFIER
    ::= { ptSCCPUserConnection 92 }

ptSCCPRegisteredPCSSNTable OBJECT-TYPE
    SYNTAX          SEQUENCE OF PtSCCPRegisteredPCSSNEntry
    MAX-ACCESS      not-accessible
    STATUS          current
    DESCRIPTION     
            "No description supplied in the proxy config file."
    ::= { ptSCCPRegisteredPCSSN 1 }

ptSCCPRegisteredPCSSNEntry OBJECT-TYPE
    SYNTAX          PtSCCPRegisteredPCSSNEntry
    MAX-ACCESS      not-accessible
    STATUS          current
    DESCRIPTION     
            "A sequence of SCCPRegisteredPCSSN attributes."
    INDEX           { ptConnGroupIndex, 
                      ptSCCPRegisteredPCSSNSCCPNAManagerIndex, 
                      ptSCCPRegisteredPCSSNSCCPNAIndex, 
                      ptSCCPRegisteredPCSSNUserConnectionsIndex, 
                      ptSCCPRegisteredPCSSNUserConnectionIndex, 
                      ptSCCPRegisteredPCSSNIndex }
    ::= { ptSCCPRegisteredPCSSNTable 1 }

PtSCCPRegisteredPCSSNEntry ::=
    SEQUENCE {
        ptSCCPRegisteredPCSSNPointCode  Integer32,
        ptSCCPRegisteredPCSSNSSN        Integer32,
        ptSCCPRegisteredPCSSNStatus     INTEGER,
        ptSCCPRegisteredPCSSNSCCPNAManagerIndex       Integer32,
        ptSCCPRegisteredPCSSNSCCPNAIndex Integer32,
        ptSCCPRegisteredPCSSNUserConnectionsIndex         Integer32,
        ptSCCPRegisteredPCSSNUserConnectionIndex        Integer32,
        ptSCCPRegisteredPCSSNParentOID  OBJECT IDENTIFIER,
        ptSCCPRegisteredPCSSNRowStatus  RowStatus,
        ptSCCPRegisteredPCSSNIndex      Integer32
    }

ptSCCPRegisteredPCSSNPointCode OBJECT-TYPE
    SYNTAX          Integer32 (-2147483648..2147483647)
    MAX-ACCESS      read-only
    STATUS          current
    DESCRIPTION     
            "Point Code registered by the User Connection."
    ::= { ptSCCPRegisteredPCSSNEntry 1 }

ptSCCPRegisteredPCSSNSSN OBJECT-TYPE
    SYNTAX          Integer32 (-2147483648..2147483647)
    MAX-ACCESS      read-only
    STATUS          current
    DESCRIPTION     
            "Subsystem Number registered by the User Connection."
    ::= { ptSCCPRegisteredPCSSNEntry 2 }

ptSCCPRegisteredPCSSNStatus OBJECT-TYPE
    SYNTAX          INTEGER { prohibited(0), allowed(1) }
    MAX-ACCESS      read-only
    STATUS          current
    DESCRIPTION     
            "PC-SSN registration status (ALLOWED/PROHIBITED)."
    ::= { ptSCCPRegisteredPCSSNEntry 3 }

ptSCCPRegisteredPCSSNSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRegisteredPCSSNEntry 242 }

ptSCCPRegisteredPCSSNSCCPNAIndex OBJECT-TYPE
    SYNTAX          Integer32 (-2147483648..2147483647)
    MAX-ACCESS      not-accessible
    STATUS          current
    DESCRIPTION     
            "This is the index of the parent type for this object.
             This parent type is SCCPNA."
    ::= { ptSCCPRegisteredPCSSNEntry 243 }

ptSCCPRegisteredPCSSNUserConnectionsIndex OBJECT-TYPE
    SYNTAX          Integer32 (-2147483648..2147483647)
    MAX-ACCESS      not-accessible
    STATUS          current
    DESCRIPTION     
            "This is the index of the parent type for this object.
             This parent type is UserConnections."
    ::= { ptSCCPRegisteredPCSSNEntry 244 }

ptSCCPRegisteredPCSSNUserConnectionIndex OBJECT-TYPE
    SYNTAX          Integer32 (-2147483648..2147483647)
    MAX-ACCESS      not-accessible
    STATUS          current
    DESCRIPTION     
            "This is the index of the parent type for this object.
             This parent type is UserConnection."
    ::= { ptSCCPRegisteredPCSSNEntry 245 }

ptSCCPRegisteredPCSSNParentOID OBJECT-TYPE
    SYNTAX          OBJECT IDENTIFIER
    MAX-ACCESS      read-create
    STATUS          current
    DESCRIPTION     
            "The OID of the parent object for this instance"
    ::= { ptSCCPRegisteredPCSSNEntry 253 }

ptSCCPRegisteredPCSSNRowStatus OBJECT-TYPE
    SYNTAX          RowStatus
    MAX-ACCESS      read-create
    STATUS          current
    DESCRIPTION     
            "The row status for the SCCPRegisteredPCSSN table"
    ::= { ptSCCPRegisteredPCSSNEntry 254 }

ptSCCPRegisteredPCSSNIndex OBJECT-TYPE
    SYNTAX          Integer32 (-2147483648..2147483647)
    MAX-ACCESS      not-accessible
    STATUS          current
    DESCRIPTION     
            "The row number for the SCCPRegisteredPCSSN table"
    ::= { ptSCCPRegisteredPCSSNEntry 255 }

ptSCCPRegisteredUserAppID OBJECT IDENTIFIER
    ::= { ptSCCPUserConnection 96 }

ptSCCPRegisteredUserAppIDTable OBJECT-TYPE
    SYNTAX          SEQUENCE OF PtSCCPRegisteredUserAppIDEntry
    MAX-ACCESS      not-accessible
    STATUS          current
    DESCRIPTION     
            "No description supplied in the proxy config file."
    ::= { ptSCCPRegisteredUserAppID 1 }

ptSCCPRegisteredUserAppIDEntry OBJECT-TYPE
    SYNTAX          PtSCCPRegisteredUserAppIDEntry
    MAX-ACCESS      not-accessible
    STATUS          current
    DESCRIPTION     
            "A sequence of SCCPRegisteredUserAppID attributes."
    INDEX           { ptConnGroupIndex, 
                      ptSCCPRegisteredUserAppIDSCCPNAManagerIndex, 
                      ptSCCPRegisteredUserAppIDSCCPNAIndex, 
                      ptSCCPRegisteredUserAppIDUserConnectionsIndex, 
                      ptSCCPRegisteredUserAppIDUserConnectionIndex, 
                      ptSCCPRegisteredUserAppIDIndex }
    ::= { ptSCCPRegisteredUserAppIDTable 1 }

PtSCCPRegisteredUserAppIDEntry ::=
    SEQUENCE {
        ptSCCPRegisteredUserAppIDName   DisplayString,
        ptSCCPRegisteredUserAppIDRegistrationMode         INTEGER,
        ptSCCPRegisteredUserAppIDSCCPNAManagerIndex           Integer32,
        ptSCCPRegisteredUserAppIDSCCPNAIndex    Integer32,
        ptSCCPRegisteredUserAppIDUserConnectionsIndex             Integer32,
        ptSCCPRegisteredUserAppIDUserConnectionIndex            Integer32,
        ptSCCPRegisteredUserAppIDParentOID  OBJECT IDENTIFIER,
        ptSCCPRegisteredUserAppIDRowStatus  RowStatus,
        ptSCCPRegisteredUserAppIDIndex  Integer32
    }

ptSCCPRegisteredUserAppIDName OBJECT-TYPE
    SYNTAX          DisplayString (SIZE(0..255))
    MAX-ACCESS      read-only
    STATUS          current
    DESCRIPTION     
            "Application Identifier registered by the User Connection."
    ::= { ptSCCPRegisteredUserAppIDEntry 1 }

ptSCCPRegisteredUserAppIDRegistrationMode OBJECT-TYPE
    SYNTAX          INTEGER { unique(0), loadShare(1) }
    MAX-ACCESS      read-only
    STATUS          current
    DESCRIPTION     
            "Application Identifier registration mode"
    ::= { ptSCCPRegisteredUserAppIDEntry 2 }

ptSCCPRegisteredUserAppIDSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRegisteredUserAppIDEntry 242 }

ptSCCPRegisteredUserAppIDSCCPNAIndex OBJECT-TYPE
    SYNTAX          Integer32 (-2147483648..2147483647)
    MAX-ACCESS      not-accessible
    STATUS          current
    DESCRIPTION     
            "This is the index of the parent type for this object.
             This parent type is SCCPNA."
    ::= { ptSCCPRegisteredUserAppIDEntry 243 }

ptSCCPRegisteredUserAppIDUserConnectionsIndex OBJECT-TYPE
    SYNTAX          Integer32 (-2147483648..2147483647)
    MAX-ACCESS      not-accessible
    STATUS          current
    DESCRIPTION     
            "This is the index of the parent type for this object.
             This parent type is UserConnections."
    ::= { ptSCCPRegisteredUserAppIDEntry 244 }

ptSCCPRegisteredUserAppIDUserConnectionIndex OBJECT-TYPE
    SYNTAX          Integer32 (-2147483648..2147483647)
    MAX-ACCESS      not-accessible
    STATUS          current
    DESCRIPTION     
            "This is the index of the parent type for this object.
             This parent type is UserConnection."
    ::= { ptSCCPRegisteredUserAppIDEntry 245 }

ptSCCPRegisteredUserAppIDParentOID OBJECT-TYPE
    SYNTAX          OBJECT IDENTIFIER
    MAX-ACCESS      read-create
    STATUS          current
    DESCRIPTION     
            "The OID of the parent object for this instance"
    ::= { ptSCCPRegisteredUserAppIDEntry 253 }

ptSCCPRegisteredUserAppIDRowStatus OBJECT-TYPE
    SYNTAX          RowStatus
    MAX-ACCESS      read-create
    STATUS          current
    DESCRIPTION     
            "The row status for the SCCPRegisteredUserAppID table"
    ::= { ptSCCPRegisteredUserAppIDEntry 254 }

ptSCCPRegisteredUserAppIDIndex OBJECT-TYPE
    SYNTAX          Integer32 (-2147483648..2147483647)
    MAX-ACCESS      not-accessible
    STATUS          current
    DESCRIPTION     
            "The row number for the SCCPRegisteredUserAppID table"
    ::= { ptSCCPRegisteredUserAppIDEntry 255 }

ptSCCPGTTConnections OBJECT IDENTIFIER
    ::= { ptSCCPSCCPNA 93 }

ptSCCPGTTConnectionsTable OBJECT-TYPE
    SYNTAX          SEQUENCE OF PtSCCPGTTConnectionsEntry
    MAX-ACCESS      not-accessible
    STATUS          current
    DESCRIPTION     
            "No description supplied in the proxy config file."
    ::= { ptSCCPGTTConnections 1 }

ptSCCPGTTConnectionsEntry OBJECT-TYPE
    SYNTAX          PtSCCPGTTConnectionsEntry
    MAX-ACCESS      not-accessible
    STATUS          current
    DESCRIPTION     
            "A sequence of SCCPGTTConnections attributes."
    INDEX           { ptConnGroupIndex, 
                      ptSCCPGTTConnectionsSCCPNAManagerIndex, 
                      ptSCCPGTTConnectionsSCCPNAIndex, 
                      ptSCCPGTTConnectionsIndex }
    ::= { ptSCCPGTTConnectionsTable 1 }

PtSCCPGTTConnectionsEntry ::=
    SEQUENCE {
        ptSCCPGTTConnectionsCount       Integer32,
        ptSCCPGTTConnectionsSCCPNAManagerIndex      Integer32,
        ptSCCPGTTConnectionsSCCPNAIndex Integer32,
        ptSCCPGTTConnectionsParentOID   OBJECT IDENTIFIER,
        ptSCCPGTTConnectionsRowStatus   RowStatus,
        ptSCCPGTTConnectionsIndex       Integer32
    }

ptSCCPGTTConnectionsCount OBJECT-TYPE
    SYNTAX          Integer32 (-2147483648..2147483647)
    MAX-ACCESS      read-only
    STATUS          current
    DESCRIPTION     
            "Number of GTT Connections."
    ::= { ptSCCPGTTConnectionsEntry 1 }

ptSCCPGTTConnectionsSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPGTTConnectionsEntry 242 }

ptSCCPGTTConnectionsSCCPNAIndex OBJECT-TYPE
    SYNTAX          Integer32 (-2147483648..2147483647)
    MAX-ACCESS      not-accessible
    STATUS          current
    DESCRIPTION     
            "This is the index of the parent type for this object.
             This parent type is SCCPNA."
    ::= { ptSCCPGTTConnectionsEntry 243 }

ptSCCPGTTConnectionsParentOID OBJECT-TYPE
    SYNTAX          OBJECT IDENTIFIER
    MAX-ACCESS      read-create
    STATUS          current
    DESCRIPTION     
            "The OID of the parent object for this instance"
    ::= { ptSCCPGTTConnectionsEntry 253 }

ptSCCPGTTConnectionsRowStatus OBJECT-TYPE
    SYNTAX          RowStatus
    MAX-ACCESS      read-create
    STATUS          current
    DESCRIPTION     
            "The row status for the SCCPGTTConnections table"
    ::= { ptSCCPGTTConnectionsEntry 254 }

ptSCCPGTTConnectionsIndex OBJECT-TYPE
    SYNTAX          Integer32 (-2147483648..2147483647)
    MAX-ACCESS      not-accessible
    STATUS          current
    DESCRIPTION     
            "The row number for the SCCPGTTConnections table"
    ::= { ptSCCPGTTConnectionsEntry 255 }

ptSCCPGTTConnection OBJECT IDENTIFIER
    ::= { ptSCCPGTTConnections 94 }

ptSCCPGTTConnectionTable OBJECT-TYPE
    SYNTAX          SEQUENCE OF PtSCCPGTTConnectionEntry
    MAX-ACCESS      not-accessible
    STATUS          current
    DESCRIPTION     
            "No description supplied in the proxy config file."
    ::= { ptSCCPGTTConnection 1 }

ptSCCPGTTConnectionEntry OBJECT-TYPE
    SYNTAX          PtSCCPGTTConnectionEntry
    MAX-ACCESS      not-accessible
    STATUS          current
    DESCRIPTION     
            "A sequence of SCCPGTTConnection attributes."
    INDEX           { ptConnGroupIndex, 
                      ptSCCPGTTConnectionSCCPNAManagerIndex, 
                      ptSCCPGTTConnectionSCCPNAIndex, 
                      ptSCCPGTTConnectionGTTConnectionsIndex, 
                      ptSCCPGTTConnectionIndex }
    ::= { ptSCCPGTTConnectionTable 1 }

PtSCCPGTTConnectionEntry ::=
    SEQUENCE {
        ptSCCPGTTConnectionPeerID       Integer32,
        ptSCCPGTTConnectionContext      DisplayString,
        ptSCCPGTTConnectionConnectionID Integer32,
        ptSCCPGTTConnectionRegisteredPCs Integer32,
        ptSCCPGTTConnectionRegisteredAppIDs   Integer32,
        ptSCCPGTTConnectionReassemblySupport    INTEGER,
        ptSCCPGTTConnectionUAPVersion   Integer32,
        ptSCCPGTTConnectionSCCPNAManagerIndex     Integer32,
        ptSCCPGTTConnectionSCCPNAIndex  Integer32,
        ptSCCPGTTConnectionGTTConnectionsIndex      Integer32,
        ptSCCPGTTConnectionActions      INTEGER,
        ptSCCPGTTConnectionParentOID    OBJECT IDENTIFIER,
        ptSCCPGTTConnectionRowStatus    RowStatus,
        ptSCCPGTTConnectionIndex        Integer32
    }

ptSCCPGTTConnectionPeerID OBJECT-TYPE
    SYNTAX          Integer32 (-2147483648..2147483647)
    MAX-ACCESS      read-only
    STATUS          current
    DESCRIPTION     
            "Peer Identifier from LDL configuration."
    ::= { ptSCCPGTTConnectionEntry 1 }

ptSCCPGTTConnectionContext OBJECT-TYPE
    SYNTAX          DisplayString (SIZE(0..255))
    MAX-ACCESS      read-only
    STATUS          current
    DESCRIPTION     
            "IP and port of this GTT Connection."
    ::= { ptSCCPGTTConnectionEntry 2 }

ptSCCPGTTConnectionConnectionID OBJECT-TYPE
    SYNTAX          Integer32 (-2147483648..2147483647)
    MAX-ACCESS      read-only
    STATUS          current
    DESCRIPTION     
            "Unique GTT Connection identifier for this peer ID."
    ::= { ptSCCPGTTConnectionEntry 3 }

ptSCCPGTTConnectionRegisteredPCs OBJECT-TYPE
    SYNTAX          Integer32 (-2147483648..2147483647)
    MAX-ACCESS      read-only
    STATUS          current
    DESCRIPTION     
            "Number of Registered PCs on this GTT Connection."
    ::= { ptSCCPGTTConnectionEntry 4 }

ptSCCPGTTConnectionRegisteredAppIDs OBJECT-TYPE
    SYNTAX          Integer32 (-2147483648..2147483647)
    MAX-ACCESS      read-only
    STATUS          current
    DESCRIPTION     
            "Number of Registered AppIDs on this GTT Connection."
    ::= { ptSCCPGTTConnectionEntry 5 }

ptSCCPGTTConnectionReassemblySupport OBJECT-TYPE
    SYNTAX          INTEGER { disabled(0), enabled(1) }
    MAX-ACCESS      read-only
    STATUS          current
    DESCRIPTION     
            "XUDT segment reassembly support feature."
    ::= { ptSCCPGTTConnectionEntry 6 }

ptSCCPGTTConnectionUAPVersion OBJECT-TYPE
    SYNTAX          Integer32 (-2147483648..2147483647)
    MAX-ACCESS      read-only
    STATUS          current
    DESCRIPTION     
            "UAP protocol version received on this GTT Connection."
    ::= { ptSCCPGTTConnectionEntry 7 }

ptSCCPGTTConnectionSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPGTTConnectionEntry 242 }

ptSCCPGTTConnectionSCCPNAIndex OBJECT-TYPE
    SYNTAX          Integer32 (-2147483648..2147483647)
    MAX-ACCESS      not-accessible
    STATUS          current
    DESCRIPTION     
            "This is the index of the parent type for this object.
             This parent type is SCCPNA."
    ::= { ptSCCPGTTConnectionEntry 243 }

ptSCCPGTTConnectionGTTConnectionsIndex OBJECT-TYPE
    SYNTAX          Integer32 (-2147483648..2147483647)
    MAX-ACCESS      not-accessible
    STATUS          current
    DESCRIPTION     
            "This is the index of the parent type for this object.
             This parent type is GTTConnections."
    ::= { ptSCCPGTTConnectionEntry 244 }

ptSCCPGTTConnectionActions OBJECT-TYPE
    SYNTAX          INTEGER { terminate(1) }
    MAX-ACCESS      read-create
    STATUS          current
    DESCRIPTION     
            "The OID of all possible actions for this instance"
    ::= { ptSCCPGTTConnectionEntry 252 }

ptSCCPGTTConnectionParentOID OBJECT-TYPE
    SYNTAX          OBJECT IDENTIFIER
    MAX-ACCESS      read-create
    STATUS          current
    DESCRIPTION     
            "The OID of the parent object for this instance"
    ::= { ptSCCPGTTConnectionEntry 253 }

ptSCCPGTTConnectionRowStatus OBJECT-TYPE
    SYNTAX          RowStatus
    MAX-ACCESS      read-create
    STATUS          current
    DESCRIPTION     
            "The row status for the SCCPGTTConnection table"
    ::= { ptSCCPGTTConnectionEntry 254 }

ptSCCPGTTConnectionIndex OBJECT-TYPE
    SYNTAX          Integer32 (-2147483648..2147483647)
    MAX-ACCESS      not-accessible
    STATUS          current
    DESCRIPTION     
            "The row number for the SCCPGTTConnection table"
    ::= { ptSCCPGTTConnectionEntry 255 }

ptSCCPRegisteredPC OBJECT IDENTIFIER
    ::= { ptSCCPGTTConnection 95 }

ptSCCPRegisteredPCTable OBJECT-TYPE
    SYNTAX          SEQUENCE OF PtSCCPRegisteredPCEntry
    MAX-ACCESS      not-accessible
    STATUS          current
    DESCRIPTION     
            "No description supplied in the proxy config file."
    ::= { ptSCCPRegisteredPC 1 }

ptSCCPRegisteredPCEntry OBJECT-TYPE
    SYNTAX          PtSCCPRegisteredPCEntry
    MAX-ACCESS      not-accessible
    STATUS          current
    DESCRIPTION     
            "A sequence of SCCPRegisteredPC attributes."
    INDEX           { ptConnGroupIndex, 
                      ptSCCPRegisteredPCSCCPNAManagerIndex, 
                      ptSCCPRegisteredPCSCCPNAIndex, 
                      ptSCCPRegisteredPCGTTConnectionsIndex, 
                      ptSCCPRegisteredPCGTTConnectionIndex, 
                      ptSCCPRegisteredPCIndex }
    ::= { ptSCCPRegisteredPCTable 1 }

PtSCCPRegisteredPCEntry ::=
    SEQUENCE {
        ptSCCPRegisteredPCPointCode     Integer32,
        ptSCCPRegisteredPCSCCPNAManagerIndex    Integer32,
        ptSCCPRegisteredPCSCCPNAIndex   Integer32,
        ptSCCPRegisteredPCGTTConnectionsIndex     Integer32,
        ptSCCPRegisteredPCGTTConnectionIndex    Integer32,
        ptSCCPRegisteredPCParentOID     OBJECT IDENTIFIER,
        ptSCCPRegisteredPCRowStatus     RowStatus,
        ptSCCPRegisteredPCIndex         Integer32
    }

ptSCCPRegisteredPCPointCode OBJECT-TYPE
    SYNTAX          Integer32 (-2147483648..2147483647)
    MAX-ACCESS      read-only
    STATUS          current
    DESCRIPTION     
            "Point Code registered by the GTT Connection."
    ::= { ptSCCPRegisteredPCEntry 1 }

ptSCCPRegisteredPCSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRegisteredPCEntry 242 }

ptSCCPRegisteredPCSCCPNAIndex OBJECT-TYPE
    SYNTAX          Integer32 (-2147483648..2147483647)
    MAX-ACCESS      not-accessible
    STATUS          current
    DESCRIPTION     
            "This is the index of the parent type for this object.
             This parent type is SCCPNA."
    ::= { ptSCCPRegisteredPCEntry 243 }

ptSCCPRegisteredPCGTTConnectionsIndex OBJECT-TYPE
    SYNTAX          Integer32 (-2147483648..2147483647)
    MAX-ACCESS      not-accessible
    STATUS          current
    DESCRIPTION     
            "This is the index of the parent type for this object.
             This parent type is GTTConnections."
    ::= { ptSCCPRegisteredPCEntry 244 }

ptSCCPRegisteredPCGTTConnectionIndex OBJECT-TYPE
    SYNTAX          Integer32 (-2147483648..2147483647)
    MAX-ACCESS      not-accessible
    STATUS          current
    DESCRIPTION     
            "This is the index of the parent type for this object.
             This parent type is GTTConnection."
    ::= { ptSCCPRegisteredPCEntry 245 }

ptSCCPRegisteredPCParentOID OBJECT-TYPE
    SYNTAX          OBJECT IDENTIFIER
    MAX-ACCESS      read-create
    STATUS          current
    DESCRIPTION     
            "The OID of the parent object for this instance"
    ::= { ptSCCPRegisteredPCEntry 253 }

ptSCCPRegisteredPCRowStatus OBJECT-TYPE
    SYNTAX          RowStatus
    MAX-ACCESS      read-create
    STATUS          current
    DESCRIPTION     
            "The row status for the SCCPRegisteredPC table"
    ::= { ptSCCPRegisteredPCEntry 254 }

ptSCCPRegisteredPCIndex OBJECT-TYPE
    SYNTAX          Integer32 (-2147483648..2147483647)
    MAX-ACCESS      not-accessible
    STATUS          current
    DESCRIPTION     
            "The row number for the SCCPRegisteredPC table"
    ::= { ptSCCPRegisteredPCEntry 255 }

ptSCCPRegisteredGTTAppID OBJECT IDENTIFIER
    ::= { ptSCCPGTTConnection 97 }

ptSCCPRegisteredGTTAppIDTable OBJECT-TYPE
    SYNTAX          SEQUENCE OF PtSCCPRegisteredGTTAppIDEntry
    MAX-ACCESS      not-accessible
    STATUS          current
    DESCRIPTION     
            "No description supplied in the proxy config file."
    ::= { ptSCCPRegisteredGTTAppID 1 }

ptSCCPRegisteredGTTAppIDEntry OBJECT-TYPE
    SYNTAX          PtSCCPRegisteredGTTAppIDEntry
    MAX-ACCESS      not-accessible
    STATUS          current
    DESCRIPTION     
            "A sequence of SCCPRegisteredGTTAppID attributes."
    INDEX           { ptConnGroupIndex, 
                      ptSCCPRegisteredGTTAppIDSCCPNAManagerIndex, 
                      ptSCCPRegisteredGTTAppIDSCCPNAIndex, 
                      ptSCCPRegisteredGTTAppIDGTTConnectionsIndex, 
                      ptSCCPRegisteredGTTAppIDGTTConnectionIndex, 
                      ptSCCPRegisteredGTTAppIDIndex }
    ::= { ptSCCPRegisteredGTTAppIDTable 1 }

PtSCCPRegisteredGTTAppIDEntry ::=
    SEQUENCE {
        ptSCCPRegisteredGTTAppIDName    DisplayString,
        ptSCCPRegisteredGTTAppIDSCCPNAManagerIndex          Integer32,
        ptSCCPRegisteredGTTAppIDSCCPNAIndex   Integer32,
        ptSCCPRegisteredGTTAppIDGTTConnectionsIndex           Integer32,
        ptSCCPRegisteredGTTAppIDGTTConnectionIndex          Integer32,
        ptSCCPRegisteredGTTAppIDParentOID OBJECT IDENTIFIER,
        ptSCCPRegisteredGTTAppIDRowStatus RowStatus,
        ptSCCPRegisteredGTTAppIDIndex   Integer32
    }

ptSCCPRegisteredGTTAppIDName OBJECT-TYPE
    SYNTAX          DisplayString (SIZE(0..255))
    MAX-ACCESS      read-only
    STATUS          current
    DESCRIPTION     
            "Application Identifier registered by the GTT Connection."
    ::= { ptSCCPRegisteredGTTAppIDEntry 1 }

ptSCCPRegisteredGTTAppIDSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRegisteredGTTAppIDEntry 242 }

ptSCCPRegisteredGTTAppIDSCCPNAIndex OBJECT-TYPE
    SYNTAX          Integer32 (-2147483648..2147483647)
    MAX-ACCESS      not-accessible
    STATUS          current
    DESCRIPTION     
            "This is the index of the parent type for this object.
             This parent type is SCCPNA."
    ::= { ptSCCPRegisteredGTTAppIDEntry 243 }

ptSCCPRegisteredGTTAppIDGTTConnectionsIndex OBJECT-TYPE
    SYNTAX          Integer32 (-2147483648..2147483647)
    MAX-ACCESS      not-accessible
    STATUS          current
    DESCRIPTION     
            "This is the index of the parent type for this object.
             This parent type is GTTConnections."
    ::= { ptSCCPRegisteredGTTAppIDEntry 244 }

ptSCCPRegisteredGTTAppIDGTTConnectionIndex OBJECT-TYPE
    SYNTAX          Integer32 (-2147483648..2147483647)
    MAX-ACCESS      not-accessible
    STATUS          current
    DESCRIPTION     
            "This is the index of the parent type for this object.
             This parent type is GTTConnection."
    ::= { ptSCCPRegisteredGTTAppIDEntry 245 }

ptSCCPRegisteredGTTAppIDParentOID OBJECT-TYPE
    SYNTAX          OBJECT IDENTIFIER
    MAX-ACCESS      read-create
    STATUS          current
    DESCRIPTION     
            "The OID of the parent object for this instance"
    ::= { ptSCCPRegisteredGTTAppIDEntry 253 }

ptSCCPRegisteredGTTAppIDRowStatus OBJECT-TYPE
    SYNTAX          RowStatus
    MAX-ACCESS      read-create
    STATUS          current
    DESCRIPTION     
            "The row status for the SCCPRegisteredGTTAppID table"
    ::= { ptSCCPRegisteredGTTAppIDEntry 254 }

ptSCCPRegisteredGTTAppIDIndex OBJECT-TYPE
    SYNTAX          Integer32 (-2147483648..2147483647)
    MAX-ACCESS      not-accessible
    STATUS          current
    DESCRIPTION     
            "The row number for the SCCPRegisteredGTTAppID table"
    ::= { ptSCCPRegisteredGTTAppIDEntry 255 }

ptSCCPTCAPServiceRules OBJECT IDENTIFIER
    ::= { ptSCCPSCCPNA 98 }

ptSCCPTCAPServiceRulesTable OBJECT-TYPE
    SYNTAX          SEQUENCE OF PtSCCPTCAPServiceRulesEntry
    MAX-ACCESS      not-accessible
    STATUS          current
    DESCRIPTION     
            "No description supplied in the proxy config file."
    ::= { ptSCCPTCAPServiceRules 1 }

ptSCCPTCAPServiceRulesEntry OBJECT-TYPE
    SYNTAX          PtSCCPTCAPServiceRulesEntry
    MAX-ACCESS      not-accessible
    STATUS          current
    DESCRIPTION     
            "A sequence of SCCPTCAPServiceRules attributes."
    INDEX           { ptConnGroupIndex, 
                      ptSCCPTCAPServiceRulesSCCPNAManagerIndex, 
                      ptSCCPTCAPServiceRulesSCCPNAIndex, 
                      ptSCCPTCAPServiceRulesIndex }
    ::= { ptSCCPTCAPServiceRulesTable 1 }

PtSCCPTCAPServiceRulesEntry ::=
    SEQUENCE {
        ptSCCPTCAPServiceRulesCount     Integer32,
        ptSCCPTCAPServiceRulesSCCPNAManagerIndex        Integer32,
        ptSCCPTCAPServiceRulesSCCPNAIndex Integer32,
        ptSCCPTCAPServiceRulesParentOID OBJECT IDENTIFIER,
        ptSCCPTCAPServiceRulesRowStatus RowStatus,
        ptSCCPTCAPServiceRulesIndex     Integer32
    }

ptSCCPTCAPServiceRulesCount OBJECT-TYPE
    SYNTAX          Integer32 (-2147483648..2147483647)
    MAX-ACCESS      read-only
    STATUS          current
    DESCRIPTION     
            "Number of TCAP Service Rules."
    ::= { ptSCCPTCAPServiceRulesEntry 1 }

ptSCCPTCAPServiceRulesSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPTCAPServiceRulesEntry 242 }

ptSCCPTCAPServiceRulesSCCPNAIndex OBJECT-TYPE
    SYNTAX          Integer32 (-2147483648..2147483647)
    MAX-ACCESS      not-accessible
    STATUS          current
    DESCRIPTION     
            "This is the index of the parent type for this object.
             This parent type is SCCPNA."
    ::= { ptSCCPTCAPServiceRulesEntry 243 }

ptSCCPTCAPServiceRulesParentOID OBJECT-TYPE
    SYNTAX          OBJECT IDENTIFIER
    MAX-ACCESS      read-create
    STATUS          current
    DESCRIPTION     
            "The OID of the parent object for this instance"
    ::= { ptSCCPTCAPServiceRulesEntry 253 }

ptSCCPTCAPServiceRulesRowStatus OBJECT-TYPE
    SYNTAX          RowStatus
    MAX-ACCESS      read-create
    STATUS          current
    DESCRIPTION     
            "The row status for the SCCPTCAPServiceRules table"
    ::= { ptSCCPTCAPServiceRulesEntry 254 }

ptSCCPTCAPServiceRulesIndex OBJECT-TYPE
    SYNTAX          Integer32 (-2147483648..2147483647)
    MAX-ACCESS      not-accessible
    STATUS          current
    DESCRIPTION     
            "The row number for the SCCPTCAPServiceRules table"
    ::= { ptSCCPTCAPServiceRulesEntry 255 }

ptSCCPTCAPServiceRule OBJECT IDENTIFIER
    ::= { ptSCCPTCAPServiceRules 99 }

ptSCCPTCAPServiceRuleTable OBJECT-TYPE
    SYNTAX          SEQUENCE OF PtSCCPTCAPServiceRuleEntry
    MAX-ACCESS      not-accessible
    STATUS          current
    DESCRIPTION     
            "No description supplied in the proxy config file."
    ::= { ptSCCPTCAPServiceRule 1 }

ptSCCPTCAPServiceRuleEntry OBJECT-TYPE
    SYNTAX          PtSCCPTCAPServiceRuleEntry
    MAX-ACCESS      not-accessible
    STATUS          current
    DESCRIPTION     
            "A sequence of SCCPTCAPServiceRule attributes."
    INDEX           { ptConnGroupIndex, 
                      ptSCCPTCAPServiceRuleSCCPNAManagerIndex, 
                      ptSCCPTCAPServiceRuleSCCPNAIndex, 
                      ptSCCPTCAPServiceRuleTCAPServiceRulesIndex, 
                      ptSCCPTCAPServiceRuleIndex }
    ::= { ptSCCPTCAPServiceRuleTable 1 }

PtSCCPTCAPServiceRuleEntry ::=
    SEQUENCE {
        ptSCCPTCAPServiceRuleSSN        INTEGER,
        ptSCCPTCAPServiceRuleTT         INTEGER,
        ptSCCPTCAPServiceRuleTCAPService INTEGER,
        ptSCCPTCAPServiceRuleSCCPNAManagerIndex       Integer32,
        ptSCCPTCAPServiceRuleSCCPNAIndex Integer32,
        ptSCCPTCAPServiceRuleTCAPServiceRulesIndex          Integer32,
        ptSCCPTCAPServiceRuleParentOID  OBJECT IDENTIFIER,
        ptSCCPTCAPServiceRuleRowStatus  RowStatus,
        ptSCCPTCAPServiceRuleIndex      Integer32
    }

ptSCCPTCAPServiceRuleSSN OBJECT-TYPE
    SYNTAX          INTEGER { default(256), notApplicable(257) }
    MAX-ACCESS      read-only
    STATUS          current
    DESCRIPTION     
            "TCAP Service Rule Subsystem Number."
    ::= { ptSCCPTCAPServiceRuleEntry 1 }

ptSCCPTCAPServiceRuleTT OBJECT-TYPE
    SYNTAX          INTEGER { default(256), notApplicable(257) }
    MAX-ACCESS      read-only
    STATUS          current
    DESCRIPTION     
            "TCAP Service Rule Translation Type."
    ::= { ptSCCPTCAPServiceRuleEntry 2 }

ptSCCPTCAPServiceRuleTCAPService OBJECT-TYPE
    SYNTAX          INTEGER { unspecified(0), map(1), cap(2), gsm(3), 
                        is41(4), ain(5), inap(6), win(7) }
    MAX-ACCESS      read-only
    STATUS          current
    DESCRIPTION     
            "TCAP Service Rule result."
    ::= { ptSCCPTCAPServiceRuleEntry 3 }

ptSCCPTCAPServiceRuleSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPTCAPServiceRuleEntry 242 }

ptSCCPTCAPServiceRuleSCCPNAIndex OBJECT-TYPE
    SYNTAX          Integer32 (-2147483648..2147483647)
    MAX-ACCESS      not-accessible
    STATUS          current
    DESCRIPTION     
            "This is the index of the parent type for this object.
             This parent type is SCCPNA."
    ::= { ptSCCPTCAPServiceRuleEntry 243 }

ptSCCPTCAPServiceRuleTCAPServiceRulesIndex OBJECT-TYPE
    SYNTAX          Integer32 (-2147483648..2147483647)
    MAX-ACCESS      not-accessible
    STATUS          current
    DESCRIPTION     
            "This is the index of the parent type for this object.
             This parent type is TCAPServiceRules."
    ::= { ptSCCPTCAPServiceRuleEntry 244 }

ptSCCPTCAPServiceRuleParentOID OBJECT-TYPE
    SYNTAX          OBJECT IDENTIFIER
    MAX-ACCESS      read-create
    STATUS          current
    DESCRIPTION     
            "The OID of the parent object for this instance"
    ::= { ptSCCPTCAPServiceRuleEntry 253 }

ptSCCPTCAPServiceRuleRowStatus OBJECT-TYPE
    SYNTAX          RowStatus
    MAX-ACCESS      read-create
    STATUS          current
    DESCRIPTION     
            "The row status for the SCCPTCAPServiceRule table"
    ::= { ptSCCPTCAPServiceRuleEntry 254 }

ptSCCPTCAPServiceRuleIndex OBJECT-TYPE
    SYNTAX          Integer32 (-2147483648..2147483647)
    MAX-ACCESS      not-accessible
    STATUS          current
    DESCRIPTION     
            "The row number for the SCCPTCAPServiceRule table"
    ::= { ptSCCPTCAPServiceRuleEntry 255 }

ptSCCPRemotePCs OBJECT IDENTIFIER
    ::= { ptSCCPSCCPNA 100 }

ptSCCPRemotePCsTable OBJECT-TYPE
    SYNTAX          SEQUENCE OF PtSCCPRemotePCsEntry
    MAX-ACCESS      not-accessible
    STATUS          current
    DESCRIPTION     
            "No description supplied in the proxy config file."
    ::= { ptSCCPRemotePCs 1 }

ptSCCPRemotePCsEntry OBJECT-TYPE
    SYNTAX          PtSCCPRemotePCsEntry
    MAX-ACCESS      not-accessible
    STATUS          current
    DESCRIPTION     
            "A sequence of SCCPRemotePCs attributes."
    INDEX           { ptConnGroupIndex, 
                      ptSCCPRemotePCsSCCPNAManagerIndex, 
                      ptSCCPRemotePCsSCCPNAIndex, ptSCCPRemotePCsIndex }
    ::= { ptSCCPRemotePCsTable 1 }

PtSCCPRemotePCsEntry ::=
    SEQUENCE {
        ptSCCPRemotePCsCount            Integer32,
        ptSCCPRemotePCsSCCPNAManagerIndex Integer32,
        ptSCCPRemotePCsSCCPNAIndex      Integer32,
        ptSCCPRemotePCsParentOID        OBJECT IDENTIFIER,
        ptSCCPRemotePCsRowStatus        RowStatus,
        ptSCCPRemotePCsIndex            Integer32
    }

ptSCCPRemotePCsCount OBJECT-TYPE
    SYNTAX          Integer32 (-2147483648..2147483647)
    MAX-ACCESS      read-only
    STATUS          current
    DESCRIPTION     
            "Number of Remote PCs."
    ::= { ptSCCPRemotePCsEntry 1 }

ptSCCPRemotePCsSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRemotePCsEntry 242 }

ptSCCPRemotePCsSCCPNAIndex OBJECT-TYPE
    SYNTAX          Integer32 (-2147483648..2147483647)
    MAX-ACCESS      not-accessible
    STATUS          current
    DESCRIPTION     
            "This is the index of the parent type for this object.
             This parent type is SCCPNA."
    ::= { ptSCCPRemotePCsEntry 243 }

ptSCCPRemotePCsParentOID OBJECT-TYPE
    SYNTAX          OBJECT IDENTIFIER
    MAX-ACCESS      read-create
    STATUS          current
    DESCRIPTION     
            "The OID of the parent object for this instance"
    ::= { ptSCCPRemotePCsEntry 253 }

ptSCCPRemotePCsRowStatus OBJECT-TYPE
    SYNTAX          RowStatus
    MAX-ACCESS      read-create
    STATUS          current
    DESCRIPTION     
            "The row status for the SCCPRemotePCs table"
    ::= { ptSCCPRemotePCsEntry 254 }

ptSCCPRemotePCsIndex OBJECT-TYPE
    SYNTAX          Integer32 (-2147483648..2147483647)
    MAX-ACCESS      not-accessible
    STATUS          current
    DESCRIPTION     
            "The row number for the SCCPRemotePCs table"
    ::= { ptSCCPRemotePCsEntry 255 }

ptSCCPRemotePC OBJECT IDENTIFIER
    ::= { ptSCCPRemotePCs 101 }

ptSCCPRemotePCTable OBJECT-TYPE
    SYNTAX          SEQUENCE OF PtSCCPRemotePCEntry
    MAX-ACCESS      not-accessible
    STATUS          current
    DESCRIPTION     
            "No description supplied in the proxy config file."
    ::= { ptSCCPRemotePC 1 }

ptSCCPRemotePCEntry OBJECT-TYPE
    SYNTAX          PtSCCPRemotePCEntry
    MAX-ACCESS      not-accessible
    STATUS          current
    DESCRIPTION     
            "A sequence of SCCPRemotePC attributes."
    INDEX           { ptConnGroupIndex, ptSCCPRemotePCSCCPNAManagerIndex, 
                      ptSCCPRemotePCSCCPNAIndex, 
                      ptSCCPRemotePCRemotePCsIndex, ptSCCPRemotePCIndex }
    ::= { ptSCCPRemotePCTable 1 }

PtSCCPRemotePCEntry ::=
    SEQUENCE {
        ptSCCPRemotePCPointCode         Integer32,
        ptSCCPRemotePCStatus            INTEGER,
        ptSCCPRemotePCRemoteSSNs        Integer32,
        ptSCCPRemotePCUserCreated       INTEGER,
        ptSCCPRemotePCAINI              INTEGER,
        ptSCCPRemotePCSCCPNAManagerIndex Integer32,
        ptSCCPRemotePCSCCPNAIndex       Integer32,
        ptSCCPRemotePCRemotePCsIndex    Integer32,
        ptSCCPRemotePCParentOID         OBJECT IDENTIFIER,
        ptSCCPRemotePCRowStatus         RowStatus,
        ptSCCPRemotePCIndex             Integer32
    }

ptSCCPRemotePCPointCode OBJECT-TYPE
    SYNTAX          Integer32 (-2147483648..2147483647)
    MAX-ACCESS      read-only
    STATUS          current
    DESCRIPTION     
            "Remote point code."
    ::= { ptSCCPRemotePCEntry 1 }

ptSCCPRemotePCStatus OBJECT-TYPE
    SYNTAX          INTEGER { unavailable(0), available(1) }
    MAX-ACCESS      read-only
    STATUS          current
    DESCRIPTION     
            "Remote PC status (AVAILABLE/UNAVAILABLE)."
    ::= { ptSCCPRemotePCEntry 2 }

ptSCCPRemotePCRemoteSSNs OBJECT-TYPE
    SYNTAX          Integer32 (-2147483648..2147483647)
    MAX-ACCESS      read-only
    STATUS          current
    DESCRIPTION     
            "Number of Remote SSNs."
    ::= { ptSCCPRemotePCEntry 3 }

ptSCCPRemotePCUserCreated OBJECT-TYPE
    SYNTAX          INTEGER { no(0), yes(1) }
    MAX-ACCESS      read-only
    STATUS          current
    DESCRIPTION     
            "Remote PC created by user (or network)."
    ::= { ptSCCPRemotePCEntry 4 }

ptSCCPRemotePCAINI OBJECT-TYPE
    SYNTAX          INTEGER { international(0), national(1) }
    MAX-ACCESS      read-only
    STATUS          current
    DESCRIPTION     
            "Remote PC address indicator network/reserved 8th bit. \nANSI network typically use NATIONAL while all others use INTERNATIONAL."
    ::= { ptSCCPRemotePCEntry 5 }

ptSCCPRemotePCSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRemotePCEntry 242 }

ptSCCPRemotePCSCCPNAIndex OBJECT-TYPE
    SYNTAX          Integer32 (-2147483648..2147483647)
    MAX-ACCESS      not-accessible
    STATUS          current
    DESCRIPTION     
            "This is the index of the parent type for this object.
             This parent type is SCCPNA."
    ::= { ptSCCPRemotePCEntry 243 }

ptSCCPRemotePCRemotePCsIndex OBJECT-TYPE
    SYNTAX          Integer32 (-2147483648..2147483647)
    MAX-ACCESS      not-accessible
    STATUS          current
    DESCRIPTION     
            "This is the index of the parent type for this object.
             This parent type is RemotePCs."
    ::= { ptSCCPRemotePCEntry 244 }

ptSCCPRemotePCParentOID OBJECT-TYPE
    SYNTAX          OBJECT IDENTIFIER
    MAX-ACCESS      read-create
    STATUS          current
    DESCRIPTION     
            "The OID of the parent object for this instance"
    ::= { ptSCCPRemotePCEntry 253 }

ptSCCPRemotePCRowStatus OBJECT-TYPE
    SYNTAX          RowStatus
    MAX-ACCESS      read-create
    STATUS          current
    DESCRIPTION     
            "The row status for the SCCPRemotePC table"
    ::= { ptSCCPRemotePCEntry 254 }

ptSCCPRemotePCIndex OBJECT-TYPE
    SYNTAX          Integer32 (-2147483648..2147483647)
    MAX-ACCESS      not-accessible
    STATUS          current
    DESCRIPTION     
            "The row number for the SCCPRemotePC table"
    ::= { ptSCCPRemotePCEntry 255 }

ptSCCPRemoteSSN OBJECT IDENTIFIER
    ::= { ptSCCPRemotePC 102 }

ptSCCPRemoteSSNTable OBJECT-TYPE
    SYNTAX          SEQUENCE OF PtSCCPRemoteSSNEntry
    MAX-ACCESS      not-accessible
    STATUS          current
    DESCRIPTION     
            "No description supplied in the proxy config file."
    ::= { ptSCCPRemoteSSN 1 }

ptSCCPRemoteSSNEntry OBJECT-TYPE
    SYNTAX          PtSCCPRemoteSSNEntry
    MAX-ACCESS      not-accessible
    STATUS          current
    DESCRIPTION     
            "A sequence of SCCPRemoteSSN attributes."
    INDEX           { ptConnGroupIndex, 
                      ptSCCPRemoteSSNSCCPNAManagerIndex, 
                      ptSCCPRemoteSSNSCCPNAIndex, 
                      ptSCCPRemoteSSNRemotePCsIndex, 
                      ptSCCPRemoteSSNRemotePCIndex, ptSCCPRemoteSSNIndex }
    ::= { ptSCCPRemoteSSNTable 1 }

PtSCCPRemoteSSNEntry ::=
    SEQUENCE {
        ptSCCPRemoteSSNSSN              Integer32,
        ptSCCPRemoteSSNStatus           INTEGER,
        ptSCCPRemoteSSNSCCPNAManagerIndex Integer32,
        ptSCCPRemoteSSNSCCPNAIndex      Integer32,
        ptSCCPRemoteSSNRemotePCsIndex   Integer32,
        ptSCCPRemoteSSNRemotePCIndex    Integer32,
        ptSCCPRemoteSSNActions          INTEGER,
        ptSCCPRemoteSSNParentOID        OBJECT IDENTIFIER,
        ptSCCPRemoteSSNRowStatus        RowStatus,
        ptSCCPRemoteSSNIndex            Integer32
    }

ptSCCPRemoteSSNSSN OBJECT-TYPE
    SYNTAX          Integer32 (-2147483648..2147483647)
    MAX-ACCESS      read-only
    STATUS          current
    DESCRIPTION     
            "Subsystem number for the Remote PC."
    ::= { ptSCCPRemoteSSNEntry 1 }

ptSCCPRemoteSSNStatus OBJECT-TYPE
    SYNTAX          INTEGER { prohibited(0), allowed(1) }
    MAX-ACCESS      read-only
    STATUS          current
    DESCRIPTION     
            "Remote SSN status (ALLOWED/PROHIBITED). \nProhibited SSNs will initiate the SST procedure for available Remote PC. \nUser Created SSN status persist following TFP/TFA."
    ::= { ptSCCPRemoteSSNEntry 2 }

ptSCCPRemoteSSNSCCPNAManagerIndex OBJECT-TYPE
    SYNTAX          Integer32 (-2147483648..2147483647)
    MAX-ACCESS      not-accessible
    STATUS          current
    DESCRIPTION     
            "This is the index of the parent type for this object.
             This parent type is SCCPNAManager."
    ::= { ptSCCPRemoteSSNEntry 242 }

ptSCCPRemoteSSNSCCPNAIndex OBJECT-TYPE
    SYNTAX          Integer32 (-2147483648..2147483647)
    MAX-ACCESS      not-accessible
    STATUS          current
    DESCRIPTION     
            "This is the index of the parent type for this object.
             This parent type is SCCPNA."
    ::= { ptSCCPRemoteSSNEntry 243 }

ptSCCPRemoteSSNRemotePCsIndex OBJECT-TYPE
    SYNTAX          Integer32 (-2147483648..2147483647)
    MAX-ACCESS      not-accessible
    STATUS          current
    DESCRIPTION     
            "This is the index of the parent type for this object.
             This parent type is RemotePCs."
    ::= { ptSCCPRemoteSSNEntry 244 }

ptSCCPRemoteSSNRemotePCIndex OBJECT-TYPE
    SYNTAX          Integer32 (-2147483648..2147483647)
    MAX-ACCESS      not-accessible
    STATUS          current
    DESCRIPTION     
            "This is the index of the parent type for this object.
             This parent type is RemotePC."
    ::= { ptSCCPRemoteSSNEntry 245 }

ptSCCPRemoteSSNActions OBJECT-TYPE
    SYNTAX          INTEGER { allow(1), prohibit(2) }
    MAX-ACCESS      read-create
    STATUS          current
    DESCRIPTION     
            "The OID of all possible actions for this instance"
    ::= { ptSCCPRemoteSSNEntry 252 }

ptSCCPRemoteSSNParentOID OBJECT-TYPE
    SYNTAX          OBJECT IDENTIFIER
    MAX-ACCESS      read-create
    STATUS          current
    DESCRIPTION     
            "The OID of the parent object for this instance"
    ::= { ptSCCPRemoteSSNEntry 253 }

ptSCCPRemoteSSNRowStatus OBJECT-TYPE
    SYNTAX          RowStatus
    MAX-ACCESS      read-create
    STATUS          current
    DESCRIPTION     
            "The row status for the SCCPRemoteSSN table"
    ::= { ptSCCPRemoteSSNEntry 254 }

ptSCCPRemoteSSNIndex OBJECT-TYPE
    SYNTAX          Integer32 (-2147483648..2147483647)
    MAX-ACCESS      not-accessible
    STATUS          current
    DESCRIPTION     
            "The row number for the SCCPRemoteSSN table"
    ::= { ptSCCPRemoteSSNEntry 255 }

ptL4CvtrL4CvtrConfiguration OBJECT IDENTIFIER
    ::= { ptConnGroup 131 }

ptL4CvtrL4CvtrConfigurationTable OBJECT-TYPE
    SYNTAX          SEQUENCE OF PtL4CvtrL4CvtrConfigurationEntry
    MAX-ACCESS      not-accessible
    STATUS          current
    DESCRIPTION     
            "No description supplied in the proxy config file."
    ::= { ptL4CvtrL4CvtrConfiguration 1 }

ptL4CvtrL4CvtrConfigurationEntry OBJECT-TYPE
    SYNTAX          PtL4CvtrL4CvtrConfigurationEntry
    MAX-ACCESS      not-accessible
    STATUS          current
    DESCRIPTION     
            "A sequence of L4CvtrL4CvtrConfiguration attributes."
    INDEX           { ptConnGroupIndex, ptL4CvtrL4CvtrConfigurationIndex }
    ::= { ptL4CvtrL4CvtrConfigurationTable 1 }

PtL4CvtrL4CvtrConfigurationEntry ::=
    SEQUENCE {
        ptL4CvtrL4CvtrConfigurationActivePeerID       Integer32,
        ptL4CvtrL4CvtrConfigurationTrafficStatus        INTEGER,
        ptL4CvtrL4CvtrConfigurationReregistrationTimer              INTEGER,
        ptL4CvtrL4CvtrConfigurationPakistanCBN      Integer32,
        ptL4CvtrL4CvtrConfigurationFastAnswerTimer          INTEGER,
        ptL4CvtrL4CvtrConfigurationCGAckTimer     INTEGER,
        ptL4CvtrL4CvtrConfigurationErrors INTEGER,
        ptL4CvtrL4CvtrConfigurationSetupManagement          INTEGER,
        ptL4CvtrL4CvtrConfigurationExecutionTrace         INTEGER,
        ptL4CvtrL4CvtrConfigurationLayerCommunication             INTEGER,
        ptL4CvtrL4CvtrConfigurationPeerManagement         INTEGER,
        ptL4CvtrL4CvtrConfigurationMessageContent         INTEGER,
        ptL4CvtrL4CvtrConfigurationMessageParsing         INTEGER,
        ptL4CvtrL4CvtrConfigurationIPVariantConfiguration                 INTEGER,
        ptL4CvtrL4CvtrConfigurationIPServicePort        Integer32,
        ptL4CvtrL4CvtrConfigurationCPAMID Integer32,
        ptL4CvtrL4CvtrConfigurationCPAPID Integer32,
        ptL4CvtrL4CvtrConfigurationSignalingIndicator             INTEGER,
        ptL4CvtrL4CvtrConfigurationIncomingAppIDPrecedence                  INTEGER,
        ptL4CvtrL4CvtrConfigurationISUPSupport      INTEGER,
        ptL4CvtrL4CvtrConfigurationSCCPSupport      INTEGER,
        ptL4CvtrL4CvtrConfigurationBICCSupport      INTEGER,
        ptL4CvtrL4CvtrConfigurationRouteMappingLimit            Integer32,
        ptL4CvtrL4CvtrConfigurationLDLDebug   INTEGER,
        ptL4CvtrL4CvtrConfigurationActions  INTEGER,
        ptL4CvtrL4CvtrConfigurationParentOID    OBJECT IDENTIFIER,
        ptL4CvtrL4CvtrConfigurationRowStatus    RowStatus,
        ptL4CvtrL4CvtrConfigurationIndex Integer32
    }

ptL4CvtrL4CvtrConfigurationActivePeerID OBJECT-TYPE
    SYNTAX          Integer32 (-2147483648..2147483647)
    MAX-ACCESS      read-only
    STATUS          current
    DESCRIPTION     
            "The active peer identifier as defined by the converter LDL file. \nThe converter LDL file (cvtr_ldl.conf) is located in the /opt/cpu_ss7gw/current/data directory."
    ::= { ptL4CvtrL4CvtrConfigurationEntry 1 }

ptL4CvtrL4CvtrConfigurationTrafficStatus OBJECT-TYPE
    SYNTAX          INTEGER { inactive(0), active(1), unlicensed(2) }
    MAX-ACCESS      read-only
    STATUS          current
    DESCRIPTION     
            "Traffic status (INACTIVE/ACTIVE/UNLICENSED). \nThe traffic should only be inactive during the initial configuration of the converter system."
    ::= { ptL4CvtrL4CvtrConfigurationEntry 2 }

ptL4CvtrL4CvtrConfigurationReregistrationTimer OBJECT-TYPE
    SYNTAX          INTEGER { disabled(0) }
    MAX-ACCESS      read-create
    STATUS          current
    DESCRIPTION     
            "Interval at which reregistration is initiated (in seconds). \nSet to 0 (DISABLED) to disable the reregistration. Default 60 seconds. Valid range is 0 to 999999."
    ::= { ptL4CvtrL4CvtrConfigurationEntry 3 }

ptL4CvtrL4CvtrConfigurationPakistanCBN OBJECT-TYPE
    SYNTAX          Integer32 (-2147483648..2147483647)
    MAX-ACCESS      read-create
    STATUS          current
    DESCRIPTION     
            "Pakistan fixed Charge Band Number parameter value. \nUsed in the Pakistan-ITU converter only for default settings. Valid range is 0 to 255."
    ::= { ptL4CvtrL4CvtrConfigurationEntry 4 }

ptL4CvtrL4CvtrConfigurationFastAnswerTimer OBJECT-TYPE
    SYNTAX          INTEGER { disabled(0) }
    MAX-ACCESS      read-create
    STATUS          current
    DESCRIPTION     
            "Lifespan of Fast Answer record (in seconds). \nUsed in the ANSI-ITU converter only for ACM and ANM conversion. \nSet to 0 (DISABLED) to disable the Fast Answer feature. Default 60 seconds. Valid range is 0 to 999999"
    ::= { ptL4CvtrL4CvtrConfigurationEntry 5 }

ptL4CvtrL4CvtrConfigurationCGAckTimer OBJECT-TYPE
    SYNTAX          INTEGER { disabled(0) }
    MAX-ACCESS      read-create
    STATUS          current
    DESCRIPTION     
            "Lifespan of Circuit Group Acknowledgement record (in seconds). \nUsed in the ANSI-ITU converter only for circuit group acknowledgement message management due to circuit range incompatibility between the variants. \nDefault 60 seconds. Valid range is 1 to 999999."
    ::= { ptL4CvtrL4CvtrConfigurationEntry 6 }

ptL4CvtrL4CvtrConfigurationErrors OBJECT-TYPE
    SYNTAX          INTEGER { notLogged(0), logged(1) }
    MAX-ACCESS      read-create
    STATUS          current
    DESCRIPTION     
            "Enable or disable debug logging of the converter errors; \nshould be logged for production systems."
    ::= { ptL4CvtrL4CvtrConfigurationEntry 7 }

ptL4CvtrL4CvtrConfigurationSetupManagement OBJECT-TYPE
    SYNTAX          INTEGER { notLogged(0), logged(1) }
    MAX-ACCESS      read-create
    STATUS          current
    DESCRIPTION     
            "Enable or disable debug logging of the setup management; \nshould be logged for production systems."
    ::= { ptL4CvtrL4CvtrConfigurationEntry 8 }

ptL4CvtrL4CvtrConfigurationExecutionTrace OBJECT-TYPE
    SYNTAX          INTEGER { notLogged(0), logged(1) }
    MAX-ACCESS      read-create
    STATUS          current
    DESCRIPTION     
            "Enable or disable debug logging of the execution trace; \nshould not be logged for production systems."
    ::= { ptL4CvtrL4CvtrConfigurationEntry 9 }

ptL4CvtrL4CvtrConfigurationLayerCommunication OBJECT-TYPE
    SYNTAX          INTEGER { notLogged(0), logged(1) }
    MAX-ACCESS      read-create
    STATUS          current
    DESCRIPTION     
            "Enable or disable debug logging of layer communication; \nshould not be logged for production systems."
    ::= { ptL4CvtrL4CvtrConfigurationEntry 10 }

ptL4CvtrL4CvtrConfigurationPeerManagement OBJECT-TYPE
    SYNTAX          INTEGER { notLogged(0), logged(1) }
    MAX-ACCESS      read-create
    STATUS          current
    DESCRIPTION     
            "Enable or disable debug logging of the peer management; \nshould not be logged for production systems."
    ::= { ptL4CvtrL4CvtrConfigurationEntry 11 }

ptL4CvtrL4CvtrConfigurationMessageContent OBJECT-TYPE
    SYNTAX          INTEGER { notLogged(0), logged(1) }
    MAX-ACCESS      read-create
    STATUS          current
    DESCRIPTION     
            "Enable or disable debug logging of the message content; \nmust not be logged for production systems. \nSystem logs to debug the raw hexadecimal dump of the SS7 messages."
    ::= { ptL4CvtrL4CvtrConfigurationEntry 12 }

ptL4CvtrL4CvtrConfigurationMessageParsing OBJECT-TYPE
    SYNTAX          INTEGER { notLogged(0), logged(1) }
    MAX-ACCESS      read-create
    STATUS          current
    DESCRIPTION     
            "Enable or disable debug logging of the message parsing; \nmust not be logged for production systems. \nSystem logs to debug the detailed decoded parsed output of the messages."
    ::= { ptL4CvtrL4CvtrConfigurationEntry 13 }

ptL4CvtrL4CvtrConfigurationIPVariantConfiguration OBJECT-TYPE
    SYNTAX          INTEGER { notApplicable(0) }
    MAX-ACCESS      read-only
    STATUS          current
    DESCRIPTION     
            "This screen is not applicable for SS7 to SS7 traffic deployment."
    ::= { ptL4CvtrL4CvtrConfigurationEntry 14 }

ptL4CvtrL4CvtrConfigurationIPServicePort OBJECT-TYPE
    SYNTAX          Integer32 (-2147483648..2147483647)
    MAX-ACCESS      read-only
    STATUS          current
    DESCRIPTION     
            "IP service port (IP-SS7 converter only). \nSignaling Gateway connection for User Application Protocol (UAP) management"
    ::= { ptL4CvtrL4CvtrConfigurationEntry 15 }

ptL4CvtrL4CvtrConfigurationCPAMID OBJECT-TYPE
    SYNTAX          Integer32 (-2147483648..2147483647)
    MAX-ACCESS      read-create
    STATUS          current
    DESCRIPTION     
            "CPA Message identifier (IP-SS7 converter only). \nUsed to envelop an unsupported message sent to the IP application for Custom Pass Along (CPA) back to the SS7 network. Valid range is 0 to 255."
    ::= { ptL4CvtrL4CvtrConfigurationEntry 16 }

ptL4CvtrL4CvtrConfigurationCPAPID OBJECT-TYPE
    SYNTAX          Integer32 (-2147483648..2147483647)
    MAX-ACCESS      read-create
    STATUS          current
    DESCRIPTION     
            "CPA parameter identifier (IP-SS7 converter only). \nUsed to envelop an unsupported parameter sent to the IP application for Custom Pass Along (CPA) back to the SS7 network. Valid range is 0 to 255."
    ::= { ptL4CvtrL4CvtrConfigurationEntry 17 }

ptL4CvtrL4CvtrConfigurationSignalingIndicator OBJECT-TYPE
    SYNTAX          INTEGER { isup(5), sccp(3), isupAndSccp(255), 
                        unknown(254) }
    MAX-ACCESS      read-only
    STATUS          current
    DESCRIPTION     
            "Licensed Signaling Indicator. \nWill be set to ISUP, SCCP, or ISUP and SCCP based on the license. \nWill be set to UNKNOWN if unlicensed. \nObsolete as of 14.1"
    ::= { ptL4CvtrL4CvtrConfigurationEntry 18 }

ptL4CvtrL4CvtrConfigurationIncomingAppIDPrecedence OBJECT-TYPE
    SYNTAX          INTEGER { opc(0), dpc(1) }
    MAX-ACCESS      read-create
    STATUS          current
    DESCRIPTION     
            "Incoming AppID Precedence (OPC/DPC). \nPrecedence only applies if both associated Route Mappings for an MSU conversion contain an Incoming AppID. The chosen Incoming AppID will be taken from the Routing Mapping corresponding with either the OPC or DPC as per this attribute."
    ::= { ptL4CvtrL4CvtrConfigurationEntry 19 }

ptL4CvtrL4CvtrConfigurationISUPSupport OBJECT-TYPE
    SYNTAX          INTEGER { unlicensed(0), licensed(1) }
    MAX-ACCESS      read-only
    STATUS          current
    DESCRIPTION     
            "ISUP Support (UNLICENSED/LICENSED)."
    ::= { ptL4CvtrL4CvtrConfigurationEntry 20 }

ptL4CvtrL4CvtrConfigurationSCCPSupport OBJECT-TYPE
    SYNTAX          INTEGER { unlicensed(0), licensed(1) }
    MAX-ACCESS      read-only
    STATUS          current
    DESCRIPTION     
            "SCCP Support (UNLICENSED/LICENSED)."
    ::= { ptL4CvtrL4CvtrConfigurationEntry 21 }

ptL4CvtrL4CvtrConfigurationBICCSupport OBJECT-TYPE
    SYNTAX          INTEGER { unlicensed(0), licensed(1) }
    MAX-ACCESS      read-only
    STATUS          current
    DESCRIPTION     
            "BICC Support (UNLICENSED/LICENSED)."
    ::= { ptL4CvtrL4CvtrConfigurationEntry 22 }

ptL4CvtrL4CvtrConfigurationRouteMappingLimit OBJECT-TYPE
    SYNTAX          Integer32 (2000..4000)
    MAX-ACCESS      read-create
    STATUS          current
    DESCRIPTION     
            "L4 Cvtr max Route Mapping Limit. \nThis attribute limits the number of Route Mapping objects \nthat may be created for each SS7 Variant. \nDefault 2000. Valid range is 2000 to 4000. \nThis limit is set to 200 and is not modifiable in ANSI-ITU \nvariant conversion configurations."
    ::= { ptL4CvtrL4CvtrConfigurationEntry 23 }

ptL4CvtrL4CvtrConfigurationLDLDebug OBJECT-TYPE
    SYNTAX          INTEGER { notLogged(0) }
    MAX-ACCESS      read-create
    STATUS          current
    DESCRIPTION     
            "The LDL Debug Level should be set to 2 or lower on all production systems, unless directed by support. Otherwise the system performance may be impacted. Valid range is (0 [NOT LOGGED], 1 to 10)."
    ::= { ptL4CvtrL4CvtrConfigurationEntry 24 }

ptL4CvtrL4CvtrConfigurationActions OBJECT-TYPE
    SYNTAX          INTEGER { activateTraffic(1), deactivateTraffic(2), 
                        restoreDebugDefaults(3) }
    MAX-ACCESS      read-create
    STATUS          current
    DESCRIPTION     
            "The OID of all possible actions for this instance"
    ::= { ptL4CvtrL4CvtrConfigurationEntry 252 }

ptL4CvtrL4CvtrConfigurationParentOID OBJECT-TYPE
    SYNTAX          OBJECT IDENTIFIER
    MAX-ACCESS      read-create
    STATUS          current
    DESCRIPTION     
            "The OID of the parent object for this instance"
    ::= { ptL4CvtrL4CvtrConfigurationEntry 253 }

ptL4CvtrL4CvtrConfigurationRowStatus OBJECT-TYPE
    SYNTAX          RowStatus
    MAX-ACCESS      read-create
    STATUS          current
    DESCRIPTION     
            "The row status for the L4CvtrL4CvtrConfiguration table"
    ::= { ptL4CvtrL4CvtrConfigurationEntry 254 }

ptL4CvtrL4CvtrConfigurationIndex OBJECT-TYPE
    SYNTAX          Integer32 (-2147483648..2147483647)
    MAX-ACCESS      not-accessible
    STATUS          current
    DESCRIPTION     
            "The row number for the L4CvtrL4CvtrConfiguration table"
    ::= { ptL4CvtrL4CvtrConfigurationEntry 255 }

ptL4CvtrL4CvtrStatistics OBJECT IDENTIFIER
    ::= { ptConnGroup 132 }

ptL4CvtrL4CvtrStatisticsTable OBJECT-TYPE
    SYNTAX          SEQUENCE OF PtL4CvtrL4CvtrStatisticsEntry
    MAX-ACCESS      not-accessible
    STATUS          current
    DESCRIPTION     
            "No description supplied in the proxy config file."
    ::= { ptL4CvtrL4CvtrStatistics 1 }

ptL4CvtrL4CvtrStatisticsEntry OBJECT-TYPE
    SYNTAX          PtL4CvtrL4CvtrStatisticsEntry
    MAX-ACCESS      not-accessible
    STATUS          current
    DESCRIPTION     
            "A sequence of L4CvtrL4CvtrStatistics attributes."
    INDEX           { ptConnGroupIndex, ptL4CvtrL4CvtrStatisticsIndex }
    ::= { ptL4CvtrL4CvtrStatisticsTable 1 }

PtL4CvtrL4CvtrStatisticsEntry ::=
    SEQUENCE {
        ptL4CvtrL4CvtrStatisticsVariant1Name    DisplayString,
        ptL4CvtrL4CvtrStatisticsVariant1Received        Integer32,
        ptL4CvtrL4CvtrStatisticsVariant1Discarded         Integer32,
        ptL4CvtrL4CvtrStatisticsVariant1Sent    Integer32,
        ptL4CvtrL4CvtrStatisticsVariant1Generated         Integer32,
        ptL4CvtrL4CvtrStatisticsVariant2Name    DisplayString,
        ptL4CvtrL4CvtrStatisticsVariant2Received        Integer32,
        ptL4CvtrL4CvtrStatisticsVariant2Discarded         Integer32,
        ptL4CvtrL4CvtrStatisticsVariant2Sent    Integer32,
        ptL4CvtrL4CvtrStatisticsVariant2Generated         Integer32,
        ptL4CvtrL4CvtrStatisticsRefreshDate   DisplayString,
        ptL4CvtrL4CvtrStatisticsResetDate DisplayString,
        ptL4CvtrL4CvtrStatisticsActions INTEGER,
        ptL4CvtrL4CvtrStatisticsParentOID OBJECT IDENTIFIER,
        ptL4CvtrL4CvtrStatisticsRowStatus RowStatus,
        ptL4CvtrL4CvtrStatisticsIndex   Integer32
    }

ptL4CvtrL4CvtrStatisticsVariant1Name OBJECT-TYPE
    SYNTAX          DisplayString (SIZE(0..255))
    MAX-ACCESS      read-only
    STATUS          current
    DESCRIPTION     
            "Name of variant 1."
    ::= { ptL4CvtrL4CvtrStatisticsEntry 1 }

ptL4CvtrL4CvtrStatisticsVariant1Received OBJECT-TYPE
    SYNTAX          Integer32 (-2147483648..2147483647)
    MAX-ACCESS      read-only
    STATUS          current
    DESCRIPTION     
            "Number of received MSU by variant 1."
    ::= { ptL4CvtrL4CvtrStatisticsEntry 2 }

ptL4CvtrL4CvtrStatisticsVariant1Discarded OBJECT-TYPE
    SYNTAX          Integer32 (-2147483648..2147483647)
    MAX-ACCESS      read-only
    STATUS          current
    DESCRIPTION     
            "Number of discarded MSU by variant 1."
    ::= { ptL4CvtrL4CvtrStatisticsEntry 3 }

ptL4CvtrL4CvtrStatisticsVariant1Sent OBJECT-TYPE
    SYNTAX          Integer32 (-2147483648..2147483647)
    MAX-ACCESS      read-only
    STATUS          current
    DESCRIPTION     
            "Number of sent MSU by variant 1."
    ::= { ptL4CvtrL4CvtrStatisticsEntry 4 }

ptL4CvtrL4CvtrStatisticsVariant1Generated OBJECT-TYPE
    SYNTAX          Integer32 (-2147483648..2147483647)
    MAX-ACCESS      read-only
    STATUS          current
    DESCRIPTION     
            "Number of generated MSU by variant 1."
    ::= { ptL4CvtrL4CvtrStatisticsEntry 5 }

ptL4CvtrL4CvtrStatisticsVariant2Name OBJECT-TYPE
    SYNTAX          DisplayString (SIZE(0..255))
    MAX-ACCESS      read-only
    STATUS          current
    DESCRIPTION     
            "Name of variant 2."
    ::= { ptL4CvtrL4CvtrStatisticsEntry 6 }

ptL4CvtrL4CvtrStatisticsVariant2Received OBJECT-TYPE
    SYNTAX          Integer32 (-2147483648..2147483647)
    MAX-ACCESS      read-only
    STATUS          current
    DESCRIPTION     
            "Number of received MSU by variant 2."
    ::= { ptL4CvtrL4CvtrStatisticsEntry 7 }

ptL4CvtrL4CvtrStatisticsVariant2Discarded OBJECT-TYPE
    SYNTAX          Integer32 (-2147483648..2147483647)
    MAX-ACCESS      read-only
    STATUS          current
    DESCRIPTION     
            "Number of discarded MSU by variant 2."
    ::= { ptL4CvtrL4CvtrStatisticsEntry 8 }

ptL4CvtrL4CvtrStatisticsVariant2Sent OBJECT-TYPE
    SYNTAX          Integer32 (-2147483648..2147483647)
    MAX-ACCESS      read-only
    STATUS          current
    DESCRIPTION     
            "Number of sent MSU by variant 2."
    ::= { ptL4CvtrL4CvtrStatisticsEntry 9 }

ptL4CvtrL4CvtrStatisticsVariant2Generated OBJECT-TYPE
    SYNTAX          Integer32 (-2147483648..2147483647)
    MAX-ACCESS      read-only
    STATUS          current
    DESCRIPTION     
            "Number of generated MSU by variant 2."
    ::= { ptL4CvtrL4CvtrStatisticsEntry 10 }

ptL4CvtrL4CvtrStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptL4CvtrL4CvtrStatisticsEntry 11 }

ptL4CvtrL4CvtrStatisticsResetDate OBJECT-TYPE
    SYNTAX          DisplayString (SIZE(0..255))
    MAX-ACCESS      read-only
    STATUS          current
    DESCRIPTION     
            "Date/Time from which the above counts were last started or reset. \nUse the Reset All Stats action to reset the counts."
    ::= { ptL4CvtrL4CvtrStatisticsEntry 12 }

ptL4CvtrL4CvtrStatisticsActions OBJECT-TYPE
    SYNTAX          INTEGER { refreshAllStats(1), resetAllStats(2) }
    MAX-ACCESS      read-create
    STATUS          current
    DESCRIPTION     
            "The OID of all possible actions for this instance"
    ::= { ptL4CvtrL4CvtrStatisticsEntry 252 }

ptL4CvtrL4CvtrStatisticsParentOID OBJECT-TYPE
    SYNTAX          OBJECT IDENTIFIER
    MAX-ACCESS      read-create
    STATUS          current
    DESCRIPTION     
            "The OID of the parent object for this instance"
    ::= { ptL4CvtrL4CvtrStatisticsEntry 253 }

ptL4CvtrL4CvtrStatisticsRowStatus OBJECT-TYPE
    SYNTAX          RowStatus
    MAX-ACCESS      read-create
    STATUS          current
    DESCRIPTION     
            "The row status for the L4CvtrL4CvtrStatistics table"
    ::= { ptL4CvtrL4CvtrStatisticsEntry 254 }

ptL4CvtrL4CvtrStatisticsIndex OBJECT-TYPE
    SYNTAX          Integer32 (-2147483648..2147483647)
    MAX-ACCESS      not-accessible
    STATUS          current
    DESCRIPTION     
            "The row number for the L4CvtrL4CvtrStatistics table"
    ::= { ptL4CvtrL4CvtrStatisticsEntry 255 }

ptL4CvtrPeerStatistics OBJECT IDENTIFIER
    ::= { ptL4CvtrL4CvtrStatistics 133 }

ptL4CvtrPeerStatisticsTable OBJECT-TYPE
    SYNTAX          SEQUENCE OF PtL4CvtrPeerStatisticsEntry
    MAX-ACCESS      not-accessible
    STATUS          current
    DESCRIPTION     
            "No description supplied in the proxy config file."
    ::= { ptL4CvtrPeerStatistics 1 }

ptL4CvtrPeerStatisticsEntry OBJECT-TYPE
    SYNTAX          PtL4CvtrPeerStatisticsEntry
    MAX-ACCESS      not-accessible
    STATUS          current
    DESCRIPTION     
            "A sequence of L4CvtrPeerStatistics attributes."
    INDEX           { ptConnGroupIndex, 
                      ptL4CvtrPeerStatisticsL4CvtrStatisticsIndex, 
                      ptL4CvtrPeerStatisticsIndex }
    ::= { ptL4CvtrPeerStatisticsTable 1 }

PtL4CvtrPeerStatisticsEntry ::=
    SEQUENCE {
        ptL4CvtrPeerStatisticsPeerID    Integer32,
        ptL4CvtrPeerStatisticsVariant1Name  DisplayString,
        ptL4CvtrPeerStatisticsVariant1Received      Integer32,
        ptL4CvtrPeerStatisticsVariant1Discarded       Integer32,
        ptL4CvtrPeerStatisticsVariant1Sent  Integer32,
        ptL4CvtrPeerStatisticsVariant1Generated       Integer32,
        ptL4CvtrPeerStatisticsVariant2Name  DisplayString,
        ptL4CvtrPeerStatisticsVariant2Received      Integer32,
        ptL4CvtrPeerStatisticsVariant2Discarded       Integer32,
        ptL4CvtrPeerStatisticsVariant2Sent  Integer32,
        ptL4CvtrPeerStatisticsVariant2Generated       Integer32,
        ptL4CvtrPeerStatisticsRefreshDate DisplayString,
        ptL4CvtrPeerStatisticsResetDate DisplayString,
        ptL4CvtrPeerStatisticsL4CvtrStatisticsIndex           Integer32,
        ptL4CvtrPeerStatisticsActions   INTEGER,
        ptL4CvtrPeerStatisticsParentOID OBJECT IDENTIFIER,
        ptL4CvtrPeerStatisticsRowStatus RowStatus,
        ptL4CvtrPeerStatisticsIndex     Integer32
    }

ptL4CvtrPeerStatisticsPeerID OBJECT-TYPE
    SYNTAX          Integer32 (-2147483648..2147483647)
    MAX-ACCESS      read-only
    STATUS          current
    DESCRIPTION     
            "The peer identifier as defined by the converter LDL file."
    ::= { ptL4CvtrPeerStatisticsEntry 1 }

ptL4CvtrPeerStatisticsVariant1Name OBJECT-TYPE
    SYNTAX          DisplayString (SIZE(0..255))
    MAX-ACCESS      read-only
    STATUS          current
    DESCRIPTION     
            "Name of variant 1."
    ::= { ptL4CvtrPeerStatisticsEntry 2 }

ptL4CvtrPeerStatisticsVariant1Received OBJECT-TYPE
    SYNTAX          Integer32 (-2147483648..2147483647)
    MAX-ACCESS      read-only
    STATUS          current
    DESCRIPTION     
            "Number of received MSU by variant 1 on this peer."
    ::= { ptL4CvtrPeerStatisticsEntry 3 }

ptL4CvtrPeerStatisticsVariant1Discarded OBJECT-TYPE
    SYNTAX          Integer32 (-2147483648..2147483647)
    MAX-ACCESS      read-only
    STATUS          current
    DESCRIPTION     
            "Number of discarded MSU by variant 1 on this peer."
    ::= { ptL4CvtrPeerStatisticsEntry 4 }

ptL4CvtrPeerStatisticsVariant1Sent OBJECT-TYPE
    SYNTAX          Integer32 (-2147483648..2147483647)
    MAX-ACCESS      read-only
    STATUS          current
    DESCRIPTION     
            "Number of sent MSU by variant 1 on this peer."
    ::= { ptL4CvtrPeerStatisticsEntry 5 }

ptL4CvtrPeerStatisticsVariant1Generated OBJECT-TYPE
    SYNTAX          Integer32 (-2147483648..2147483647)
    MAX-ACCESS      read-only
    STATUS          current
    DESCRIPTION     
            "Number of generated MSU by variant 1 on this peer."
    ::= { ptL4CvtrPeerStatisticsEntry 6 }

ptL4CvtrPeerStatisticsVariant2Name OBJECT-TYPE
    SYNTAX          DisplayString (SIZE(0..255))
    MAX-ACCESS      read-only
    STATUS          current
    DESCRIPTION     
            "Name of variant 2."
    ::= { ptL4CvtrPeerStatisticsEntry 7 }

ptL4CvtrPeerStatisticsVariant2Received OBJECT-TYPE
    SYNTAX          Integer32 (-2147483648..2147483647)
    MAX-ACCESS      read-only
    STATUS          current
    DESCRIPTION     
            "Number of received MSU by variant 2 on this peer."
    ::= { ptL4CvtrPeerStatisticsEntry 8 }

ptL4CvtrPeerStatisticsVariant2Discarded OBJECT-TYPE
    SYNTAX          Integer32 (-2147483648..2147483647)
    MAX-ACCESS      read-only
    STATUS          current
    DESCRIPTION     
            "Number of discarded MSU by variant 2 on this peer."
    ::= { ptL4CvtrPeerStatisticsEntry 9 }

ptL4CvtrPeerStatisticsVariant2Sent OBJECT-TYPE
    SYNTAX          Integer32 (-2147483648..2147483647)
    MAX-ACCESS      read-only
    STATUS          current
    DESCRIPTION     
            "Number of sent MSU by variant 2 on this peer."
    ::= { ptL4CvtrPeerStatisticsEntry 10 }

ptL4CvtrPeerStatisticsVariant2Generated OBJECT-TYPE
    SYNTAX          Integer32 (-2147483648..2147483647)
    MAX-ACCESS      read-only
    STATUS          current
    DESCRIPTION     
            "Number of generated MSU by variant 2 on this peer."
    ::= { ptL4CvtrPeerStatisticsEntry 11 }

ptL4CvtrPeerStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptL4CvtrPeerStatisticsEntry 12 }

ptL4CvtrPeerStatisticsResetDate OBJECT-TYPE
    SYNTAX          DisplayString (SIZE(0..255))
    MAX-ACCESS      read-only
    STATUS          current
    DESCRIPTION     
            "Date/Time from which the above counts were last started or reset. \nUse the Reset All Stats action to reset the counts."
    ::= { ptL4CvtrPeerStatisticsEntry 13 }

ptL4CvtrPeerStatisticsL4CvtrStatisticsIndex OBJECT-TYPE
    SYNTAX          Integer32 (-2147483648..2147483647)
    MAX-ACCESS      not-accessible
    STATUS          current
    DESCRIPTION     
            "This is the index of the parent type for this object.
             This parent type is L4CvtrStatistics."
    ::= { ptL4CvtrPeerStatisticsEntry 242 }

ptL4CvtrPeerStatisticsActions OBJECT-TYPE
    SYNTAX          INTEGER { refreshAllStats(1), resetAllStats(2) }
    MAX-ACCESS      read-create
    STATUS          current
    DESCRIPTION     
            "The OID of all possible actions for this instance"
    ::= { ptL4CvtrPeerStatisticsEntry 252 }

ptL4CvtrPeerStatisticsParentOID OBJECT-TYPE
    SYNTAX          OBJECT IDENTIFIER
    MAX-ACCESS      read-create
    STATUS          current
    DESCRIPTION     
            "The OID of the parent object for this instance"
    ::= { ptL4CvtrPeerStatisticsEntry 253 }

ptL4CvtrPeerStatisticsRowStatus OBJECT-TYPE
    SYNTAX          RowStatus
    MAX-ACCESS      read-create
    STATUS          current
    DESCRIPTION     
            "The row status for the L4CvtrPeerStatistics table"
    ::= { ptL4CvtrPeerStatisticsEntry 254 }

ptL4CvtrPeerStatisticsIndex OBJECT-TYPE
    SYNTAX          Integer32 (-2147483648..2147483647)
    MAX-ACCESS      not-accessible
    STATUS          current
    DESCRIPTION     
            "The row number for the L4CvtrPeerStatistics table"
    ::= { ptL4CvtrPeerStatisticsEntry 255 }

ptL4CvtrL4CvtrSS7Variant OBJECT IDENTIFIER
    ::= { ptConnGroup 134 }

ptL4CvtrL4CvtrSS7VariantTable OBJECT-TYPE
    SYNTAX          SEQUENCE OF PtL4CvtrL4CvtrSS7VariantEntry
    MAX-ACCESS      not-accessible
    STATUS          current
    DESCRIPTION     
            "No description supplied in the proxy config file."
    ::= { ptL4CvtrL4CvtrSS7Variant 1 }

ptL4CvtrL4CvtrSS7VariantEntry OBJECT-TYPE
    SYNTAX          PtL4CvtrL4CvtrSS7VariantEntry
    MAX-ACCESS      not-accessible
    STATUS          current
    DESCRIPTION     
            "A sequence of L4CvtrL4CvtrSS7Variant attributes."
    INDEX           { ptConnGroupIndex, ptL4CvtrL4CvtrSS7VariantIndex }
    ::= { ptL4CvtrL4CvtrSS7VariantTable 1 }

PtL4CvtrL4CvtrSS7VariantEntry ::=
    SEQUENCE {
        ptL4CvtrL4CvtrSS7VariantName    DisplayString,
        ptL4CvtrL4CvtrSS7VariantSS7Variant  INTEGER,
        ptL4CvtrL4CvtrSS7VariantNetworkIndicator        INTEGER,
        ptL4CvtrL4CvtrSS7VariantConnectionType      INTEGER,
        ptL4CvtrL4CvtrSS7VariantConnectionStatus        INTEGER,
        ptL4CvtrL4CvtrSS7VariantCPASupport  INTEGER,
        ptL4CvtrL4CvtrSS7VariantISUPIAMCLDSTMandatory             INTEGER,
        ptL4CvtrL4CvtrSS7VariantISUPIAMCLGSTMandatory             INTEGER,
        ptL4CvtrL4CvtrSS7VariantSCCPCLDPCConversion           INTEGER,
        ptL4CvtrL4CvtrSS7VariantSCCPCLGPCConversion           INTEGER,
        ptL4CvtrL4CvtrSS7VariantSCCPRelayMateLPC        Integer32,
        ptL4CvtrL4CvtrSS7VariantID      Integer32,
        ptL4CvtrL4CvtrSS7VariantNetworkAppearance         Integer32,
        ptL4CvtrL4CvtrSS7VariantSCCPLPCRegistration           INTEGER,
        ptL4CvtrL4CvtrSS7VariantActions INTEGER,
        ptL4CvtrL4CvtrSS7VariantParentOID OBJECT IDENTIFIER,
        ptL4CvtrL4CvtrSS7VariantRowStatus RowStatus,
        ptL4CvtrL4CvtrSS7VariantIndex   Integer32
    }

ptL4CvtrL4CvtrSS7VariantName OBJECT-TYPE
    SYNTAX          DisplayString (SIZE(0..255))
    MAX-ACCESS      read-create
    STATUS          current
    DESCRIPTION     
            "Name of the SS7 variant."
    ::= { ptL4CvtrL4CvtrSS7VariantEntry 1 }

ptL4CvtrL4CvtrSS7VariantSS7Variant OBJECT-TYPE
    SYNTAX          INTEGER { undefined(255), itu(0), pakistan(1), 
                        india(2), china(3), ansi(4), japanTtc(6), 
                        japanNtt(7), newZealand(8) }
    MAX-ACCESS      read-only
    STATUS          current
    DESCRIPTION     
            "SS7 variant provided by MTP3 on setup."
    ::= { ptL4CvtrL4CvtrSS7VariantEntry 2 }

ptL4CvtrL4CvtrSS7VariantNetworkIndicator OBJECT-TYPE
    SYNTAX          INTEGER { undefined(255), ni00(0), ni01(1), ni10(2), 
                        ni11(3) }
    MAX-ACCESS      read-only
    STATUS          current
    DESCRIPTION     
            "Network indicator of the SS7 variant as per MTP3."
    ::= { ptL4CvtrL4CvtrSS7VariantEntry 3 }

ptL4CvtrL4CvtrSS7VariantConnectionType OBJECT-TYPE
    SYNTAX          INTEGER { ss7(0), ip(1) }
    MAX-ACCESS      read-only
    STATUS          current
    DESCRIPTION     
            "Connection type (SS7/IP) of the SS7 variant."
    ::= { ptL4CvtrL4CvtrSS7VariantEntry 5 }

ptL4CvtrL4CvtrSS7VariantConnectionStatus OBJECT-TYPE
    SYNTAX          INTEGER { unavailable(0), available(1) }
    MAX-ACCESS      read-only
    STATUS          current
    DESCRIPTION     
            "Connection status (AVAILABLE/UNAVAILABLE)."
    ::= { ptL4CvtrL4CvtrSS7VariantEntry 6 }

ptL4CvtrL4CvtrSS7VariantCPASupport OBJECT-TYPE
    SYNTAX          INTEGER { disabled(0), enabled(1) }
    MAX-ACCESS      read-create
    STATUS          current
    DESCRIPTION     
            "Enable or disable the Custom Pass Along (CPA) feature."
    ::= { ptL4CvtrL4CvtrSS7VariantEntry 7 }

ptL4CvtrL4CvtrSS7VariantISUPIAMCLDSTMandatory OBJECT-TYPE
    SYNTAX          INTEGER { disabled(0), enabled(1) }
    MAX-ACCESS      read-create
    STATUS          current
    DESCRIPTION     
            "Enable or disable the mandatory IAM CLD parameter ST value."
    ::= { ptL4CvtrL4CvtrSS7VariantEntry 8 }

ptL4CvtrL4CvtrSS7VariantISUPIAMCLGSTMandatory OBJECT-TYPE
    SYNTAX          INTEGER { disabled(0), enabled(1) }
    MAX-ACCESS      read-create
    STATUS          current
    DESCRIPTION     
            "Enable or disable the mandatory IAM CLG parameter ST value."
    ::= { ptL4CvtrL4CvtrSS7VariantEntry 9 }

ptL4CvtrL4CvtrSS7VariantSCCPCLDPCConversion OBJECT-TYPE
    SYNTAX          INTEGER { noMatchDiscardMsu(0), noMatchRemovePc(1) }
    MAX-ACCESS      read-create
    STATUS          current
    DESCRIPTION     
            "SCCP Called Party Address PC invalid conversion, discard MSU or remove PC."
    ::= { ptL4CvtrL4CvtrSS7VariantEntry 10 }

ptL4CvtrL4CvtrSS7VariantSCCPCLGPCConversion OBJECT-TYPE
    SYNTAX          INTEGER { noMatchDiscardMsu(0), noMatchRemovePc(1) }
    MAX-ACCESS      read-create
    STATUS          current
    DESCRIPTION     
            "SCCP Calling Party Address PC invalid conversion, discard MSU or remove PC."
    ::= { ptL4CvtrL4CvtrSS7VariantEntry 11 }

ptL4CvtrL4CvtrSS7VariantSCCPRelayMateLPC OBJECT-TYPE
    SYNTAX          Integer32 (-2147483648..2147483647)
    MAX-ACCESS      read-create
    STATUS          current
    DESCRIPTION     
            "SCCP Relay Mate Local Point Code as per MTP3 C-link definition. \nTo reset the point code to UNSET, set to -1."
    ::= { ptL4CvtrL4CvtrSS7VariantEntry 12 }

ptL4CvtrL4CvtrSS7VariantID OBJECT-TYPE
    SYNTAX          Integer32 (-2147483648..2147483647)
    MAX-ACCESS      read-only
    STATUS          current
    DESCRIPTION     
            "Unique identifier of the SS7 variant."
    ::= { ptL4CvtrL4CvtrSS7VariantEntry 13 }

ptL4CvtrL4CvtrSS7VariantNetworkAppearance OBJECT-TYPE
    SYNTAX          Integer32 (1..99)
    MAX-ACCESS      read-create
    STATUS          current
    DESCRIPTION     
            "Network Appearance of the SS7 Variant. \nValid range is 1 to 99."
    ::= { ptL4CvtrL4CvtrSS7VariantEntry 14 }

ptL4CvtrL4CvtrSS7VariantSCCPLPCRegistration OBJECT-TYPE
    SYNTAX          INTEGER { disabled(0), enabled(1) }
    MAX-ACCESS      read-create
    STATUS          current
    DESCRIPTION     
            "SCCP LPC Registration for GTT override support (ENABLED/DISABLED). \nIf the NA requires GTT processing via the LPC, the L4 Converter must disable the registration for SCCP (SI 3) on the LPC as defined and triggered by an associated Route Mapping Mirror PC. \nDoes not impact ISUP (SI 5) registration. \nThis feature should never be disabled unless instructed by Customer Support. \nDefault: ENABLED."
    ::= { ptL4CvtrL4CvtrSS7VariantEntry 15 }

ptL4CvtrL4CvtrSS7VariantActions OBJECT-TYPE
    SYNTAX          INTEGER { loadDefaultRules(1), clearRules(2) }
    MAX-ACCESS      read-create
    STATUS          current
    DESCRIPTION     
            "The OID of all possible actions for this instance"
    ::= { ptL4CvtrL4CvtrSS7VariantEntry 252 }

ptL4CvtrL4CvtrSS7VariantParentOID OBJECT-TYPE
    SYNTAX          OBJECT IDENTIFIER
    MAX-ACCESS      read-create
    STATUS          current
    DESCRIPTION     
            "The OID of the parent object for this instance"
    ::= { ptL4CvtrL4CvtrSS7VariantEntry 253 }

ptL4CvtrL4CvtrSS7VariantRowStatus OBJECT-TYPE
    SYNTAX          RowStatus
    MAX-ACCESS      read-create
    STATUS          current
    DESCRIPTION     
            "The row status for the L4CvtrL4CvtrSS7Variant table"
    ::= { ptL4CvtrL4CvtrSS7VariantEntry 254 }

ptL4CvtrL4CvtrSS7VariantIndex OBJECT-TYPE
    SYNTAX          Integer32 (-2147483648..2147483647)
    MAX-ACCESS      not-accessible
    STATUS          current
    DESCRIPTION     
            "The row number for the L4CvtrL4CvtrSS7Variant table"
    ::= { ptL4CvtrL4CvtrSS7VariantEntry 255 }

ptL4CvtrRouteMappings OBJECT IDENTIFIER
    ::= { ptL4CvtrL4CvtrSS7Variant 139 }

ptL4CvtrRouteMappingsTable OBJECT-TYPE
    SYNTAX          SEQUENCE OF PtL4CvtrRouteMappingsEntry
    MAX-ACCESS      not-accessible
    STATUS          current
    DESCRIPTION     
            "No description supplied in the proxy config file."
    ::= { ptL4CvtrRouteMappings 1 }

ptL4CvtrRouteMappingsEntry OBJECT-TYPE
    SYNTAX          PtL4CvtrRouteMappingsEntry
    MAX-ACCESS      not-accessible
    STATUS          current
    DESCRIPTION     
            "A sequence of L4CvtrRouteMappings attributes."
    INDEX           { ptConnGroupIndex, 
                      ptL4CvtrRouteMappingsL4CvtrSS7VariantIndex, 
                      ptL4CvtrRouteMappingsIndex }
    ::= { ptL4CvtrRouteMappingsTable 1 }

PtL4CvtrRouteMappingsEntry ::=
    SEQUENCE {
        ptL4CvtrRouteMappingsRouteMappings  Integer32,
        ptL4CvtrRouteMappingsL4CvtrSS7VariantIndex          Integer32,
        ptL4CvtrRouteMappingsParentOID  OBJECT IDENTIFIER,
        ptL4CvtrRouteMappingsRowStatus  RowStatus,
        ptL4CvtrRouteMappingsIndex      Integer32
    }

ptL4CvtrRouteMappingsRouteMappings OBJECT-TYPE
    SYNTAX          Integer32 (-2147483648..2147483647)
    MAX-ACCESS      read-only
    STATUS          current
    DESCRIPTION     
            "Number of Route Mappings"
    ::= { ptL4CvtrRouteMappingsEntry 1 }

ptL4CvtrRouteMappingsL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrRouteMappingsEntry 242 }

ptL4CvtrRouteMappingsParentOID OBJECT-TYPE
    SYNTAX          OBJECT IDENTIFIER
    MAX-ACCESS      read-create
    STATUS          current
    DESCRIPTION     
            "The OID of the parent object for this instance"
    ::= { ptL4CvtrRouteMappingsEntry 253 }

ptL4CvtrRouteMappingsRowStatus OBJECT-TYPE
    SYNTAX          RowStatus
    MAX-ACCESS      read-create
    STATUS          current
    DESCRIPTION     
            "The row status for the L4CvtrRouteMappings table"
    ::= { ptL4CvtrRouteMappingsEntry 254 }

ptL4CvtrRouteMappingsIndex OBJECT-TYPE
    SYNTAX          Integer32 (-2147483648..2147483647)
    MAX-ACCESS      not-accessible
    STATUS          current
    DESCRIPTION     
            "The row number for the L4CvtrRouteMappings table"
    ::= { ptL4CvtrRouteMappingsEntry 255 }

ptL4CvtrRouteMapping OBJECT IDENTIFIER
    ::= { ptL4CvtrRouteMappings 135 }

ptL4CvtrRouteMappingTable OBJECT-TYPE
    SYNTAX          SEQUENCE OF PtL4CvtrRouteMappingEntry
    MAX-ACCESS      not-accessible
    STATUS          current
    DESCRIPTION     
            "No description supplied in the proxy config file."
    ::= { ptL4CvtrRouteMapping 1 }

ptL4CvtrRouteMappingEntry OBJECT-TYPE
    SYNTAX          PtL4CvtrRouteMappingEntry
    MAX-ACCESS      not-accessible
    STATUS          current
    DESCRIPTION     
            "A sequence of L4CvtrRouteMapping attributes."
    INDEX           { ptConnGroupIndex, 
                      ptL4CvtrRouteMappingL4CvtrSS7VariantIndex, 
                      ptL4CvtrRouteMappingRouteMappingsIndex, 
                      ptL4CvtrRouteMappingIndex }
    ::= { ptL4CvtrRouteMappingTable 1 }

PtL4CvtrRouteMappingEntry ::=
    SEQUENCE {
        ptL4CvtrRouteMappingHomePC      Integer32,
        ptL4CvtrRouteMappingMirrorPC    Integer32,
        ptL4CvtrRouteMappingDescription DisplayString,
        ptL4CvtrRouteMappingRouteMappingConversion          INTEGER,
        ptL4CvtrRouteMappingANSICountryCode   INTEGER,
        ptL4CvtrRouteMappingANSICCRLPAResponse      INTEGER,
        ptL4CvtrRouteMappingANSICGAckBroadcast      INTEGER,
        ptL4CvtrRouteMappingANSICLDNOA  INTEGER,
        ptL4CvtrRouteMappingANSICLGNOA  INTEGER,
        ptL4CvtrRouteMappingANSIFCIInternational        INTEGER,
        ptL4CvtrRouteMappingANSISendMsgTwice    INTEGER,
        ptL4CvtrRouteMappingANSICG32Support   INTEGER,
        ptL4CvtrRouteMappingANSIUSITMRFallback      INTEGER,
        ptL4CvtrRouteMappingITUCountryCode  Integer32,
        ptL4CvtrRouteMappingITUCLDNOA   INTEGER,
        ptL4CvtrRouteMappingITUCLGNOA   INTEGER,
        ptL4CvtrRouteMappingITUFCIInternational       INTEGER,
        ptL4CvtrRouteMappingITUMinCLDANSIIAM    Integer32,
        ptL4CvtrRouteMappingITUMaxNumberOfSAM     Integer32,
        ptL4CvtrRouteMappingITUSAMOverlapTimer      INTEGER,
        ptL4CvtrRouteMappingITUUSIDiscard INTEGER,
        ptL4CvtrRouteMappingMandatoryACMBCI   INTEGER,
        ptL4CvtrRouteMappingACMBCICharge Integer32,
        ptL4CvtrRouteMappingACMBCICLD   Integer32,
        ptL4CvtrRouteMappingACMBCIISDNAccess    INTEGER,
        ptL4CvtrRouteMappingMandatoryANMBCI   INTEGER,
        ptL4CvtrRouteMappingANMBCICharge Integer32,
        ptL4CvtrRouteMappingANMBCICLD   Integer32,
        ptL4CvtrRouteMappingANMBCIISDNAccess    INTEGER,
        ptL4CvtrRouteMappingOverloadSupport   INTEGER,
        ptL4CvtrRouteMappingHomePCSecondary   Integer32,
        ptL4CvtrRouteMappingMirrorPCSecondary     Integer32,
        ptL4CvtrRouteMappingHomePCTertiary  Integer32,
        ptL4CvtrRouteMappingMirrorPCTertiary    Integer32,
        ptL4CvtrRouteMappingIncomingAppID DisplayString,
        ptL4CvtrRouteMappingL4CvtrSS7VariantIndex         Integer32,
        ptL4CvtrRouteMappingRouteMappingsIndex      Integer32,
        ptL4CvtrRouteMappingParentOID   OBJECT IDENTIFIER,
        ptL4CvtrRouteMappingRowStatus   RowStatus,
        ptL4CvtrRouteMappingIndex       Integer32
    }

ptL4CvtrRouteMappingHomePC OBJECT-TYPE
    SYNTAX          Integer32 (-2147483648..2147483647)
    MAX-ACCESS      read-only
    STATUS          current
    DESCRIPTION     
            "Switch Point Code in the home network."
    ::= { ptL4CvtrRouteMappingEntry 1 }

ptL4CvtrRouteMappingMirrorPC OBJECT-TYPE
    SYNTAX          Integer32 (-2147483648..2147483647)
    MAX-ACCESS      read-only
    STATUS          current
    DESCRIPTION     
            "Mirror Point Code in the other network."
    ::= { ptL4CvtrRouteMappingEntry 2 }

ptL4CvtrRouteMappingDescription OBJECT-TYPE
    SYNTAX          DisplayString (SIZE(0..255))
    MAX-ACCESS      read-create
    STATUS          current
    DESCRIPTION     
            "Route Mapping description."
    ::= { ptL4CvtrRouteMappingEntry 3 }

ptL4CvtrRouteMappingRouteMappingConversion OBJECT-TYPE
    SYNTAX          INTEGER { notApplicable(0) }
    MAX-ACCESS      read-only
    STATUS          current
    DESCRIPTION     
            "This screen is not applicable for given variants."
    ::= { ptL4CvtrRouteMappingEntry 4 }

ptL4CvtrRouteMappingANSICountryCode OBJECT-TYPE
    SYNTAX          INTEGER { disabled(0), enabled(1) }
    MAX-ACCESS      read-create
    STATUS          current
    DESCRIPTION     
            "ANSI country code."
    ::= { ptL4CvtrRouteMappingEntry 5 }

ptL4CvtrRouteMappingANSICCRLPAResponse OBJECT-TYPE
    SYNTAX          INTEGER { disabled(0), enabled(1) }
    MAX-ACCESS      read-create
    STATUS          current
    DESCRIPTION     
            "ANSI requires loop back ack to a CCR msg."
    ::= { ptL4CvtrRouteMappingEntry 6 }

ptL4CvtrRouteMappingANSICGAckBroadcast OBJECT-TYPE
    SYNTAX          INTEGER { disabled(0), enabled(1) }
    MAX-ACCESS      read-create
    STATUS          current
    DESCRIPTION     
            "ANSI broadcast CG ack msg."
    ::= { ptL4CvtrRouteMappingEntry 7 }

ptL4CvtrRouteMappingANSICLDNOA OBJECT-TYPE
    SYNTAX          INTEGER { disabled(0), enabled(1) }
    MAX-ACCESS      read-create
    STATUS          current
    DESCRIPTION     
            "ANSI force CLD nature of address to national."
    ::= { ptL4CvtrRouteMappingEntry 8 }

ptL4CvtrRouteMappingANSICLGNOA OBJECT-TYPE
    SYNTAX          INTEGER { disabled(0), enabled(1) }
    MAX-ACCESS      read-create
    STATUS          current
    DESCRIPTION     
            "ANSI force CLG nature of address to national."
    ::= { ptL4CvtrRouteMappingEntry 9 }

ptL4CvtrRouteMappingANSIFCIInternational OBJECT-TYPE
    SYNTAX          INTEGER { disabled(0), enabled(1) }
    MAX-ACCESS      read-create
    STATUS          current
    DESCRIPTION     
            "ANSI forward call indicator."
    ::= { ptL4CvtrRouteMappingEntry 10 }

ptL4CvtrRouteMappingANSISendMsgTwice OBJECT-TYPE
    SYNTAX          INTEGER { disabled(0), enabled(1) }
    MAX-ACCESS      read-create
    STATUS          current
    DESCRIPTION     
            "ANSI send certain messages twice."
    ::= { ptL4CvtrRouteMappingEntry 11 }

ptL4CvtrRouteMappingANSICG32Support OBJECT-TYPE
    SYNTAX          INTEGER { disabled(0), enabled(1) }
    MAX-ACCESS      read-create
    STATUS          current
    DESCRIPTION     
            "ANSI switch supports circuit group 32-bit range."
    ::= { ptL4CvtrRouteMappingEntry 12 }

ptL4CvtrRouteMappingANSIUSITMRFallback OBJECT-TYPE
    SYNTAX          INTEGER { disabled(0), enabled(1) }
    MAX-ACCESS      read-create
    STATUS          current
    DESCRIPTION     
            "ANSI CPAP USI TMP fallback mgmt."
    ::= { ptL4CvtrRouteMappingEntry 13 }

ptL4CvtrRouteMappingITUCountryCode OBJECT-TYPE
    SYNTAX          Integer32 (0..999)
    MAX-ACCESS      read-create
    STATUS          current
    DESCRIPTION     
            "ITU country code (0..999)."
    ::= { ptL4CvtrRouteMappingEntry 15 }

ptL4CvtrRouteMappingITUCLDNOA OBJECT-TYPE
    SYNTAX          INTEGER { disabled(0), enabled(1) }
    MAX-ACCESS      read-create
    STATUS          current
    DESCRIPTION     
            "ITU force CLD nature of address to national."
    ::= { ptL4CvtrRouteMappingEntry 16 }

ptL4CvtrRouteMappingITUCLGNOA OBJECT-TYPE
    SYNTAX          INTEGER { disabled(0), enabled(1) }
    MAX-ACCESS      read-create
    STATUS          current
    DESCRIPTION     
            "ITU force CLG nature of address to national."
    ::= { ptL4CvtrRouteMappingEntry 17 }

ptL4CvtrRouteMappingITUFCIInternational OBJECT-TYPE
    SYNTAX          INTEGER { disabled(0), enabled(1) }
    MAX-ACCESS      read-create
    STATUS          current
    DESCRIPTION     
            "ITU forward call indicator."
    ::= { ptL4CvtrRouteMappingEntry 18 }

ptL4CvtrRouteMappingITUMinCLDANSIIAM OBJECT-TYPE
    SYNTAX          Integer32 (0..32)
    MAX-ACCESS      read-create
    STATUS          current
    DESCRIPTION     
            "ITU minimum number of digits required in ANSI IAM (0..32)."
    ::= { ptL4CvtrRouteMappingEntry 19 }

ptL4CvtrRouteMappingITUMaxNumberOfSAM OBJECT-TYPE
    SYNTAX          Integer32 (0..32)
    MAX-ACCESS      read-create
    STATUS          current
    DESCRIPTION     
            "ITU maximum number of expected SAM msgs (0..32)."
    ::= { ptL4CvtrRouteMappingEntry 20 }

ptL4CvtrRouteMappingITUSAMOverlapTimer OBJECT-TYPE
    SYNTAX          INTEGER { disabled(0) }
    MAX-ACCESS      read-create
    STATUS          current
    DESCRIPTION     
            "ITU SAM overlap timer. Set to 0 to disable."
    ::= { ptL4CvtrRouteMappingEntry 21 }

ptL4CvtrRouteMappingITUUSIDiscard OBJECT-TYPE
    SYNTAX          INTEGER { disabled(0), enabled(1) }
    MAX-ACCESS      read-create
    STATUS          current
    DESCRIPTION     
            "ITU discard USI."
    ::= { ptL4CvtrRouteMappingEntry 22 }

ptL4CvtrRouteMappingMandatoryACMBCI OBJECT-TYPE
    SYNTAX          INTEGER { disabled(0), enabled(1) }
    MAX-ACCESS      read-create
    STATUS          current
    DESCRIPTION     
            "Japan ACM BCI parameter is mandatory."
    ::= { ptL4CvtrRouteMappingEntry 23 }

ptL4CvtrRouteMappingACMBCICharge OBJECT-TYPE
    SYNTAX          Integer32 (0..3)
    MAX-ACCESS      read-create
    STATUS          current
    DESCRIPTION     
            "Japan ACM BCI Charge value (BA bits)."
    ::= { ptL4CvtrRouteMappingEntry 24 }

ptL4CvtrRouteMappingACMBCICLD OBJECT-TYPE
    SYNTAX          Integer32 (0..3)
    MAX-ACCESS      read-create
    STATUS          current
    DESCRIPTION     
            "Japan ACM BCI CLD value (DC bits)."
    ::= { ptL4CvtrRouteMappingEntry 25 }

ptL4CvtrRouteMappingACMBCIISDNAccess OBJECT-TYPE
    SYNTAX          INTEGER { disabled(0), enabled(1) }
    MAX-ACCESS      read-create
    STATUS          current
    DESCRIPTION     
            "Japan ACM BCI ISDN Access value."
    ::= { ptL4CvtrRouteMappingEntry 26 }

ptL4CvtrRouteMappingMandatoryANMBCI OBJECT-TYPE
    SYNTAX          INTEGER { disabled(0), enabled(1) }
    MAX-ACCESS      read-create
    STATUS          current
    DESCRIPTION     
            "Japan ANM BCI parameter is mandatory."
    ::= { ptL4CvtrRouteMappingEntry 27 }

ptL4CvtrRouteMappingANMBCICharge OBJECT-TYPE
    SYNTAX          Integer32 (0..3)
    MAX-ACCESS      read-create
    STATUS          current
    DESCRIPTION     
            "Japan ANM BCI Charge value (BA bits)."
    ::= { ptL4CvtrRouteMappingEntry 28 }

ptL4CvtrRouteMappingANMBCICLD OBJECT-TYPE
    SYNTAX          Integer32 (0..3)
    MAX-ACCESS      read-create
    STATUS          current
    DESCRIPTION     
            "Japan ANM BCI CLD value (DC bits)."
    ::= { ptL4CvtrRouteMappingEntry 29 }

ptL4CvtrRouteMappingANMBCIISDNAccess OBJECT-TYPE
    SYNTAX          INTEGER { disabled(0), enabled(1) }
    MAX-ACCESS      read-create
    STATUS          current
    DESCRIPTION     
            "Japan ANM BCI ISDN Access value."
    ::= { ptL4CvtrRouteMappingEntry 30 }

ptL4CvtrRouteMappingOverloadSupport OBJECT-TYPE
    SYNTAX          INTEGER { disabled(0), enabled(1) }
    MAX-ACCESS      read-create
    STATUS          current
    DESCRIPTION     
            "NZ to ITU for Overload national support."
    ::= { ptL4CvtrRouteMappingEntry 31 }

ptL4CvtrRouteMappingHomePCSecondary OBJECT-TYPE
    SYNTAX          Integer32 (-2147483648..2147483647)
    MAX-ACCESS      read-create
    STATUS          current
    DESCRIPTION     
            "Switch Point Code in the home network (secondary). \nUsed with SCCP Relay if Mate LPC is defined. \nTo reset the point code to UNSET, set to -1."
    ::= { ptL4CvtrRouteMappingEntry 32 }

ptL4CvtrRouteMappingMirrorPCSecondary OBJECT-TYPE
    SYNTAX          Integer32 (-2147483648..2147483647)
    MAX-ACCESS      read-create
    STATUS          current
    DESCRIPTION     
            "Mirror Point Code in the other network (secondary). \nUsed with SCCP Relay if Mate LPC is defined. \nTo reset the point code to UNSET, set to -1."
    ::= { ptL4CvtrRouteMappingEntry 33 }

ptL4CvtrRouteMappingHomePCTertiary OBJECT-TYPE
    SYNTAX          Integer32 (-2147483648..2147483647)
    MAX-ACCESS      read-create
    STATUS          current
    DESCRIPTION     
            "Switch Point Code in the home network (tertiary). \nUsed with SCCP Relay if Mate LPC is defined. \nTo reset the point code to UNSET, set to -1."
    ::= { ptL4CvtrRouteMappingEntry 34 }

ptL4CvtrRouteMappingMirrorPCTertiary OBJECT-TYPE
    SYNTAX          Integer32 (-2147483648..2147483647)
    MAX-ACCESS      read-create
    STATUS          current
    DESCRIPTION     
            "Mirror Point Code in the other network (tertiary). \nUsed with SCCP Relay if Mate LPC is defined. \nTo reset the point code to UNSET, set to -1."
    ::= { ptL4CvtrRouteMappingEntry 35 }

ptL4CvtrRouteMappingIncomingAppID OBJECT-TYPE
    SYNTAX          DisplayString (SIZE(0..255))
    MAX-ACCESS      read-create
    STATUS          current
    DESCRIPTION     
            "Incoming AppID for Gateway Screening. \nOn creation, the attribute is defaulted to an empty string which disables the feature. \nAlphanumeric, dash, and underscore for a maximum of 16 characters including the terminating null."
    ::= { ptL4CvtrRouteMappingEntry 36 }

ptL4CvtrRouteMappingL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrRouteMappingEntry 242 }

ptL4CvtrRouteMappingRouteMappingsIndex OBJECT-TYPE
    SYNTAX          Integer32 (-2147483648..2147483647)
    MAX-ACCESS      not-accessible
    STATUS          current
    DESCRIPTION     
            "This is the index of the parent type for this object.
             This parent type is RouteMappings."
    ::= { ptL4CvtrRouteMappingEntry 243 }

ptL4CvtrRouteMappingParentOID OBJECT-TYPE
    SYNTAX          OBJECT IDENTIFIER
    MAX-ACCESS      read-create
    STATUS          current
    DESCRIPTION     
            "The OID of the parent object for this instance"
    ::= { ptL4CvtrRouteMappingEntry 253 }

ptL4CvtrRouteMappingRowStatus OBJECT-TYPE
    SYNTAX          RowStatus
    MAX-ACCESS      read-create
    STATUS          current
    DESCRIPTION     
            "The row status for the L4CvtrRouteMapping table"
    ::= { ptL4CvtrRouteMappingEntry 254 }

ptL4CvtrRouteMappingIndex OBJECT-TYPE
    SYNTAX          Integer32 (-2147483648..2147483647)
    MAX-ACCESS      not-accessible
    STATUS          current
    DESCRIPTION     
            "The row number for the L4CvtrRouteMapping table"
    ::= { ptL4CvtrRouteMappingEntry 255 }

ptL4CvtrMessageRules OBJECT IDENTIFIER
    ::= { ptL4CvtrL4CvtrSS7Variant 140 }

ptL4CvtrMessageRulesTable OBJECT-TYPE
    SYNTAX          SEQUENCE OF PtL4CvtrMessageRulesEntry
    MAX-ACCESS      not-accessible
    STATUS          current
    DESCRIPTION     
            "No description supplied in the proxy config file."
    ::= { ptL4CvtrMessageRules 1 }

ptL4CvtrMessageRulesEntry OBJECT-TYPE
    SYNTAX          PtL4CvtrMessageRulesEntry
    MAX-ACCESS      not-accessible
    STATUS          current
    DESCRIPTION     
            "A sequence of L4CvtrMessageRules attributes."
    INDEX           { ptConnGroupIndex, 
                      ptL4CvtrMessageRulesL4CvtrSS7VariantIndex, 
                      ptL4CvtrMessageRulesIndex }
    ::= { ptL4CvtrMessageRulesTable 1 }

PtL4CvtrMessageRulesEntry ::=
    SEQUENCE {
        ptL4CvtrMessageRulesMessageRules Integer32,
        ptL4CvtrMessageRulesL4CvtrSS7VariantIndex         Integer32,
        ptL4CvtrMessageRulesParentOID   OBJECT IDENTIFIER,
        ptL4CvtrMessageRulesRowStatus   RowStatus,
        ptL4CvtrMessageRulesIndex       Integer32
    }

ptL4CvtrMessageRulesMessageRules OBJECT-TYPE
    SYNTAX          Integer32 (-2147483648..2147483647)
    MAX-ACCESS      read-only
    STATUS          current
    DESCRIPTION     
            "Number of Message Rules"
    ::= { ptL4CvtrMessageRulesEntry 1 }

ptL4CvtrMessageRulesL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrMessageRulesEntry 242 }

ptL4CvtrMessageRulesParentOID OBJECT-TYPE
    SYNTAX          OBJECT IDENTIFIER
    MAX-ACCESS      read-create
    STATUS          current
    DESCRIPTION     
            "The OID of the parent object for this instance"
    ::= { ptL4CvtrMessageRulesEntry 253 }

ptL4CvtrMessageRulesRowStatus OBJECT-TYPE
    SYNTAX          RowStatus
    MAX-ACCESS      read-create
    STATUS          current
    DESCRIPTION     
            "The row status for the L4CvtrMessageRules table"
    ::= { ptL4CvtrMessageRulesEntry 254 }

ptL4CvtrMessageRulesIndex OBJECT-TYPE
    SYNTAX          Integer32 (-2147483648..2147483647)
    MAX-ACCESS      not-accessible
    STATUS          current
    DESCRIPTION     
            "The row number for the L4CvtrMessageRules table"
    ::= { ptL4CvtrMessageRulesEntry 255 }

ptL4CvtrMessageRule OBJECT IDENTIFIER
    ::= { ptL4CvtrMessageRules 136 }

ptL4CvtrMessageRuleTable OBJECT-TYPE
    SYNTAX          SEQUENCE OF PtL4CvtrMessageRuleEntry
    MAX-ACCESS      not-accessible
    STATUS          current
    DESCRIPTION     
            "No description supplied in the proxy config file."
    ::= { ptL4CvtrMessageRule 1 }

ptL4CvtrMessageRuleEntry OBJECT-TYPE
    SYNTAX          PtL4CvtrMessageRuleEntry
    MAX-ACCESS      not-accessible
    STATUS          current
    DESCRIPTION     
            "A sequence of L4CvtrMessageRule attributes."
    INDEX           { ptConnGroupIndex, 
                      ptL4CvtrMessageRuleL4CvtrSS7VariantIndex, 
                      ptL4CvtrMessageRuleMessageRulesIndex, 
                      ptL4CvtrMessageRuleIndex }
    ::= { ptL4CvtrMessageRuleTable 1 }

PtL4CvtrMessageRuleEntry ::=
    SEQUENCE {
        ptL4CvtrMessageRuleMessageID    Integer32,
        ptL4CvtrMessageRuleAction       INTEGER,
        ptL4CvtrMessageRuleDescription  DisplayString,
        ptL4CvtrMessageRuleSI           INTEGER,
        ptL4CvtrMessageRuleL4CvtrSS7VariantIndex        Integer32,
        ptL4CvtrMessageRuleMessageRulesIndex    Integer32,
        ptL4CvtrMessageRuleParentOID    OBJECT IDENTIFIER,
        ptL4CvtrMessageRuleRowStatus    RowStatus,
        ptL4CvtrMessageRuleIndex        Integer32
    }

ptL4CvtrMessageRuleMessageID OBJECT-TYPE
    SYNTAX          Integer32 (-2147483648..2147483647)
    MAX-ACCESS      read-only
    STATUS          current
    DESCRIPTION     
            "Message Rule message identifier as per SS7 specifications."
    ::= { ptL4CvtrMessageRuleEntry 1 }

ptL4CvtrMessageRuleAction OBJECT-TYPE
    SYNTAX          INTEGER { discard(0), passThrough(1), process(2), 
                        cpam(3) }
    MAX-ACCESS      read-create
    STATUS          current
    DESCRIPTION     
            "Message Rule Action (DISCARD/PASS THROUGH/PROCESS/CPAM). \nMessage rules necessary to the conversion must be set on initial setup via the SS7 Variant object Load Default Rules action once both SS7 Variants are set. The message rule action applies to all MSUs with the matching SI and ID received by the associated SS7 Variant. \nIf no message rule is found for an incoming MSU, the default action is PASS THROUGH. \nThe default rules apply may be enhanced as required by the network deployment or the national variant. \nSet the action to DISCARD to discard the matching MSUs. \nSet the action to PASS THROUGH to forward the matching MSUs with no additional conversions beyond the routing label and no parameter rules are applied. \nSet the action to PROCESS to trigger pre-defined conversion and apply parameter rules to matching MSUs. \nThe CPAM action is reserved for SS7-IP deployments to encapsulate the matching MSUs to the IP network."
    ::= { ptL4CvtrMessageRuleEntry 2 }

ptL4CvtrMessageRuleDescription OBJECT-TYPE
    SYNTAX          DisplayString (SIZE(0..255))
    MAX-ACCESS      read-create
    STATUS          current
    DESCRIPTION     
            "Message Rule description."
    ::= { ptL4CvtrMessageRuleEntry 3 }

ptL4CvtrMessageRuleSI OBJECT-TYPE
    SYNTAX          INTEGER { isup(5), sccp(3) }
    MAX-ACCESS      read-create
    STATUS          current
    DESCRIPTION     
            "Message Rule signaling indicator (ISUP/SCCP)."
    ::= { ptL4CvtrMessageRuleEntry 4 }

ptL4CvtrMessageRuleL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrMessageRuleEntry 242 }

ptL4CvtrMessageRuleMessageRulesIndex OBJECT-TYPE
    SYNTAX          Integer32 (-2147483648..2147483647)
    MAX-ACCESS      not-accessible
    STATUS          current
    DESCRIPTION     
            "This is the index of the parent type for this object.
             This parent type is MessageRules."
    ::= { ptL4CvtrMessageRuleEntry 243 }

ptL4CvtrMessageRuleParentOID OBJECT-TYPE
    SYNTAX          OBJECT IDENTIFIER
    MAX-ACCESS      read-create
    STATUS          current
    DESCRIPTION     
            "The OID of the parent object for this instance"
    ::= { ptL4CvtrMessageRuleEntry 253 }

ptL4CvtrMessageRuleRowStatus OBJECT-TYPE
    SYNTAX          RowStatus
    MAX-ACCESS      read-create
    STATUS          current
    DESCRIPTION     
            "The row status for the L4CvtrMessageRule table"
    ::= { ptL4CvtrMessageRuleEntry 254 }

ptL4CvtrMessageRuleIndex OBJECT-TYPE
    SYNTAX          Integer32 (-2147483648..2147483647)
    MAX-ACCESS      not-accessible
    STATUS          current
    DESCRIPTION     
            "The row number for the L4CvtrMessageRule table"
    ::= { ptL4CvtrMessageRuleEntry 255 }

ptL4CvtrParameterRules OBJECT IDENTIFIER
    ::= { ptL4CvtrL4CvtrSS7Variant 141 }

ptL4CvtrParameterRulesTable OBJECT-TYPE
    SYNTAX          SEQUENCE OF PtL4CvtrParameterRulesEntry
    MAX-ACCESS      not-accessible
    STATUS          current
    DESCRIPTION     
            "No description supplied in the proxy config file."
    ::= { ptL4CvtrParameterRules 1 }

ptL4CvtrParameterRulesEntry OBJECT-TYPE
    SYNTAX          PtL4CvtrParameterRulesEntry
    MAX-ACCESS      not-accessible
    STATUS          current
    DESCRIPTION     
            "A sequence of L4CvtrParameterRules attributes."
    INDEX           { ptConnGroupIndex, 
                      ptL4CvtrParameterRulesL4CvtrSS7VariantIndex, 
                      ptL4CvtrParameterRulesIndex }
    ::= { ptL4CvtrParameterRulesTable 1 }

PtL4CvtrParameterRulesEntry ::=
    SEQUENCE {
        ptL4CvtrParameterRulesParameterRules    Integer32,
        ptL4CvtrParameterRulesL4CvtrSS7VariantIndex           Integer32,
        ptL4CvtrParameterRulesParentOID OBJECT IDENTIFIER,
        ptL4CvtrParameterRulesRowStatus RowStatus,
        ptL4CvtrParameterRulesIndex     Integer32
    }

ptL4CvtrParameterRulesParameterRules OBJECT-TYPE
    SYNTAX          Integer32 (-2147483648..2147483647)
    MAX-ACCESS      read-only
    STATUS          current
    DESCRIPTION     
            "Number of Parameter Rules"
    ::= { ptL4CvtrParameterRulesEntry 1 }

ptL4CvtrParameterRulesL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrParameterRulesEntry 242 }

ptL4CvtrParameterRulesParentOID OBJECT-TYPE
    SYNTAX          OBJECT IDENTIFIER
    MAX-ACCESS      read-create
    STATUS          current
    DESCRIPTION     
            "The OID of the parent object for this instance"
    ::= { ptL4CvtrParameterRulesEntry 253 }

ptL4CvtrParameterRulesRowStatus OBJECT-TYPE
    SYNTAX          RowStatus
    MAX-ACCESS      read-create
    STATUS          current
    DESCRIPTION     
            "The row status for the L4CvtrParameterRules table"
    ::= { ptL4CvtrParameterRulesEntry 254 }

ptL4CvtrParameterRulesIndex OBJECT-TYPE
    SYNTAX          Integer32 (-2147483648..2147483647)
    MAX-ACCESS      not-accessible
    STATUS          current
    DESCRIPTION     
            "The row number for the L4CvtrParameterRules table"
    ::= { ptL4CvtrParameterRulesEntry 255 }

ptL4CvtrParameterRule OBJECT IDENTIFIER
    ::= { ptL4CvtrParameterRules 137 }

ptL4CvtrParameterRuleTable OBJECT-TYPE
    SYNTAX          SEQUENCE OF PtL4CvtrParameterRuleEntry
    MAX-ACCESS      not-accessible
    STATUS          current
    DESCRIPTION     
            "No description supplied in the proxy config file."
    ::= { ptL4CvtrParameterRule 1 }

ptL4CvtrParameterRuleEntry OBJECT-TYPE
    SYNTAX          PtL4CvtrParameterRuleEntry
    MAX-ACCESS      not-accessible
    STATUS          current
    DESCRIPTION     
            "A sequence of L4CvtrParameterRule attributes."
    INDEX           { ptConnGroupIndex, 
                      ptL4CvtrParameterRuleL4CvtrSS7VariantIndex, 
                      ptL4CvtrParameterRuleParameterRulesIndex, 
                      ptL4CvtrParameterRuleIndex }
    ::= { ptL4CvtrParameterRuleTable 1 }

PtL4CvtrParameterRuleEntry ::=
    SEQUENCE {
        ptL4CvtrParameterRuleParameterID Integer32,
        ptL4CvtrParameterRuleAction     INTEGER,
        ptL4CvtrParameterRuleDescription DisplayString,
        ptL4CvtrParameterRuleSI         INTEGER,
        ptL4CvtrParameterRuleL4CvtrSS7VariantIndex          Integer32,
        ptL4CvtrParameterRuleParameterRulesIndex        Integer32,
        ptL4CvtrParameterRuleParentOID  OBJECT IDENTIFIER,
        ptL4CvtrParameterRuleRowStatus  RowStatus,
        ptL4CvtrParameterRuleIndex      Integer32
    }

ptL4CvtrParameterRuleParameterID OBJECT-TYPE
    SYNTAX          Integer32 (-2147483648..2147483647)
    MAX-ACCESS      read-only
    STATUS          current
    DESCRIPTION     
            "Parameter Rule parameter identifier as per SS7 specifications."
    ::= { ptL4CvtrParameterRuleEntry 1 }

ptL4CvtrParameterRuleAction OBJECT-TYPE
    SYNTAX          INTEGER { discard(0), passThrough(1), process(2), 
                        cpap(3) }
    MAX-ACCESS      read-create
    STATUS          current
    DESCRIPTION     
            "Parameter Rule Action (DISCARD/PASS THROUGH/PROCESS/CPAP). \nParameter rules necessary to the conversion must be set on initial setup via the SS7 Variant object Load Default Rules action once both SS7 Variants are set. The parameter rule action applies to parameters with the matching SI and ID in MSUs with a correlated PROCESS Message Rule received by the associated SS7 Variant. If the Message Rule action is not set to PROCESS, the parameter, if present, is forwarded with no modification. \nIf no parameter rule is found for a PROCESS MSU, the default action is PASS THROUGH. \nThe default rules apply may be enhanced as required by the network deployment or the national variant. \nSet the action to DISCARD to discard the matching parameter. \nSet the action to PASS THROUGH to forward the matching parameter with no modification. \nSet the action to PROCESS to trigger pre-defined conversion. \nThe CPAP action is reserved for SS7-IP deployments to encapsulate the matching parameters to the IP network."
    ::= { ptL4CvtrParameterRuleEntry 2 }

ptL4CvtrParameterRuleDescription OBJECT-TYPE
    SYNTAX          DisplayString (SIZE(0..255))
    MAX-ACCESS      read-create
    STATUS          current
    DESCRIPTION     
            "Parameter Rule description."
    ::= { ptL4CvtrParameterRuleEntry 3 }

ptL4CvtrParameterRuleSI OBJECT-TYPE
    SYNTAX          INTEGER { isup(5), sccp(3) }
    MAX-ACCESS      read-create
    STATUS          current
    DESCRIPTION     
            "Parameter Rule signaling indicator (ISUP/SCCP)."
    ::= { ptL4CvtrParameterRuleEntry 4 }

ptL4CvtrParameterRuleL4CvtrSS7VariantIndex OBJECT-TYPE
    SYNTAX          Integer32 (-2147483648..2147483647)
    MAX-ACCESS      not-accessible
    STATUS          current
    DESCRIPTION     
            "This is the index of the parent type for this object.
             This parent type is L4CvtrSS7Variant."
    ::= { ptL4CvtrParameterRuleEntry 242 }

ptL4CvtrParameterRuleParameterRulesIndex OBJECT-TYPE
    SYNTAX          Integer32 (-2147483648..2147483647)
    MAX-ACCESS      not-accessible
    STATUS          current
    DESCRIPTION     
            "This is the index of the parent type for this object.
             This parent type is ParameterRules."
    ::= { ptL4CvtrParameterRuleEntry 243 }

ptL4CvtrParameterRuleParentOID OBJECT-TYPE
    SYNTAX          OBJECT IDENTIFIER
    MAX-ACCESS      read-create
    STATUS          current
    DESCRIPTION     
            "The OID of the parent object for this instance"
    ::= { ptL4CvtrParameterRuleEntry 253 }

ptL4CvtrParameterRuleRowStatus OBJECT-TYPE
    SYNTAX          RowStatus
    MAX-ACCESS      read-create
    STATUS          current
    DESCRIPTION     
            "The row status for the L4CvtrParameterRule table"
    ::= { ptL4CvtrParameterRuleEntry 254 }

ptL4CvtrParameterRuleIndex OBJECT-TYPE
    SYNTAX          Integer32 (-2147483648..2147483647)
    MAX-ACCESS      not-accessible
    STATUS          current
    DESCRIPTION     
            "The row number for the L4CvtrParameterRule table"
    ::= { ptL4CvtrParameterRuleEntry 255 }

ptL4CvtrL4Converter OBJECT IDENTIFIER
    ::= { ptConnGroup 138 }

ptL4CvtrL4ConverterTable OBJECT-TYPE
    SYNTAX          SEQUENCE OF PtL4CvtrL4ConverterEntry
    MAX-ACCESS      not-accessible
    STATUS          current
    DESCRIPTION     
            "No description supplied in the proxy config file."
    ::= { ptL4CvtrL4Converter 1 }

ptL4CvtrL4ConverterEntry OBJECT-TYPE
    SYNTAX          PtL4CvtrL4ConverterEntry
    MAX-ACCESS      not-accessible
    STATUS          current
    DESCRIPTION     
            "A sequence of L4CvtrL4Converter attributes."
    INDEX           { ptConnGroupIndex, ptL4CvtrL4ConverterIndex }
    ::= { ptL4CvtrL4ConverterTable 1 }

PtL4CvtrL4ConverterEntry ::=
    SEQUENCE {
        ptL4CvtrL4ConverterParentOID    OBJECT IDENTIFIER,
        ptL4CvtrL4ConverterRowStatus    RowStatus,
        ptL4CvtrL4ConverterIndex        Integer32
    }

ptL4CvtrL4ConverterParentOID OBJECT-TYPE
    SYNTAX          OBJECT IDENTIFIER
    MAX-ACCESS      read-create
    STATUS          current
    DESCRIPTION     
            "The OID of the parent object for this instance"
    ::= { ptL4CvtrL4ConverterEntry 253 }

ptL4CvtrL4ConverterRowStatus OBJECT-TYPE
    SYNTAX          RowStatus
    MAX-ACCESS      read-create
    STATUS          current
    DESCRIPTION     
            "The row status for the L4CvtrL4Converter table"
    ::= { ptL4CvtrL4ConverterEntry 254 }

ptL4CvtrL4ConverterIndex OBJECT-TYPE
    SYNTAX          Integer32 (-2147483648..2147483647)
    MAX-ACCESS      not-accessible
    STATUS          current
    DESCRIPTION     
            "The row number for the L4CvtrL4Converter table"
    ::= { ptL4CvtrL4ConverterEntry 255 }

ptSGSignalingGateway OBJECT IDENTIFIER
    ::= { ptConnGroup 149 }

ptSGSignalingGatewayTable OBJECT-TYPE
    SYNTAX          SEQUENCE OF PtSGSignalingGatewayEntry
    MAX-ACCESS      not-accessible
    STATUS          current
    DESCRIPTION     
            "No description supplied in the proxy config file."
    ::= { ptSGSignalingGateway 1 }

ptSGSignalingGatewayEntry OBJECT-TYPE
    SYNTAX          PtSGSignalingGatewayEntry
    MAX-ACCESS      not-accessible
    STATUS          current
    DESCRIPTION     
            "A sequence of SGSignalingGateway attributes."
    INDEX           { ptConnGroupIndex, ptSGSignalingGatewayIndex }
    ::= { ptSGSignalingGatewayTable 1 }

PtSGSignalingGatewayEntry ::=
    SEQUENCE {
        ptSGSignalingGatewayParentOID   OBJECT IDENTIFIER,
        ptSGSignalingGatewayRowStatus   RowStatus,
        ptSGSignalingGatewayIndex       Integer32
    }

ptSGSignalingGatewayParentOID OBJECT-TYPE
    SYNTAX          OBJECT IDENTIFIER
    MAX-ACCESS      read-create
    STATUS          current
    DESCRIPTION     
            "The OID of the parent object for this instance"
    ::= { ptSGSignalingGatewayEntry 253 }

ptSGSignalingGatewayRowStatus OBJECT-TYPE
    SYNTAX          RowStatus
    MAX-ACCESS      read-create
    STATUS          current
    DESCRIPTION     
            "The row status for the SGSignalingGateway table"
    ::= { ptSGSignalingGatewayEntry 254 }

ptSGSignalingGatewayIndex OBJECT-TYPE
    SYNTAX          Integer32 (-2147483648..2147483647)
    MAX-ACCESS      not-accessible
    STATUS          current
    DESCRIPTION     
            "The row number for the SGSignalingGateway table"
    ::= { ptSGSignalingGatewayEntry 255 }

ptSGSGConfiguration OBJECT IDENTIFIER
    ::= { ptConnGroup 152 }

ptSGSGConfigurationTable OBJECT-TYPE
    SYNTAX          SEQUENCE OF PtSGSGConfigurationEntry
    MAX-ACCESS      not-accessible
    STATUS          current
    DESCRIPTION     
            "No description supplied in the proxy config file."
    ::= { ptSGSGConfiguration 1 }

ptSGSGConfigurationEntry OBJECT-TYPE
    SYNTAX          PtSGSGConfigurationEntry
    MAX-ACCESS      not-accessible
    STATUS          current
    DESCRIPTION     
            "A sequence of SGSGConfiguration attributes."
    INDEX           { ptConnGroupIndex, ptSGSGConfigurationIndex }
    ::= { ptSGSGConfigurationTable 1 }

PtSGSGConfigurationEntry ::=
    SEQUENCE {
        ptSGSGConfigurationSGDebugLevel INTEGER,
        ptSGSGConfigurationSCTPDebugLevel Integer32,
        ptSGSGConfigurationLDLDebugLevel Integer32,
        ptSGSGConfigurationNPeerDebugLevel  Integer32,
        ptSGSGConfigurationActiveSlot   DisplayString,
        ptSGSGConfigurationDBError      INTEGER,
        ptSGSGConfigurationDBMgmt       INTEGER,
        ptSGSGConfigurationDBFileMgmt   INTEGER,
        ptSGSGConfigurationASMasterDebug INTEGER,
        ptSGSGConfigurationMSADebug     INTEGER,
        ptSGSGConfigurationActions      INTEGER,
        ptSGSGConfigurationParentOID    OBJECT IDENTIFIER,
        ptSGSGConfigurationRowStatus    RowStatus,
        ptSGSGConfigurationIndex        Integer32
    }

ptSGSGConfigurationSGDebugLevel OBJECT-TYPE
    SYNTAX          INTEGER { none(0), critical(1), major(2), minor(3), 
                        log(4), info(5) }
    MAX-ACCESS      read-create
    STATUS          current
    DESCRIPTION     
            "Signaling Gateway logging level"
    ::= { ptSGSGConfigurationEntry 1 }

ptSGSGConfigurationSCTPDebugLevel OBJECT-TYPE
    SYNTAX          Integer32 (-2147483648..2147483647)
    MAX-ACCESS      read-create
    STATUS          current
    DESCRIPTION     
            "SCTP logging level"
    ::= { ptSGSGConfigurationEntry 2 }

ptSGSGConfigurationLDLDebugLevel OBJECT-TYPE
    SYNTAX          Integer32 (-2147483648..2147483647)
    MAX-ACCESS      read-create
    STATUS          current
    DESCRIPTION     
            "LDL logging level"
    ::= { ptSGSGConfigurationEntry 3 }

ptSGSGConfigurationNPeerDebugLevel OBJECT-TYPE
    SYNTAX          Integer32 (-2147483648..2147483647)
    MAX-ACCESS      read-create
    STATUS          current
    DESCRIPTION     
            "NPeer logging level"
    ::= { ptSGSGConfigurationEntry 4 }

ptSGSGConfigurationActiveSlot OBJECT-TYPE
    SYNTAX          DisplayString (SIZE(0..255))
    MAX-ACCESS      read-only
    STATUS          current
    DESCRIPTION     
            "Slot running the SG"
    ::= { ptSGSGConfigurationEntry 5 }

ptSGSGConfigurationDBError OBJECT-TYPE
    SYNTAX          INTEGER { disabled(0), enabled(1) }
    MAX-ACCESS      read-create
    STATUS          current
    DESCRIPTION     
            "Binary DB Error Logging"
    ::= { ptSGSGConfigurationEntry 6 }

ptSGSGConfigurationDBMgmt OBJECT-TYPE
    SYNTAX          INTEGER { disabled(0), enabled(1) }
    MAX-ACCESS      read-create
    STATUS          current
    DESCRIPTION     
            "Binary DB Management"
    ::= { ptSGSGConfigurationEntry 7 }

ptSGSGConfigurationDBFileMgmt OBJECT-TYPE
    SYNTAX          INTEGER { disabled(0), enabled(1) }
    MAX-ACCESS      read-create
    STATUS          current
    DESCRIPTION     
            "Binary DB File Management"
    ::= { ptSGSGConfigurationEntry 8 }

ptSGSGConfigurationASMasterDebug OBJECT-TYPE
    SYNTAX          INTEGER { disabled(0), enabled(1) }
    MAX-ACCESS      read-create
    STATUS          current
    DESCRIPTION     
            "AS Master Debug Management"
    ::= { ptSGSGConfigurationEntry 9 }

ptSGSGConfigurationMSADebug OBJECT-TYPE
    SYNTAX          INTEGER { disabled(0), enabled(1) }
    MAX-ACCESS      read-create
    STATUS          current
    DESCRIPTION     
            "MSA Debug Management"
    ::= { ptSGSGConfigurationEntry 10 }

ptSGSGConfigurationActions OBJECT-TYPE
    SYNTAX          INTEGER { restoreDebugDefaults(1) }
    MAX-ACCESS      read-create
    STATUS          current
    DESCRIPTION     
            "The OID of all possible actions for this instance"
    ::= { ptSGSGConfigurationEntry 252 }

ptSGSGConfigurationParentOID OBJECT-TYPE
    SYNTAX          OBJECT IDENTIFIER
    MAX-ACCESS      read-create
    STATUS          current
    DESCRIPTION     
            "The OID of the parent object for this instance"
    ::= { ptSGSGConfigurationEntry 253 }

ptSGSGConfigurationRowStatus OBJECT-TYPE
    SYNTAX          RowStatus
    MAX-ACCESS      read-create
    STATUS          current
    DESCRIPTION     
            "The row status for the SGSGConfiguration table"
    ::= { ptSGSGConfigurationEntry 254 }

ptSGSGConfigurationIndex OBJECT-TYPE
    SYNTAX          Integer32 (-2147483648..2147483647)
    MAX-ACCESS      not-accessible
    STATUS          current
    DESCRIPTION     
            "The row number for the SGSGConfiguration table"
    ::= { ptSGSGConfigurationEntry 255 }

ptSGM3UA OBJECT IDENTIFIER
    ::= { ptConnGroup 175 }

ptSGM3UATable OBJECT-TYPE
    SYNTAX          SEQUENCE OF PtSGM3UAEntry
    MAX-ACCESS      not-accessible
    STATUS          current
    DESCRIPTION     
            "No description supplied in the proxy config file."
    ::= { ptSGM3UA 1 }

ptSGM3UAEntry OBJECT-TYPE
    SYNTAX          PtSGM3UAEntry
    MAX-ACCESS      not-accessible
    STATUS          current
    DESCRIPTION     
            "A sequence of SGM3UA attributes."
    INDEX           { ptConnGroupIndex, ptSGM3UAIndex }
    ::= { ptSGM3UATable 1 }

PtSGM3UAEntry ::=
    SEQUENCE {
        ptSGM3UAPendingTimer            INTEGER,
        ptSGM3UAMonitoring              INTEGER,
        ptSGM3UAAssociationCapacity     Integer32,
        ptSGM3UAHighUsageOnset          INTEGER,
        ptSGM3UAHighUsageAbatement      INTEGER,
        ptSGM3UAUsageIntervalSeconds    Integer32,
        ptSGM3UAIMFSupport              INTEGER,
        ptSGM3UASCTPProtocolIDValidation INTEGER,
        ptSGM3UAASMasterTimer           Integer32,
        ptSGM3UAASMasterPendingTimer    INTEGER,
        ptSGM3UAActions                 INTEGER,
        ptSGM3UAParentOID               OBJECT IDENTIFIER,
        ptSGM3UARowStatus               RowStatus,
        ptSGM3UAIndex                   Integer32
    }

ptSGM3UAPendingTimer OBJECT-TYPE
    SYNTAX          INTEGER { disabled(0) }
    MAX-ACCESS      read-create
    STATUS          current
    DESCRIPTION     
            "Duration of PENDING state in msecs for an M3UA AS. Pending timer is started when an AS transitions out of ACTIVE state. \nIf an ASP sends an ASPAC before the timer expires, the AS will immediately transition back to the ACTIVE status. Otherwise, when the timer expires the AS will either transition to INACTIVE or DOWN state. This timer is used by all M3UA AS of type other than AS Master. \nMessages will be queued while in PENDING state. \nValid range of this timer is 1 to 2000. \nTo disable the timer, set to 0. \nDefault value is 2000 msecs."
    ::= { ptSGM3UAEntry 2 }

ptSGM3UAMonitoring OBJECT-TYPE
    SYNTAX          INTEGER { disabled(0), enabled(1) }
    MAX-ACCESS      read-only
    STATUS          current
    DESCRIPTION     
            "Monitoring feature (ENABLED/DISABLED)."
    ::= { ptSGM3UAEntry 3 }

ptSGM3UAAssociationCapacity OBJECT-TYPE
    SYNTAX          Integer32 (0..2147483647)
    MAX-ACCESS      read-create
    STATUS          current
    DESCRIPTION     
            "Bandwidth of SCTP association. Number of bytes per second support by association."
    ::= { ptSGM3UAEntry 4 }

ptSGM3UAHighUsageOnset OBJECT-TYPE
    SYNTAX          INTEGER { default(-1) }
    MAX-ACCESS      read-create
    STATUS          current
    DESCRIPTION     
            "Traffic level at which high usage alarms are triggered. (% of association capacity).\n This setting is used for both the transmit and receive high usage alarms for SCTP associations used by M3UA ASPs.\n The alarm is automatically cleared when traffic levels fall below the High Usage Abatement setting."
    ::= { ptSGM3UAEntry 5 }

ptSGM3UAHighUsageAbatement OBJECT-TYPE
    SYNTAX          INTEGER { default(-1) }
    MAX-ACCESS      read-create
    STATUS          current
    DESCRIPTION     
            "Traffic level at which high usage alarms are cleared. (% of association capacity).\n This setting is used for both the transmit and receive high usage alarms for SCTP associations used by M3UA ASPs."
    ::= { ptSGM3UAEntry 6 }

ptSGM3UAUsageIntervalSeconds OBJECT-TYPE
    SYNTAX          Integer32 (-2147483648..2147483647)
    MAX-ACCESS      read-only
    STATUS          current
    DESCRIPTION     
            "Interval in seconds used to calculate average traffic load."
    ::= { ptSGM3UAEntry 8 }

ptSGM3UAIMFSupport OBJECT-TYPE
    SYNTAX          INTEGER { disabled(0), enabled(1) }
    MAX-ACCESS      read-create
    STATUS          current
    DESCRIPTION     
            "Integrated Monitoring Feed feature support for M3UA. \nIMF must be licensed to enable this attribute."
    ::= { ptSGM3UAEntry 9 }

ptSGM3UASCTPProtocolIDValidation OBJECT-TYPE
    SYNTAX          INTEGER { disabled(0), enabled(1) }
    MAX-ACCESS      read-create
    STATUS          current
    DESCRIPTION     
            "Validation of protocol ID of received data. \nWhen enabled, the SG will discard all M3UA messages that do not have an SCTP Protocol ID of either 0 or 3 as described in RFC 4666. \nWhen disabled, the SG will not inspect the SCTP protocol ID and accept all M3UA messages."
    ::= { ptSGM3UAEntry 10 }

ptSGM3UAASMasterTimer OBJECT-TYPE
    SYNTAX          Integer32 (10..300)
    MAX-ACCESS      read-create
    STATUS          current
    DESCRIPTION     
            "Amount of time (in seconds) all AS of type AS Master must be in ACTIVE state before the PT_C20 Application ID is registered with MTP3. This feature ensures a more stable system start-up procedure for SP2000 deployments as MTP3 links, based on link type, will only initiate alignment or clear local processor outage on the PT_C20 Application ID registration. Following AS Master recovery due to maintenance or connection loss beyond the AS Master Pending Timer, the MTP3 links will remain unavailable (out of service or processor outage) until this timer expires and PT_C20 registration is triggered. Valid values: 10 to 300 seconds. Default value: 60 seconds."
    ::= { ptSGM3UAEntry 11 }

ptSGM3UAASMasterPendingTimer OBJECT-TYPE
    SYNTAX          INTEGER { disabled(0) }
    MAX-ACCESS      read-create
    STATUS          current
    DESCRIPTION     
            "Duration of PENDING state in msecs for an M3UA AS of type AS Master. Pending timer is started when an AS of transitions out of ACTIVE state. \nIf an ASP sends an ASPAC before the timer expires, the AS will immediately transition back to the ACTIVE status. Otherwise, when the timer expires the AS will either transition to INACTIVE or DOWN state. \nMessages bound for an AS, of type AS Master, during PENDING state will not be queued. \nTo disable the timer, set to 0. \nValid values: 0 to 120000 milliseconds. \nDefault value: 30000 msecs."
    ::= { ptSGM3UAEntry 12 }

ptSGM3UAActions OBJECT-TYPE
    SYNTAX          INTEGER { startMonitoring(1), stopMonitoring(2) }
    MAX-ACCESS      read-create
    STATUS          current
    DESCRIPTION     
            "The OID of all possible actions for this instance"
    ::= { ptSGM3UAEntry 252 }

ptSGM3UAParentOID OBJECT-TYPE
    SYNTAX          OBJECT IDENTIFIER
    MAX-ACCESS      read-create
    STATUS          current
    DESCRIPTION     
            "The OID of the parent object for this instance"
    ::= { ptSGM3UAEntry 253 }

ptSGM3UARowStatus OBJECT-TYPE
    SYNTAX          RowStatus
    MAX-ACCESS      read-create
    STATUS          current
    DESCRIPTION     
            "The row status for the SGM3UA table"
    ::= { ptSGM3UAEntry 254 }

ptSGM3UAIndex OBJECT-TYPE
    SYNTAX          Integer32 (-2147483648..2147483647)
    MAX-ACCESS      not-accessible
    STATUS          current
    DESCRIPTION     
            "The row number for the SGM3UA table"
    ::= { ptSGM3UAEntry 255 }

ptSGM3UAAppServers OBJECT IDENTIFIER
    ::= { ptSGM3UA 176 }

ptSGM3UAAppServersTable OBJECT-TYPE
    SYNTAX          SEQUENCE OF PtSGM3UAAppServersEntry
    MAX-ACCESS      not-accessible
    STATUS          current
    DESCRIPTION     
            "No description supplied in the proxy config file."
    ::= { ptSGM3UAAppServers 1 }

ptSGM3UAAppServersEntry OBJECT-TYPE
    SYNTAX          PtSGM3UAAppServersEntry
    MAX-ACCESS      not-accessible
    STATUS          current
    DESCRIPTION     
            "A sequence of SGM3UAAppServers attributes."
    INDEX           { ptConnGroupIndex, ptSGM3UAAppServersM3UAIndex, 
                      ptSGM3UAAppServersIndex }
    ::= { ptSGM3UAAppServersTable 1 }

PtSGM3UAAppServersEntry ::=
    SEQUENCE {
        ptSGM3UAAppServersM3UAIndex     Integer32,
        ptSGM3UAAppServersParentOID     OBJECT IDENTIFIER,
        ptSGM3UAAppServersRowStatus     RowStatus,
        ptSGM3UAAppServersIndex         Integer32
    }

ptSGM3UAAppServersM3UAIndex OBJECT-TYPE
    SYNTAX          Integer32 (-2147483648..2147483647)
    MAX-ACCESS      not-accessible
    STATUS          current
    DESCRIPTION     
            "This is the index of the parent type for this object.
             This parent type is M3UA."
    ::= { ptSGM3UAAppServersEntry 242 }

ptSGM3UAAppServersParentOID OBJECT-TYPE
    SYNTAX          OBJECT IDENTIFIER
    MAX-ACCESS      read-create
    STATUS          current
    DESCRIPTION     
            "The OID of the parent object for this instance"
    ::= { ptSGM3UAAppServersEntry 253 }

ptSGM3UAAppServersRowStatus OBJECT-TYPE
    SYNTAX          RowStatus
    MAX-ACCESS      read-create
    STATUS          current
    DESCRIPTION     
            "The row status for the SGM3UAAppServers table"
    ::= { ptSGM3UAAppServersEntry 254 }

ptSGM3UAAppServersIndex OBJECT-TYPE
    SYNTAX          Integer32 (-2147483648..2147483647)
    MAX-ACCESS      not-accessible
    STATUS          current
    DESCRIPTION     
            "The row number for the SGM3UAAppServers table"
    ::= { ptSGM3UAAppServersEntry 255 }

ptSGM3UAAppServer OBJECT IDENTIFIER
    ::= { ptSGM3UAAppServers 177 }

ptSGM3UAAppServerTable OBJECT-TYPE
    SYNTAX          SEQUENCE OF PtSGM3UAAppServerEntry
    MAX-ACCESS      not-accessible
    STATUS          current
    DESCRIPTION     
            "No description supplied in the proxy config file."
    ::= { ptSGM3UAAppServer 1 }

ptSGM3UAAppServerEntry OBJECT-TYPE
    SYNTAX          PtSGM3UAAppServerEntry
    MAX-ACCESS      not-accessible
    STATUS          current
    DESCRIPTION     
            "A sequence of SGM3UAAppServer attributes."
    INDEX           { ptConnGroupIndex, ptSGM3UAAppServerM3UAIndex, 
                      ptSGM3UAAppServerM3UAAppServersIndex, 
                      ptSGM3UAAppServerIndex }
    ::= { ptSGM3UAAppServerTable 1 }

PtSGM3UAAppServerEntry ::=
    SEQUENCE {
        ptSGM3UAAppServerStatus         INTEGER,
        ptSGM3UAAppServerRoutingContext Integer32,
        ptSGM3UAAppServerDPC            Integer32,
        ptSGM3UAAppServerSI             Integer32,
        ptSGM3UAAppServerNetworkAppearance  Integer32,
        ptSGM3UAAppServerTrafficMode    INTEGER,
        ptSGM3UAAppServerApplicationID  DisplayString,
        ptSGM3UAAppServerASPType        INTEGER,
        ptSGM3UAAppServerM3UAIndex      Integer32,
        ptSGM3UAAppServerM3UAAppServersIndex    Integer32,
        ptSGM3UAAppServerActions        INTEGER,
        ptSGM3UAAppServerParentOID      OBJECT IDENTIFIER,
        ptSGM3UAAppServerRowStatus      RowStatus,
        ptSGM3UAAppServerIndex          Integer32
    }

ptSGM3UAAppServerStatus OBJECT-TYPE
    SYNTAX          INTEGER { active(0), inactive(1), pendingReg(2), 
                        down(3), offLine(4), pending(5) }
    MAX-ACCESS      read-only
    STATUS          current
    DESCRIPTION     
            "M3UA AS Status."
    ::= { ptSGM3UAAppServerEntry 1 }

ptSGM3UAAppServerRoutingContext OBJECT-TYPE
    SYNTAX          Integer32 (1..2147483647)
    MAX-ACCESS      read-only
    STATUS          current
    DESCRIPTION     
            "M3UA AS Routing context."
    ::= { ptSGM3UAAppServerEntry 2 }

ptSGM3UAAppServerDPC OBJECT-TYPE
    SYNTAX          Integer32 (-2147483648..2147483647)
    MAX-ACCESS      read-only
    STATUS          current
    DESCRIPTION     
            "Point Codes are set to UNSET when routing on Application ID is configured"
    ::= { ptSGM3UAAppServerEntry 3 }

ptSGM3UAAppServerSI OBJECT-TYPE
    SYNTAX          Integer32 (-2147483648..2147483647)
    MAX-ACCESS      read-only
    STATUS          current
    DESCRIPTION     
            "SIs are set to 0 when routing on Application ID is configured"
    ::= { ptSGM3UAAppServerEntry 4 }

ptSGM3UAAppServerNetworkAppearance OBJECT-TYPE
    SYNTAX          Integer32 (-2147483648..2147483647)
    MAX-ACCESS      read-only
    STATUS          current
    DESCRIPTION     
            "M3UA AS Network appearance."
    ::= { ptSGM3UAAppServerEntry 5 }

ptSGM3UAAppServerTrafficMode OBJECT-TYPE
    SYNTAX          INTEGER { override(0), loadshare(1), broadcast(2) }
    MAX-ACCESS      read-only
    STATUS          current
    DESCRIPTION     
            "M3UA Application Server Traffic Mode. Traffic modes, override, loadshare and broadcast are supported."
    ::= { ptSGM3UAAppServerEntry 6 }

ptSGM3UAAppServerApplicationID OBJECT-TYPE
    SYNTAX          DisplayString (SIZE(0..255))
    MAX-ACCESS      read-only
    STATUS          current
    DESCRIPTION     
            "M3UA AS Application ID (optional)."
    ::= { ptSGM3UAAppServerEntry 9 }

ptSGM3UAAppServerASPType OBJECT-TYPE
    SYNTAX          INTEGER { singleAssociation(0), multiAssociation(1), 
                        asMaster(2) }
    MAX-ACCESS      read-create
    STATUS          current
    DESCRIPTION     
            "ASP Type can be set to SINGLE/MULTI ASSOCIATION as long the AS is not online"
    ::= { ptSGM3UAAppServerEntry 10 }

ptSGM3UAAppServerM3UAIndex OBJECT-TYPE
    SYNTAX          Integer32 (-2147483648..2147483647)
    MAX-ACCESS      not-accessible
    STATUS          current
    DESCRIPTION     
            "This is the index of the parent type for this object.
             This parent type is M3UA."
    ::= { ptSGM3UAAppServerEntry 242 }

ptSGM3UAAppServerM3UAAppServersIndex OBJECT-TYPE
    SYNTAX          Integer32 (-2147483648..2147483647)
    MAX-ACCESS      not-accessible
    STATUS          current
    DESCRIPTION     
            "This is the index of the parent type for this object.
             This parent type is M3UAAppServers."
    ::= { ptSGM3UAAppServerEntry 243 }

ptSGM3UAAppServerActions OBJECT-TYPE
    SYNTAX          INTEGER { goOnline(1) }
    MAX-ACCESS      read-create
    STATUS          current
    DESCRIPTION     
            "The OID of all possible actions for this instance"
    ::= { ptSGM3UAAppServerEntry 252 }

ptSGM3UAAppServerParentOID OBJECT-TYPE
    SYNTAX          OBJECT IDENTIFIER
    MAX-ACCESS      read-create
    STATUS          current
    DESCRIPTION     
            "The OID of the parent object for this instance"
    ::= { ptSGM3UAAppServerEntry 253 }

ptSGM3UAAppServerRowStatus OBJECT-TYPE
    SYNTAX          RowStatus
    MAX-ACCESS      read-create
    STATUS          current
    DESCRIPTION     
            "The row status for the SGM3UAAppServer table"
    ::= { ptSGM3UAAppServerEntry 254 }

ptSGM3UAAppServerIndex OBJECT-TYPE
    SYNTAX          Integer32 (-2147483648..2147483647)
    MAX-ACCESS      not-accessible
    STATUS          current
    DESCRIPTION     
            "The row number for the SGM3UAAppServer table"
    ::= { ptSGM3UAAppServerEntry 255 }

ptSGM3UAOPCCICRange OBJECT IDENTIFIER
    ::= { ptSGM3UAAppServer 178 }

ptSGM3UAOPCCICRangeTable OBJECT-TYPE
    SYNTAX          SEQUENCE OF PtSGM3UAOPCCICRangeEntry
    MAX-ACCESS      not-accessible
    STATUS          current
    DESCRIPTION     
            "No description supplied in the proxy config file."
    ::= { ptSGM3UAOPCCICRange 1 }

ptSGM3UAOPCCICRangeEntry OBJECT-TYPE
    SYNTAX          PtSGM3UAOPCCICRangeEntry
    MAX-ACCESS      not-accessible
    STATUS          current
    DESCRIPTION     
            "A sequence of SGM3UAOPCCICRange attributes."
    INDEX           { ptConnGroupIndex, ptSGM3UAOPCCICRangeM3UAIndex, 
                      ptSGM3UAOPCCICRangeM3UAAppServersIndex, 
                      ptSGM3UAOPCCICRangeM3UAAppServerIndex, 
                      ptSGM3UAOPCCICRangeIndex }
    ::= { ptSGM3UAOPCCICRangeTable 1 }

PtSGM3UAOPCCICRangeEntry ::=
    SEQUENCE {
        ptSGM3UAOPCCICRangeCICMinimum   INTEGER,
        ptSGM3UAOPCCICRangeCICMaximum   INTEGER,
        ptSGM3UAOPCCICRangeOPC          Integer32,
        ptSGM3UAOPCCICRangeM3UAIndex    Integer32,
        ptSGM3UAOPCCICRangeM3UAAppServersIndex      Integer32,
        ptSGM3UAOPCCICRangeM3UAAppServerIndex     Integer32,
        ptSGM3UAOPCCICRangeParentOID    OBJECT IDENTIFIER,
        ptSGM3UAOPCCICRangeRowStatus    RowStatus,
        ptSGM3UAOPCCICRangeIndex        Integer32
    }

ptSGM3UAOPCCICRangeCICMinimum OBJECT-TYPE
    SYNTAX          INTEGER { undefined(-1) }
    MAX-ACCESS      read-only
    STATUS          current
    DESCRIPTION     
            "The Minimum CIC value is used in conjunction with the Maximum CIC value in order to augment the M3UA Routing Key to which the CIC range belongs. The range allows the ASP to restrict the traffic that it will receive to only that traffic for those circuits included in the configured CIC ranges "
    ::= { ptSGM3UAOPCCICRangeEntry 1 }

ptSGM3UAOPCCICRangeCICMaximum OBJECT-TYPE
    SYNTAX          INTEGER { undefined(-1) }
    MAX-ACCESS      read-only
    STATUS          current
    DESCRIPTION     
            "The Maximum CIC value is used in conjunction with the Minimum CIC value in order to augment the M3UA Routing Key to which the CIC range belongs. The range allows the ASP to restrict the traffic that it will receive to only that for those circuits included in the configured CIC ranges "
    ::= { ptSGM3UAOPCCICRangeEntry 2 }

ptSGM3UAOPCCICRangeOPC OBJECT-TYPE
    SYNTAX          Integer32 (-2147483648..2147483647)
    MAX-ACCESS      read-only
    STATUS          current
    DESCRIPTION     
            "The OPC is an optional parameter which is used to augment M3UA Routing Keys. The addition of an OPC or a list of OPCs enables a Routing Key to be created where by an ASP can restrict the traffic it receives to only come from those originators listed. Please Note that if an OPC is configured then the ASP will not receive traffic from any other originating point codes"
    ::= { ptSGM3UAOPCCICRangeEntry 3 }

ptSGM3UAOPCCICRangeM3UAIndex OBJECT-TYPE
    SYNTAX          Integer32 (-2147483648..2147483647)
    MAX-ACCESS      not-accessible
    STATUS          current
    DESCRIPTION     
            "This is the index of the parent type for this object.
             This parent type is M3UA."
    ::= { ptSGM3UAOPCCICRangeEntry 242 }

ptSGM3UAOPCCICRangeM3UAAppServersIndex OBJECT-TYPE
    SYNTAX          Integer32 (-2147483648..2147483647)
    MAX-ACCESS      not-accessible
    STATUS          current
    DESCRIPTION     
            "This is the index of the parent type for this object.
             This parent type is M3UAAppServers."
    ::= { ptSGM3UAOPCCICRangeEntry 243 }

ptSGM3UAOPCCICRangeM3UAAppServerIndex OBJECT-TYPE
    SYNTAX          Integer32 (-2147483648..2147483647)
    MAX-ACCESS      not-accessible
    STATUS          current
    DESCRIPTION     
            "This is the index of the parent type for this object.
             This parent type is M3UAAppServer."
    ::= { ptSGM3UAOPCCICRangeEntry 244 }

ptSGM3UAOPCCICRangeParentOID OBJECT-TYPE
    SYNTAX          OBJECT IDENTIFIER
    MAX-ACCESS      read-create
    STATUS          current
    DESCRIPTION     
            "The OID of the parent object for this instance"
    ::= { ptSGM3UAOPCCICRangeEntry 253 }

ptSGM3UAOPCCICRangeRowStatus OBJECT-TYPE
    SYNTAX          RowStatus
    MAX-ACCESS      read-create
    STATUS          current
    DESCRIPTION     
            "The row status for the SGM3UAOPCCICRange table"
    ::= { ptSGM3UAOPCCICRangeEntry 254 }

ptSGM3UAOPCCICRangeIndex OBJECT-TYPE
    SYNTAX          Integer32 (-2147483648..2147483647)
    MAX-ACCESS      not-accessible
    STATUS          current
    DESCRIPTION     
            "The row number for the SGM3UAOPCCICRange table"
    ::= { ptSGM3UAOPCCICRangeEntry 255 }

ptSGM3UAASPStatus OBJECT IDENTIFIER
    ::= { ptSGM3UAAppServer 180 }

ptSGM3UAASPStatusTable OBJECT-TYPE
    SYNTAX          SEQUENCE OF PtSGM3UAASPStatusEntry
    MAX-ACCESS      not-accessible
    STATUS          current
    DESCRIPTION     
            "No description supplied in the proxy config file."
    ::= { ptSGM3UAASPStatus 1 }

ptSGM3UAASPStatusEntry OBJECT-TYPE
    SYNTAX          PtSGM3UAASPStatusEntry
    MAX-ACCESS      not-accessible
    STATUS          current
    DESCRIPTION     
            "A sequence of SGM3UAASPStatus attributes."
    INDEX           { ptConnGroupIndex, ptSGM3UAASPStatusM3UAIndex, 
                      ptSGM3UAASPStatusM3UAAppServersIndex, 
                      ptSGM3UAASPStatusM3UAAppServerIndex, 
                      ptSGM3UAASPStatusIndex }
    ::= { ptSGM3UAASPStatusTable 1 }

PtSGM3UAASPStatusEntry ::=
    SEQUENCE {
        ptSGM3UAASPStatusASPID          Integer32,
        ptSGM3UAASPStatusState          INTEGER,
        ptSGM3UAASPStatusSlot           Integer32,
        ptSGM3UAASPStatusServerID       Integer32,
        ptSGM3UAASPStatusName           DisplayString,
        ptSGM3UAASPStatusAssociationID  Integer32,
        ptSGM3UAASPStatusM3UAIndex      Integer32,
        ptSGM3UAASPStatusM3UAAppServersIndex    Integer32,
        ptSGM3UAASPStatusM3UAAppServerIndex   Integer32,
        ptSGM3UAASPStatusParentOID      OBJECT IDENTIFIER,
        ptSGM3UAASPStatusRowStatus      RowStatus,
        ptSGM3UAASPStatusIndex          Integer32
    }

ptSGM3UAASPStatusASPID OBJECT-TYPE
    SYNTAX          Integer32 (-2147483648..2147483647)
    MAX-ACCESS      read-only
    STATUS          current
    DESCRIPTION     
            "M3UA AS ASP unique identifier."
    ::= { ptSGM3UAASPStatusEntry 1 }

ptSGM3UAASPStatusState OBJECT-TYPE
    SYNTAX          INTEGER { up(0), active(1), inactive(2), down(3) }
    MAX-ACCESS      read-only
    STATUS          current
    DESCRIPTION     
            "M3UA AS ASP status."
    ::= { ptSGM3UAASPStatusEntry 2 }

ptSGM3UAASPStatusSlot OBJECT-TYPE
    SYNTAX          Integer32 (-2147483648..2147483647)
    MAX-ACCESS      read-only
    STATUS          current
    DESCRIPTION     
            "M3UA AS ASP corresponding slot."
    ::= { ptSGM3UAASPStatusEntry 3 }

ptSGM3UAASPStatusServerID OBJECT-TYPE
    SYNTAX          Integer32 (-2147483648..2147483647)
    MAX-ACCESS      read-only
    STATUS          current
    DESCRIPTION     
            "M3UA AS ASP corresponding server ID."
    ::= { ptSGM3UAASPStatusEntry 4 }

ptSGM3UAASPStatusName OBJECT-TYPE
    SYNTAX          DisplayString (SIZE(0..255))
    MAX-ACCESS      read-only
    STATUS          current
    DESCRIPTION     
            "M3UA AS ASP corresponding name."
    ::= { ptSGM3UAASPStatusEntry 5 }

ptSGM3UAASPStatusAssociationID OBJECT-TYPE
    SYNTAX          Integer32 (-2147483648..2147483647)
    MAX-ACCESS      read-only
    STATUS          current
    DESCRIPTION     
            "M3UA AS ASP Association unique identifier."
    ::= { ptSGM3UAASPStatusEntry 6 }

ptSGM3UAASPStatusM3UAIndex OBJECT-TYPE
    SYNTAX          Integer32 (-2147483648..2147483647)
    MAX-ACCESS      not-accessible
    STATUS          current
    DESCRIPTION     
            "This is the index of the parent type for this object.
             This parent type is M3UA."
    ::= { ptSGM3UAASPStatusEntry 242 }

ptSGM3UAASPStatusM3UAAppServersIndex OBJECT-TYPE
    SYNTAX          Integer32 (-2147483648..2147483647)
    MAX-ACCESS      not-accessible
    STATUS          current
    DESCRIPTION     
            "This is the index of the parent type for this object.
             This parent type is M3UAAppServers."
    ::= { ptSGM3UAASPStatusEntry 243 }

ptSGM3UAASPStatusM3UAAppServerIndex OBJECT-TYPE
    SYNTAX          Integer32 (-2147483648..2147483647)
    MAX-ACCESS      not-accessible
    STATUS          current
    DESCRIPTION     
            "This is the index of the parent type for this object.
             This parent type is M3UAAppServer."
    ::= { ptSGM3UAASPStatusEntry 244 }

ptSGM3UAASPStatusParentOID OBJECT-TYPE
    SYNTAX          OBJECT IDENTIFIER
    MAX-ACCESS      read-create
    STATUS          current
    DESCRIPTION     
            "The OID of the parent object for this instance"
    ::= { ptSGM3UAASPStatusEntry 253 }

ptSGM3UAASPStatusRowStatus OBJECT-TYPE
    SYNTAX          RowStatus
    MAX-ACCESS      read-create
    STATUS          current
    DESCRIPTION     
            "The row status for the SGM3UAASPStatus table"
    ::= { ptSGM3UAASPStatusEntry 254 }

ptSGM3UAASPStatusIndex OBJECT-TYPE
    SYNTAX          Integer32 (-2147483648..2147483647)
    MAX-ACCESS      not-accessible
    STATUS          current
    DESCRIPTION     
            "The row number for the SGM3UAASPStatus table"
    ::= { ptSGM3UAASPStatusEntry 255 }

ptSGM3UAASPs OBJECT IDENTIFIER
    ::= { ptSGM3UA 181 }

ptSGM3UAASPsTable OBJECT-TYPE
    SYNTAX          SEQUENCE OF PtSGM3UAASPsEntry
    MAX-ACCESS      not-accessible
    STATUS          current
    DESCRIPTION     
            "No description supplied in the proxy config file."
    ::= { ptSGM3UAASPs 1 }

ptSGM3UAASPsEntry OBJECT-TYPE
    SYNTAX          PtSGM3UAASPsEntry
    MAX-ACCESS      not-accessible
    STATUS          current
    DESCRIPTION     
            "A sequence of SGM3UAASPs attributes."
    INDEX           { ptConnGroupIndex, ptSGM3UAASPsM3UAIndex, 
                      ptSGM3UAASPsIndex }
    ::= { ptSGM3UAASPsTable 1 }

PtSGM3UAASPsEntry ::=
    SEQUENCE {
        ptSGM3UAASPsM3UAIndex           Integer32,
        ptSGM3UAASPsParentOID           OBJECT IDENTIFIER,
        ptSGM3UAASPsRowStatus           RowStatus,
        ptSGM3UAASPsIndex               Integer32
    }

ptSGM3UAASPsM3UAIndex OBJECT-TYPE
    SYNTAX          Integer32 (-2147483648..2147483647)
    MAX-ACCESS      not-accessible
    STATUS          current
    DESCRIPTION     
            "This is the index of the parent type for this object.
             This parent type is M3UA."
    ::= { ptSGM3UAASPsEntry 242 }

ptSGM3UAASPsParentOID OBJECT-TYPE
    SYNTAX          OBJECT IDENTIFIER
    MAX-ACCESS      read-create
    STATUS          current
    DESCRIPTION     
            "The OID of the parent object for this instance"
    ::= { ptSGM3UAASPsEntry 253 }

ptSGM3UAASPsRowStatus OBJECT-TYPE
    SYNTAX          RowStatus
    MAX-ACCESS      read-create
    STATUS          current
    DESCRIPTION     
            "The row status for the SGM3UAASPs table"
    ::= { ptSGM3UAASPsEntry 254 }

ptSGM3UAASPsIndex OBJECT-TYPE
    SYNTAX          Integer32 (-2147483648..2147483647)
    MAX-ACCESS      not-accessible
    STATUS          current
    DESCRIPTION     
            "The row number for the SGM3UAASPs table"
    ::= { ptSGM3UAASPsEntry 255 }

ptSGM3UAASP OBJECT IDENTIFIER
    ::= { ptSGM3UAASPs 182 }

ptSGM3UAASPTable OBJECT-TYPE
    SYNTAX          SEQUENCE OF PtSGM3UAASPEntry
    MAX-ACCESS      not-accessible
    STATUS          current
    DESCRIPTION     
            "No description supplied in the proxy config file."
    ::= { ptSGM3UAASP 1 }

ptSGM3UAASPEntry OBJECT-TYPE
    SYNTAX          PtSGM3UAASPEntry
    MAX-ACCESS      not-accessible
    STATUS          current
    DESCRIPTION     
            "A sequence of SGM3UAASP attributes."
    INDEX           { ptConnGroupIndex, ptSGM3UAASPM3UAIndex, 
                      ptSGM3UAASPM3UAASPsIndex, ptSGM3UAASPIndex }
    ::= { ptSGM3UAASPTable 1 }

PtSGM3UAASPEntry ::=
    SEQUENCE {
        ptSGM3UAASPIPAddress1           DisplayString,
        ptSGM3UAASPIPAddress2           DisplayString,
        ptSGM3UAASPAssocID              Integer32,
        ptSGM3UAASPPort                 Integer32,
        ptSGM3UAASPID                   Integer32,
        ptSGM3UAASPState                INTEGER,
        ptSGM3UAASPSlot                 Integer32,
        ptSGM3UAASPServerID             Integer32,
        ptSGM3UAASPHeartbeat            INTEGER,
        ptSGM3UAASPHeartbeatInterval    Integer32,
        ptSGM3UAASPRTOInitial           Integer32,
        ptSGM3UAASPRTOMinimum           Integer32,
        ptSGM3UAASPRTOMaximum           Integer32,
        ptSGM3UAASPMaximumInitRetrans   Integer32,
        ptSGM3UAASPMaximumAssocRetrans  Integer32,
        ptSGM3UAASPMaximumPathRetrans   Integer32,
        ptSGM3UAASPBundling             INTEGER,
        ptSGM3UAASPBundlingTimeout      Integer32,
        ptSGM3UAASPDelayedAckTimeout    Integer32,
        ptSGM3UAASPChecksum             INTEGER,
        ptSGM3UAASPInStreams            Integer32,
        ptSGM3UAASPOutStreams           Integer32,
        ptSGM3UAASPUserASPID            DisplayString,
        ptSGM3UAASPName                 DisplayString,
        ptSGM3UAASPRxMSGCount           Integer32,
        ptSGM3UAASPTxMSGCount           Integer32,
        ptSGM3UAASPM3UAIndex            Integer32,
        ptSGM3UAASPM3UAASPsIndex        Integer32,
        ptSGM3UAASPActions              INTEGER,
        ptSGM3UAASPParentOID            OBJECT IDENTIFIER,
        ptSGM3UAASPRowStatus            RowStatus,
        ptSGM3UAASPIndex                Integer32
    }

ptSGM3UAASPIPAddress1 OBJECT-TYPE
    SYNTAX          DisplayString (SIZE(0..255))
    MAX-ACCESS      read-only
    STATUS          current
    DESCRIPTION     
            "M3UA ASP primary IP address."
    ::= { ptSGM3UAASPEntry 1 }

ptSGM3UAASPIPAddress2 OBJECT-TYPE
    SYNTAX          DisplayString (SIZE(0..255))
    MAX-ACCESS      read-only
    STATUS          current
    DESCRIPTION     
            "M3UA ASP secondary IP address."
    ::= { ptSGM3UAASPEntry 2 }

ptSGM3UAASPAssocID OBJECT-TYPE
    SYNTAX          Integer32 (-2147483648..2147483647)
    MAX-ACCESS      read-only
    STATUS          current
    DESCRIPTION     
            "M3UA ASP Association ID."
    ::= { ptSGM3UAASPEntry 3 }

ptSGM3UAASPPort OBJECT-TYPE
    SYNTAX          Integer32 (-2147483648..2147483647)
    MAX-ACCESS      read-only
    STATUS          current
    DESCRIPTION     
            "M3UA ASP port."
    ::= { ptSGM3UAASPEntry 5 }

ptSGM3UAASPID OBJECT-TYPE
    SYNTAX          Integer32 (-2147483648..2147483647)
    MAX-ACCESS      read-only
    STATUS          current
    DESCRIPTION     
            "M3UA ASP unique identifier."
    ::= { ptSGM3UAASPEntry 6 }

ptSGM3UAASPState OBJECT-TYPE
    SYNTAX          INTEGER { up(0), active(1), inactive(2), down(3) }
    MAX-ACCESS      read-only
    STATUS          current
    DESCRIPTION     
            "M3UA ASP status."
    ::= { ptSGM3UAASPEntry 7 }

ptSGM3UAASPSlot OBJECT-TYPE
    SYNTAX          Integer32 (-2147483648..2147483647)
    MAX-ACCESS      read-only
    STATUS          current
    DESCRIPTION     
            "A Peers Slot in the chassis."
    ::= { ptSGM3UAASPEntry 8 }

ptSGM3UAASPServerID OBJECT-TYPE
    SYNTAX          Integer32 (-2147483648..2147483647)
    MAX-ACCESS      read-only
    STATUS          current
    DESCRIPTION     
            "M3UA SCTP Server ID."
    ::= { ptSGM3UAASPEntry 9 }

ptSGM3UAASPHeartbeat OBJECT-TYPE
    SYNTAX          INTEGER { disabled(0), enabled(1) }
    MAX-ACCESS      read-create
    STATUS          current
    DESCRIPTION     
            "Enable or disable the Heartbeat feature."
    ::= { ptSGM3UAASPEntry 10 }

ptSGM3UAASPHeartbeatInterval OBJECT-TYPE
    SYNTAX          Integer32 (0..65355)
    MAX-ACCESS      read-create
    STATUS          current
    DESCRIPTION     
            "Heartbeat interval (ms)."
    ::= { ptSGM3UAASPEntry 11 }

ptSGM3UAASPRTOInitial OBJECT-TYPE
    SYNTAX          Integer32 (0..2147483647)
    MAX-ACCESS      read-create
    STATUS          current
    DESCRIPTION     
            "Initial Retransmission Timeout (ms)."
    ::= { ptSGM3UAASPEntry 12 }

ptSGM3UAASPRTOMinimum OBJECT-TYPE
    SYNTAX          Integer32 (0..2147483647)
    MAX-ACCESS      read-create
    STATUS          current
    DESCRIPTION     
            "Minimum Retransmission Timeout (ms)."
    ::= { ptSGM3UAASPEntry 13 }

ptSGM3UAASPRTOMaximum OBJECT-TYPE
    SYNTAX          Integer32 (0..2147483647)
    MAX-ACCESS      read-create
    STATUS          current
    DESCRIPTION     
            "Maximum Retransmission Timeout (ms)."
    ::= { ptSGM3UAASPEntry 14 }

ptSGM3UAASPMaximumInitRetrans OBJECT-TYPE
    SYNTAX          Integer32 (0..2147483647)
    MAX-ACCESS      read-create
    STATUS          current
    DESCRIPTION     
            "Maximum initial retransmissions."
    ::= { ptSGM3UAASPEntry 15 }

ptSGM3UAASPMaximumAssocRetrans OBJECT-TYPE
    SYNTAX          Integer32 (0..2147483647)
    MAX-ACCESS      read-create
    STATUS          current
    DESCRIPTION     
            "Maximum association retransmissions."
    ::= { ptSGM3UAASPEntry 16 }

ptSGM3UAASPMaximumPathRetrans OBJECT-TYPE
    SYNTAX          Integer32 (0..2147483647)
    MAX-ACCESS      read-create
    STATUS          current
    DESCRIPTION     
            "Maximum path retransmissions."
    ::= { ptSGM3UAASPEntry 17 }

ptSGM3UAASPBundling OBJECT-TYPE
    SYNTAX          INTEGER { disabled(0), enabled(1) }
    MAX-ACCESS      read-create
    STATUS          current
    DESCRIPTION     
            "Enable or disable the Bundling feature."
    ::= { ptSGM3UAASPEntry 18 }

ptSGM3UAASPBundlingTimeout OBJECT-TYPE
    SYNTAX          Integer32 (0..2147483647)
    MAX-ACCESS      read-create
    STATUS          current
    DESCRIPTION     
            "Bundling timeout (msecs)."
    ::= { ptSGM3UAASPEntry 19 }

ptSGM3UAASPDelayedAckTimeout OBJECT-TYPE
    SYNTAX          Integer32 (0..500)
    MAX-ACCESS      read-create
    STATUS          current
    DESCRIPTION     
            "Delayed acknowledgement timeout."
    ::= { ptSGM3UAASPEntry 20 }

ptSGM3UAASPChecksum OBJECT-TYPE
    SYNTAX          INTEGER { adler32(0), crc32c(1), none(2) }
    MAX-ACCESS      read-only
    STATUS          current
    DESCRIPTION     
            "Checksum algorithm"
    ::= { ptSGM3UAASPEntry 21 }

ptSGM3UAASPInStreams OBJECT-TYPE
    SYNTAX          Integer32 (0..65355)
    MAX-ACCESS      read-create
    STATUS          current
    DESCRIPTION     
            "Number of in streams."
    ::= { ptSGM3UAASPEntry 22 }

ptSGM3UAASPOutStreams OBJECT-TYPE
    SYNTAX          Integer32 (0..65355)
    MAX-ACCESS      read-create
    STATUS          current
    DESCRIPTION     
            "Number of out streams."
    ::= { ptSGM3UAASPEntry 23 }

ptSGM3UAASPUserASPID OBJECT-TYPE
    SYNTAX          DisplayString (SIZE(0..255))
    MAX-ACCESS      read-only
    STATUS          current
    DESCRIPTION     
            "M3UA ASP Identifier received from a preconfigured user. This value can differ from the ID if ASP ID Validation for the pre-configured ASP has been set to DISABLED. The User ASP ID is used (rather than the ID) when sending NOTIFY messages concerning this ASP."
    ::= { ptSGM3UAASPEntry 24 }

ptSGM3UAASPName OBJECT-TYPE
    SYNTAX          DisplayString (SIZE(0..255))
    MAX-ACCESS      read-only
    STATUS          current
    DESCRIPTION     
            "M3UA ASP name."
    ::= { ptSGM3UAASPEntry 25 }

ptSGM3UAASPRxMSGCount OBJECT-TYPE
    SYNTAX          Integer32 (-2147483648..2147483647)
    MAX-ACCESS      read-only
    STATUS          current
    DESCRIPTION     
            "Number Received Messages per second"
    ::= { ptSGM3UAASPEntry 26 }

ptSGM3UAASPTxMSGCount OBJECT-TYPE
    SYNTAX          Integer32 (-2147483648..2147483647)
    MAX-ACCESS      read-only
    STATUS          current
    DESCRIPTION     
            "Number Transmitted Messages per second"
    ::= { ptSGM3UAASPEntry 27 }

ptSGM3UAASPM3UAIndex OBJECT-TYPE
    SYNTAX          Integer32 (-2147483648..2147483647)
    MAX-ACCESS      not-accessible
    STATUS          current
    DESCRIPTION     
            "This is the index of the parent type for this object.
             This parent type is M3UA."
    ::= { ptSGM3UAASPEntry 242 }

ptSGM3UAASPM3UAASPsIndex OBJECT-TYPE
    SYNTAX          Integer32 (-2147483648..2147483647)
    MAX-ACCESS      not-accessible
    STATUS          current
    DESCRIPTION     
            "This is the index of the parent type for this object.
             This parent type is M3UAASPs."
    ::= { ptSGM3UAASPEntry 243 }

ptSGM3UAASPActions OBJECT-TYPE
    SYNTAX          INTEGER { terminate(1), shutdown(2) }
    MAX-ACCESS      read-create
    STATUS          current
    DESCRIPTION     
            "The OID of all possible actions for this instance"
    ::= { ptSGM3UAASPEntry 252 }

ptSGM3UAASPParentOID OBJECT-TYPE
    SYNTAX          OBJECT IDENTIFIER
    MAX-ACCESS      read-create
    STATUS          current
    DESCRIPTION     
            "The OID of the parent object for this instance"
    ::= { ptSGM3UAASPEntry 253 }

ptSGM3UAASPRowStatus OBJECT-TYPE
    SYNTAX          RowStatus
    MAX-ACCESS      read-create
    STATUS          current
    DESCRIPTION     
            "The row status for the SGM3UAASP table"
    ::= { ptSGM3UAASPEntry 254 }

ptSGM3UAASPIndex OBJECT-TYPE
    SYNTAX          Integer32 (-2147483648..2147483647)
    MAX-ACCESS      not-accessible
    STATUS          current
    DESCRIPTION     
            "The row number for the SGM3UAASP table"
    ::= { ptSGM3UAASPEntry 255 }

ptSGM3UASCTPServers OBJECT IDENTIFIER
    ::= { ptSGM3UA 183 }

ptSGM3UASCTPServersTable OBJECT-TYPE
    SYNTAX          SEQUENCE OF PtSGM3UASCTPServersEntry
    MAX-ACCESS      not-accessible
    STATUS          current
    DESCRIPTION     
            "No description supplied in the proxy config file."
    ::= { ptSGM3UASCTPServers 1 }

ptSGM3UASCTPServersEntry OBJECT-TYPE
    SYNTAX          PtSGM3UASCTPServersEntry
    MAX-ACCESS      not-accessible
    STATUS          current
    DESCRIPTION     
            "A sequence of SGM3UASCTPServers attributes."
    INDEX           { ptConnGroupIndex, ptSGM3UASCTPServersM3UAIndex, 
                      ptSGM3UASCTPServersIndex }
    ::= { ptSGM3UASCTPServersTable 1 }

PtSGM3UASCTPServersEntry ::=
    SEQUENCE {
        ptSGM3UASCTPServersASPManagement INTEGER,
        ptSGM3UASCTPServersStatus       INTEGER,
        ptSGM3UASCTPServersHeartbeat    INTEGER,
        ptSGM3UASCTPServersHeartbeatInterval    Integer32,
        ptSGM3UASCTPServersMaximumAssocRetrans      Integer32,
        ptSGM3UASCTPServersMaximumPathRetrans     Integer32,
        ptSGM3UASCTPServersMaximumInitRetrans     Integer32,
        ptSGM3UASCTPServersBundling     INTEGER,
        ptSGM3UASCTPServersBundlingTimeout  Integer32,
        ptSGM3UASCTPServersDelayedAckTimeout    Integer32,
        ptSGM3UASCTPServersRTOInitial   Integer32,
        ptSGM3UASCTPServersRTOMinimum   Integer32,
        ptSGM3UASCTPServersRTOMaximum   Integer32,
        ptSGM3UASCTPServersChecksum     INTEGER,
        ptSGM3UASCTPServersInStreams    Integer32,
        ptSGM3UASCTPServersOutStreams   Integer32,
        ptSGM3UASCTPServersDefaultNetworkAppearance           Integer32,
        ptSGM3UASCTPServersM3UAIndex    Integer32,
        ptSGM3UASCTPServersActions      INTEGER,
        ptSGM3UASCTPServersParentOID    OBJECT IDENTIFIER,
        ptSGM3UASCTPServersRowStatus    RowStatus,
        ptSGM3UASCTPServersIndex        Integer32
    }

ptSGM3UASCTPServersASPManagement OBJECT-TYPE
    SYNTAX          INTEGER { configuredAndDynamic(0), configuredOnly(1) }
    MAX-ACCESS      read-create
    STATUS          current
    DESCRIPTION     
            "ASP Dynamic and/or preconfigured setup."
    ::= { ptSGM3UASCTPServersEntry 1 }

ptSGM3UASCTPServersStatus OBJECT-TYPE
    SYNTAX          INTEGER { disabled(0), enabled(1) }
    MAX-ACCESS      read-only
    STATUS          current
    DESCRIPTION     
            "M3UA SCTP Over All Server status."
    ::= { ptSGM3UASCTPServersEntry 2 }

ptSGM3UASCTPServersHeartbeat OBJECT-TYPE
    SYNTAX          INTEGER { disabled(0), enabled(1) }
    MAX-ACCESS      read-create
    STATUS          current
    DESCRIPTION     
            "Enable or disable the Heartbeat feature. \nSCTP Server must be de-activated and re-activated to take effect."
    ::= { ptSGM3UASCTPServersEntry 6 }

ptSGM3UASCTPServersHeartbeatInterval OBJECT-TYPE
    SYNTAX          Integer32 (0..65355)
    MAX-ACCESS      read-create
    STATUS          current
    DESCRIPTION     
            "Heartbeat interval (ms). \nSCTP Server must be de-activated and re-activated to take effect."
    ::= { ptSGM3UASCTPServersEntry 7 }

ptSGM3UASCTPServersMaximumAssocRetrans OBJECT-TYPE
    SYNTAX          Integer32 (0..2147483647)
    MAX-ACCESS      read-create
    STATUS          current
    DESCRIPTION     
            "Maximum association retransmissions. \nSCTP Server must be de-activated and re-activated to take effect."
    ::= { ptSGM3UASCTPServersEntry 8 }

ptSGM3UASCTPServersMaximumPathRetrans OBJECT-TYPE
    SYNTAX          Integer32 (0..2147483647)
    MAX-ACCESS      read-create
    STATUS          current
    DESCRIPTION     
            "Maximum path retransmissions. \nSCTP Server must be de-activated and re-activated to take effect."
    ::= { ptSGM3UASCTPServersEntry 9 }

ptSGM3UASCTPServersMaximumInitRetrans OBJECT-TYPE
    SYNTAX          Integer32 (0..2147483647)
    MAX-ACCESS      read-create
    STATUS          current
    DESCRIPTION     
            "Maximum initial retransmissions. \nSCTP Server must be de-activated and re-activated to take effect."
    ::= { ptSGM3UASCTPServersEntry 10 }

ptSGM3UASCTPServersBundling OBJECT-TYPE
    SYNTAX          INTEGER { disabled(0), enabled(1) }
    MAX-ACCESS      read-create
    STATUS          current
    DESCRIPTION     
            "Enable or disable the Bundling feature. \nSCTP Server must be de-activated and re-activated to take effect."
    ::= { ptSGM3UASCTPServersEntry 11 }

ptSGM3UASCTPServersBundlingTimeout OBJECT-TYPE
    SYNTAX          Integer32 (0..2147483647)
    MAX-ACCESS      read-create
    STATUS          current
    DESCRIPTION     
            "Bundling timeout (msecs). \nSCTP Server must be de-activated and re-activated to take effect."
    ::= { ptSGM3UASCTPServersEntry 12 }

ptSGM3UASCTPServersDelayedAckTimeout OBJECT-TYPE
    SYNTAX          Integer32 (0..500)
    MAX-ACCESS      read-create
    STATUS          current
    DESCRIPTION     
            "Delayed acknowledgement timeout. \nSCTP Server must be de-activated and re-activated to take effect."
    ::= { ptSGM3UASCTPServersEntry 13 }

ptSGM3UASCTPServersRTOInitial OBJECT-TYPE
    SYNTAX          Integer32 (0..2147483647)
    MAX-ACCESS      read-create
    STATUS          current
    DESCRIPTION     
            "Initial Retransmission Timeout (ms). \nSCTP Server must be de-activated and re-activated to take effect."
    ::= { ptSGM3UASCTPServersEntry 15 }

ptSGM3UASCTPServersRTOMinimum OBJECT-TYPE
    SYNTAX          Integer32 (0..2147483647)
    MAX-ACCESS      read-create
    STATUS          current
    DESCRIPTION     
            "Minimum Retransmission Timeout (ms). \nSCTP Server must be de-activated and re-activated to take effect."
    ::= { ptSGM3UASCTPServersEntry 16 }

ptSGM3UASCTPServersRTOMaximum OBJECT-TYPE
    SYNTAX          Integer32 (0..2147483647)
    MAX-ACCESS      read-create
    STATUS          current
    DESCRIPTION     
            "Maximum Retransmission Timeout (ms). \nSCTP Server must be de-activated and re-activated to take effect."
    ::= { ptSGM3UASCTPServersEntry 17 }

ptSGM3UASCTPServersChecksum OBJECT-TYPE
    SYNTAX          INTEGER { adler32(0), crc32c(1), none(2) }
    MAX-ACCESS      read-only
    STATUS          current
    DESCRIPTION     
            "Checksum algorithm. \nSCTP Server must be de-activated and re-activated to take effect."
    ::= { ptSGM3UASCTPServersEntry 18 }

ptSGM3UASCTPServersInStreams OBJECT-TYPE
    SYNTAX          Integer32 (0..65355)
    MAX-ACCESS      read-create
    STATUS          current
    DESCRIPTION     
            "Number of in streams. \nSCTP Server must be de-activated and re-activated to take effect."
    ::= { ptSGM3UASCTPServersEntry 19 }

ptSGM3UASCTPServersOutStreams OBJECT-TYPE
    SYNTAX          Integer32 (0..65355)
    MAX-ACCESS      read-create
    STATUS          current
    DESCRIPTION     
            "Number of out streams. \nSCTP Server must be de-activated and re-activated to take effect."
    ::= { ptSGM3UASCTPServersEntry 20 }

ptSGM3UASCTPServersDefaultNetworkAppearance OBJECT-TYPE
    SYNTAX          Integer32 (-2147483648..2147483647)
    MAX-ACCESS      read-create
    STATUS          current
    DESCRIPTION     
            "M3UA default network appearance. \nIf the NA is not provided in the transfer message and the connected ASP is either dynamic or the default NA of its corresponding configured ASP object is UNSET (-1), this value is used to select the MTP3 NA Connection. \nChanging this attribute value can impact traffic."
    ::= { ptSGM3UASCTPServersEntry 21 }

ptSGM3UASCTPServersM3UAIndex OBJECT-TYPE
    SYNTAX          Integer32 (-2147483648..2147483647)
    MAX-ACCESS      not-accessible
    STATUS          current
    DESCRIPTION     
            "This is the index of the parent type for this object.
             This parent type is M3UA."
    ::= { ptSGM3UASCTPServersEntry 242 }

ptSGM3UASCTPServersActions OBJECT-TYPE
    SYNTAX          INTEGER { activateAll(1), deactivateAll(2) }
    MAX-ACCESS      read-create
    STATUS          current
    DESCRIPTION     
            "The OID of all possible actions for this instance"
    ::= { ptSGM3UASCTPServersEntry 252 }

ptSGM3UASCTPServersParentOID OBJECT-TYPE
    SYNTAX          OBJECT IDENTIFIER
    MAX-ACCESS      read-create
    STATUS          current
    DESCRIPTION     
            "The OID of the parent object for this instance"
    ::= { ptSGM3UASCTPServersEntry 253 }

ptSGM3UASCTPServersRowStatus OBJECT-TYPE
    SYNTAX          RowStatus
    MAX-ACCESS      read-create
    STATUS          current
    DESCRIPTION     
            "The row status for the SGM3UASCTPServers table"
    ::= { ptSGM3UASCTPServersEntry 254 }

ptSGM3UASCTPServersIndex OBJECT-TYPE
    SYNTAX          Integer32 (-2147483648..2147483647)
    MAX-ACCESS      not-accessible
    STATUS          current
    DESCRIPTION     
            "The row number for the SGM3UASCTPServers table"
    ::= { ptSGM3UASCTPServersEntry 255 }

ptSGM3UASCTPServer OBJECT IDENTIFIER
    ::= { ptSGM3UASCTPServers 184 }

ptSGM3UASCTPServerTable OBJECT-TYPE
    SYNTAX          SEQUENCE OF PtSGM3UASCTPServerEntry
    MAX-ACCESS      not-accessible
    STATUS          current
    DESCRIPTION     
            "No description supplied in the proxy config file."
    ::= { ptSGM3UASCTPServer 1 }

ptSGM3UASCTPServerEntry OBJECT-TYPE
    SYNTAX          PtSGM3UASCTPServerEntry
    MAX-ACCESS      not-accessible
    STATUS          current
    DESCRIPTION     
            "A sequence of SGM3UASCTPServer attributes."
    INDEX           { ptConnGroupIndex, ptSGM3UASCTPServerM3UAIndex, 
                      ptSGM3UASCTPServerM3UASCTPServersIndex, 
                      ptSGM3UASCTPServerIndex }
    ::= { ptSGM3UASCTPServerTable 1 }

PtSGM3UASCTPServerEntry ::=
    SEQUENCE {
        ptSGM3UASCTPServerSlot          Integer32,
        ptSGM3UASCTPServerIPAddress1    DisplayString,
        ptSGM3UASCTPServerIPAddress2    DisplayString,
        ptSGM3UASCTPServerPort          Integer32,
        ptSGM3UASCTPServerServerID      Integer32,
        ptSGM3UASCTPServerStatus        INTEGER,
        ptSGM3UASCTPServerHeartbeat     INTEGER,
        ptSGM3UASCTPServerHeartbeatInterval   Integer32,
        ptSGM3UASCTPServerRTOInitial    Integer32,
        ptSGM3UASCTPServerRTOMinimum    Integer32,
        ptSGM3UASCTPServerRTOMaximum    Integer32,
        ptSGM3UASCTPServerMaximumInitRetrans    Integer32,
        ptSGM3UASCTPServerMaximumAssocRetrans     Integer32,
        ptSGM3UASCTPServerMaximumPathRetrans    Integer32,
        ptSGM3UASCTPServerBundling      INTEGER,
        ptSGM3UASCTPServerBundlingTimeout Integer32,
        ptSGM3UASCTPServerDelayedAckTimeout   Integer32,
        ptSGM3UASCTPServerChecksum      INTEGER,
        ptSGM3UASCTPServerInStreams     Integer32,
        ptSGM3UASCTPServerOutStreams    Integer32,
        ptSGM3UASCTPServerDefaultSCTPValues   INTEGER,
        ptSGM3UASCTPServerListenStatus  INTEGER,
        ptSGM3UASCTPServerM3UAIndex     Integer32,
        ptSGM3UASCTPServerM3UASCTPServersIndex      Integer32,
        ptSGM3UASCTPServerActions       INTEGER,
        ptSGM3UASCTPServerParentOID     OBJECT IDENTIFIER,
        ptSGM3UASCTPServerRowStatus     RowStatus,
        ptSGM3UASCTPServerIndex         Integer32
    }

ptSGM3UASCTPServerSlot OBJECT-TYPE
    SYNTAX          Integer32 (-2147483648..2147483647)
    MAX-ACCESS      read-only
    STATUS          current
    DESCRIPTION     
            "The Slot where the server is being configured"
    ::= { ptSGM3UASCTPServerEntry 1 }

ptSGM3UASCTPServerIPAddress1 OBJECT-TYPE
    SYNTAX          DisplayString (SIZE(0..255))
    MAX-ACCESS      read-create
    STATUS          current
    DESCRIPTION     
            "M3UA SCTP Server primary address. This may be a hostname or an IP Address. If a hostname is used it must be provisioned either in /etc/hosts or via a properly-configured DNS Server and should resolve to a subset of the local IP Addresses configured for the slot where the SCTP server is hosted. Hostname resolution is attempted periodically. Resolution updates take effect ONLY when the server is restarted."
    ::= { ptSGM3UASCTPServerEntry 2 }

ptSGM3UASCTPServerIPAddress2 OBJECT-TYPE
    SYNTAX          DisplayString (SIZE(0..255))
    MAX-ACCESS      read-create
    STATUS          current
    DESCRIPTION     
            "M3UA SCTP Server secondary address. This may be a hostname or an IP Address. If a hostname is used it must be provisioned either in /etc/hosts or via a properly-configured DNS Server and should resolve to a subset of the local IP Addresses configured for the slot where the SCTP server is hosted. Hostname resolution is attempted periodically. Resolution updates take effect ONLY when the server is restarted."
    ::= { ptSGM3UASCTPServerEntry 3 }

ptSGM3UASCTPServerPort OBJECT-TYPE
    SYNTAX          Integer32 (-2147483648..2147483647)
    MAX-ACCESS      read-create
    STATUS          current
    DESCRIPTION     
            "M3UA SCTP Server port."
    ::= { ptSGM3UASCTPServerEntry 4 }

ptSGM3UASCTPServerServerID OBJECT-TYPE
    SYNTAX          Integer32 (-2147483648..2147483647)
    MAX-ACCESS      read-only
    STATUS          current
    DESCRIPTION     
            "M3UA SCTP Server ID."
    ::= { ptSGM3UASCTPServerEntry 5 }

ptSGM3UASCTPServerStatus OBJECT-TYPE
    SYNTAX          INTEGER { disabled(0), enabled(1) }
    MAX-ACCESS      read-only
    STATUS          current
    DESCRIPTION     
            "M3UA SCTP Over All Server status."
    ::= { ptSGM3UASCTPServerEntry 6 }

ptSGM3UASCTPServerHeartbeat OBJECT-TYPE
    SYNTAX          INTEGER { disabled(0), enabled(1) }
    MAX-ACCESS      read-create
    STATUS          current
    DESCRIPTION     
            "Enable or disable the Heartbeat feature. \nSCTP Server must be de-activated and re-activated to take effect."
    ::= { ptSGM3UASCTPServerEntry 7 }

ptSGM3UASCTPServerHeartbeatInterval OBJECT-TYPE
    SYNTAX          Integer32 (0..65355)
    MAX-ACCESS      read-create
    STATUS          current
    DESCRIPTION     
            "Heartbeat interval (ms). \nSCTP Server must be de-activated and re-activated to take effect."
    ::= { ptSGM3UASCTPServerEntry 8 }

ptSGM3UASCTPServerRTOInitial OBJECT-TYPE
    SYNTAX          Integer32 (0..2147483647)
    MAX-ACCESS      read-create
    STATUS          current
    DESCRIPTION     
            "Initial Retransmission Timeout (ms). \nSCTP Server must be de-activated and re-activated to take effect."
    ::= { ptSGM3UASCTPServerEntry 9 }

ptSGM3UASCTPServerRTOMinimum OBJECT-TYPE
    SYNTAX          Integer32 (0..2147483647)
    MAX-ACCESS      read-create
    STATUS          current
    DESCRIPTION     
            "Minimum Retransmission Timeout (ms). \nSCTP Server must be de-activated and re-activated to take effect."
    ::= { ptSGM3UASCTPServerEntry 10 }

ptSGM3UASCTPServerRTOMaximum OBJECT-TYPE
    SYNTAX          Integer32 (0..2147483647)
    MAX-ACCESS      read-create
    STATUS          current
    DESCRIPTION     
            "Maximum Retransmission Timeout (ms). \nSCTP Server must be de-activated and re-activated to take effect."
    ::= { ptSGM3UASCTPServerEntry 11 }

ptSGM3UASCTPServerMaximumInitRetrans OBJECT-TYPE
    SYNTAX          Integer32 (0..2147483647)
    MAX-ACCESS      read-create
    STATUS          current
    DESCRIPTION     
            "Maximum initial retransmissions. \nSCTP Server must be de-activated and re-activated to take effect."
    ::= { ptSGM3UASCTPServerEntry 12 }

ptSGM3UASCTPServerMaximumAssocRetrans OBJECT-TYPE
    SYNTAX          Integer32 (0..2147483647)
    MAX-ACCESS      read-create
    STATUS          current
    DESCRIPTION     
            "Maximum association retransmissions. \nSCTP Server must be de-activated and re-activated to take effect."
    ::= { ptSGM3UASCTPServerEntry 13 }

ptSGM3UASCTPServerMaximumPathRetrans OBJECT-TYPE
    SYNTAX          Integer32 (0..2147483647)
    MAX-ACCESS      read-create
    STATUS          current
    DESCRIPTION     
            "Maximum path retransmissions. \nSCTP Server must be de-activated and re-activated to take effect."
    ::= { ptSGM3UASCTPServerEntry 14 }

ptSGM3UASCTPServerBundling OBJECT-TYPE
    SYNTAX          INTEGER { disabled(0), enabled(1) }
    MAX-ACCESS      read-create
    STATUS          current
    DESCRIPTION     
            "Enable or disable the Bundling feature. \nSCTP Server must be de-activated and re-activated to take effect."
    ::= { ptSGM3UASCTPServerEntry 15 }

ptSGM3UASCTPServerBundlingTimeout OBJECT-TYPE
    SYNTAX          Integer32 (0..2147483647)
    MAX-ACCESS      read-create
    STATUS          current
    DESCRIPTION     
            "Bundling timeout (msecs). \nSCTP Server must be de-activated and re-activated to take effect."
    ::= { ptSGM3UASCTPServerEntry 16 }

ptSGM3UASCTPServerDelayedAckTimeout OBJECT-TYPE
    SYNTAX          Integer32 (0..500)
    MAX-ACCESS      read-create
    STATUS          current
    DESCRIPTION     
            "Delayed acknowledgement timeout. \nSCTP Server must be de-activated and re-activated to take effect."
    ::= { ptSGM3UASCTPServerEntry 17 }

ptSGM3UASCTPServerChecksum OBJECT-TYPE
    SYNTAX          INTEGER { adler32(0), crc32c(1), none(2) }
    MAX-ACCESS      read-only
    STATUS          current
    DESCRIPTION     
            "Checksum algorithm. \nSCTP Server must be de-activated and re-activated to take effect."
    ::= { ptSGM3UASCTPServerEntry 18 }

ptSGM3UASCTPServerInStreams OBJECT-TYPE
    SYNTAX          Integer32 (0..65355)
    MAX-ACCESS      read-create
    STATUS          current
    DESCRIPTION     
            "Number of in streams. \nSCTP Server must be de-activated and re-activated to take effect."
    ::= { ptSGM3UASCTPServerEntry 19 }

ptSGM3UASCTPServerOutStreams OBJECT-TYPE
    SYNTAX          Integer32 (0..65355)
    MAX-ACCESS      read-create
    STATUS          current
    DESCRIPTION     
            "Number of out streams. \nSCTP Server must be de-activated and re-activated to take effect."
    ::= { ptSGM3UASCTPServerEntry 20 }

ptSGM3UASCTPServerDefaultSCTPValues OBJECT-TYPE
    SYNTAX          INTEGER { no(0), yes(1) }
    MAX-ACCESS      read-create
    STATUS          current
    DESCRIPTION     
            "Use M3UA SCTP default parameters."
    ::= { ptSGM3UASCTPServerEntry 21 }

ptSGM3UASCTPServerListenStatus OBJECT-TYPE
    SYNTAX          INTEGER { down(0), stopped(1), up(2), partiallyUp(3) }
    MAX-ACCESS      read-only
    STATUS          current
    DESCRIPTION     
            "M3UA SCTP Server Listen Status.\n If Status is DISABLED, Listen Status must be set to 'DOWN'.\n If Status is ENABLED, Listen Status must be set to one of the following states:\n - 'DOWN': The server is not listening on any of the provided IP addresses due to a technical issue, e.g., the provided port is already in use, the provided IP addresses are not available or the provided hostnames are not resolvable.\n The alarm M3UASCTPServerDown indicating that the server is down must be raised.\n - 'STOPPED': The server is not listening on any of the provided IP addresses because it has been purposefully stopped by the application. This status means that the server has been 'UP' or 'PARTIALLY UP' and it has been purposefully brought down either because the ASP license max count has been reached or because SCTP system max capacity per routing slot has been reached.\n The alarm M3UASCTPServerDown indicating that the server is down must be raised.\n - 'UP': The server is listening on all the provided IP addresses\n - 'PARTIALLY UP': The server is listening on at least one, but not all, of the provided IP addresses.\n The alarm M3UASCTPServerAddrListMismatch, indicating a mismatch between the list of the provided IP addresses and the list of the listening IP addresses, must be raised. PARTIALLY UP is also an indication that the server was up but the hostname has been removed from the hosts file. In this case the Server Status will be PARTIALLY UP but will continue to listen until deactivated."
    ::= { ptSGM3UASCTPServerEntry 22 }

ptSGM3UASCTPServerM3UAIndex OBJECT-TYPE
    SYNTAX          Integer32 (-2147483648..2147483647)
    MAX-ACCESS      not-accessible
    STATUS          current
    DESCRIPTION     
            "This is the index of the parent type for this object.
             This parent type is M3UA."
    ::= { ptSGM3UASCTPServerEntry 242 }

ptSGM3UASCTPServerM3UASCTPServersIndex OBJECT-TYPE
    SYNTAX          Integer32 (-2147483648..2147483647)
    MAX-ACCESS      not-accessible
    STATUS          current
    DESCRIPTION     
            "This is the index of the parent type for this object.
             This parent type is M3UASCTPServers."
    ::= { ptSGM3UASCTPServerEntry 243 }

ptSGM3UASCTPServerActions OBJECT-TYPE
    SYNTAX          INTEGER { activate(1), deactivate(2) }
    MAX-ACCESS      read-create
    STATUS          current
    DESCRIPTION     
            "The OID of all possible actions for this instance"
    ::= { ptSGM3UASCTPServerEntry 252 }

ptSGM3UASCTPServerParentOID OBJECT-TYPE
    SYNTAX          OBJECT IDENTIFIER
    MAX-ACCESS      read-create
    STATUS          current
    DESCRIPTION     
            "The OID of the parent object for this instance"
    ::= { ptSGM3UASCTPServerEntry 253 }

ptSGM3UASCTPServerRowStatus OBJECT-TYPE
    SYNTAX          RowStatus
    MAX-ACCESS      read-create
    STATUS          current
    DESCRIPTION     
            "The row status for the SGM3UASCTPServer table"
    ::= { ptSGM3UASCTPServerEntry 254 }

ptSGM3UASCTPServerIndex OBJECT-TYPE
    SYNTAX          Integer32 (-2147483648..2147483647)
    MAX-ACCESS      not-accessible
    STATUS          current
    DESCRIPTION     
            "The row number for the SGM3UASCTPServer table"
    ::= { ptSGM3UASCTPServerEntry 255 }

ptSGM3UAConfiguredASPs OBJECT IDENTIFIER
    ::= { ptSGM3UA 185 }

ptSGM3UAConfiguredASPsTable OBJECT-TYPE
    SYNTAX          SEQUENCE OF PtSGM3UAConfiguredASPsEntry
    MAX-ACCESS      not-accessible
    STATUS          current
    DESCRIPTION     
            "No description supplied in the proxy config file."
    ::= { ptSGM3UAConfiguredASPs 1 }

ptSGM3UAConfiguredASPsEntry OBJECT-TYPE
    SYNTAX          PtSGM3UAConfiguredASPsEntry
    MAX-ACCESS      not-accessible
    STATUS          current
    DESCRIPTION     
            "A sequence of SGM3UAConfiguredASPs attributes."
    INDEX           { ptConnGroupIndex, ptSGM3UAConfiguredASPsM3UAIndex, 
                      ptSGM3UAConfiguredASPsIndex }
    ::= { ptSGM3UAConfiguredASPsTable 1 }

PtSGM3UAConfiguredASPsEntry ::=
    SEQUENCE {
        ptSGM3UAConfiguredASPsM3UAIndex Integer32,
        ptSGM3UAConfiguredASPsActions   INTEGER,
        ptSGM3UAConfiguredASPsParentOID OBJECT IDENTIFIER,
        ptSGM3UAConfiguredASPsRowStatus RowStatus,
        ptSGM3UAConfiguredASPsIndex     Integer32
    }

ptSGM3UAConfiguredASPsM3UAIndex OBJECT-TYPE
    SYNTAX          Integer32 (-2147483648..2147483647)
    MAX-ACCESS      not-accessible
    STATUS          current
    DESCRIPTION     
            "This is the index of the parent type for this object.
             This parent type is M3UA."
    ::= { ptSGM3UAConfiguredASPsEntry 242 }

ptSGM3UAConfiguredASPsActions OBJECT-TYPE
    SYNTAX          INTEGER { resetIMF(1) }
    MAX-ACCESS      read-create
    STATUS          current
    DESCRIPTION     
            "The OID of all possible actions for this instance"
    ::= { ptSGM3UAConfiguredASPsEntry 252 }

ptSGM3UAConfiguredASPsParentOID OBJECT-TYPE
    SYNTAX          OBJECT IDENTIFIER
    MAX-ACCESS      read-create
    STATUS          current
    DESCRIPTION     
            "The OID of the parent object for this instance"
    ::= { ptSGM3UAConfiguredASPsEntry 253 }

ptSGM3UAConfiguredASPsRowStatus OBJECT-TYPE
    SYNTAX          RowStatus
    MAX-ACCESS      read-create
    STATUS          current
    DESCRIPTION     
            "The row status for the SGM3UAConfiguredASPs table"
    ::= { ptSGM3UAConfiguredASPsEntry 254 }

ptSGM3UAConfiguredASPsIndex OBJECT-TYPE
    SYNTAX          Integer32 (-2147483648..2147483647)
    MAX-ACCESS      not-accessible
    STATUS          current
    DESCRIPTION     
            "The row number for the SGM3UAConfiguredASPs table"
    ::= { ptSGM3UAConfiguredASPsEntry 255 }

ptSGM3UAConfiguredASP OBJECT IDENTIFIER
    ::= { ptSGM3UAConfiguredASPs 186 }

ptSGM3UAConfiguredASPTable OBJECT-TYPE
    SYNTAX          SEQUENCE OF PtSGM3UAConfiguredASPEntry
    MAX-ACCESS      not-accessible
    STATUS          current
    DESCRIPTION     
            "No description supplied in the proxy config file."
    ::= { ptSGM3UAConfiguredASP 1 }

ptSGM3UAConfiguredASPEntry OBJECT-TYPE
    SYNTAX          PtSGM3UAConfiguredASPEntry
    MAX-ACCESS      not-accessible
    STATUS          current
    DESCRIPTION     
            "A sequence of SGM3UAConfiguredASP attributes."
    INDEX           { ptConnGroupIndex, ptSGM3UAConfiguredASPM3UAIndex, 
                      ptSGM3UAConfiguredASPM3UAConfiguredASPsIndex, 
                      ptSGM3UAConfiguredASPIndex }
    ::= { ptSGM3UAConfiguredASPTable 1 }

PtSGM3UAConfiguredASPEntry ::=
    SEQUENCE {
        ptSGM3UAConfiguredASPID         Integer32,
        ptSGM3UAConfiguredASPPort       Integer32,
        ptSGM3UAConfiguredASPIPAddress1 DisplayString,
        ptSGM3UAConfiguredASPIPAddress2 DisplayString,
        ptSGM3UAConfiguredASPASPIDValidation    INTEGER,
        ptSGM3UAConfiguredASPIncomingAppID  DisplayString,
        ptSGM3UAConfiguredASPName       DisplayString,
        ptSGM3UAConfiguredASPRCInDATAMessage    INTEGER,
        ptSGM3UAConfiguredASPServerID   INTEGER,
        ptSGM3UAConfiguredASPSlot       INTEGER,
        ptSGM3UAConfiguredASPUserActivated  INTEGER,
        ptSGM3UAConfiguredASPNAInDATAMessage    INTEGER,
        ptSGM3UAConfiguredASPNATranslation  INTEGER,
        ptSGM3UAConfiguredASPDefaultNetworkAppearance             INTEGER,
        ptSGM3UAConfiguredASPIMFSupport INTEGER,
        ptSGM3UAConfiguredASPM3UAIndex  Integer32,
        ptSGM3UAConfiguredASPM3UAConfiguredASPsIndex            Integer32,
        ptSGM3UAConfiguredASPActions    INTEGER,
        ptSGM3UAConfiguredASPParentOID  OBJECT IDENTIFIER,
        ptSGM3UAConfiguredASPRowStatus  RowStatus,
        ptSGM3UAConfiguredASPIndex      Integer32
    }

ptSGM3UAConfiguredASPID OBJECT-TYPE
    SYNTAX          Integer32 (1..2147483647)
    MAX-ACCESS      read-only
    STATUS          current
    DESCRIPTION     
            "M3UA configured ASP unique identifier."
    ::= { ptSGM3UAConfiguredASPEntry 1 }

ptSGM3UAConfiguredASPPort OBJECT-TYPE
    SYNTAX          Integer32 (-2147483648..2147483647)
    MAX-ACCESS      read-only
    STATUS          current
    DESCRIPTION     
            "Remote port from which ASP will connect."
    ::= { ptSGM3UAConfiguredASPEntry 2 }

ptSGM3UAConfiguredASPIPAddress1 OBJECT-TYPE
    SYNTAX          DisplayString (SIZE(0..255))
    MAX-ACCESS      read-only
    STATUS          current
    DESCRIPTION     
            "M3UA Configured ASP primary address. This may be a hostname or an IP Address. If a hostname is used it must be provisioned either in /etc/hosts or via a properly-configured DNS Server and should resolve to a subset of the remote IP Addresses configured for the host where the ASP terminates. Hostname resolution is attempted periodically. This attribute defines the primary IP address specifying the SCTP primary path to the remote SCTP endpoint. If the resolution returns more than one IP address, no guarantee is made as to non-ambiguous definition of the SCTP primary path."
    ::= { ptSGM3UAConfiguredASPEntry 3 }

ptSGM3UAConfiguredASPIPAddress2 OBJECT-TYPE
    SYNTAX          DisplayString (SIZE(0..255))
    MAX-ACCESS      read-only
    STATUS          current
    DESCRIPTION     
            "M3UA Configured ASP secondary address. This may be a hostname or an IP Address. If a hostname is used it must be provisioned either in /etc/hosts or via a properly-configured DNS Server and should resolve to a subset of the remote IP Addresses configured for the host where the ASP terminates. Hostname resolution is attempted periodically."
    ::= { ptSGM3UAConfiguredASPEntry 4 }

ptSGM3UAConfiguredASPASPIDValidation OBJECT-TYPE
    SYNTAX          INTEGER { disabled(0), enabled(1) }
    MAX-ACCESS      read-create
    STATUS          current
    DESCRIPTION     
            "It is highly recommended that for increased security that this attribute remain enabled. When enabled the ASP using the configured endpoint MUST either NOT send the ASP ID parameter OR send the preconfigured ID. If an ASP ID parameter contains an identifier other than what is preconfigured, an ERROR (Invalid ASP Identifier) will be sent. When disabled, the ASP Identifier contained in the ASPUP is not validated. This is typically useful when changing the ID used by the ASP is especially troublesome"
    ::= { ptSGM3UAConfiguredASPEntry 5 }

ptSGM3UAConfiguredASPIncomingAppID OBJECT-TYPE
    SYNTAX          DisplayString (SIZE(0..255))
    MAX-ACCESS      read-create
    STATUS          current
    DESCRIPTION     
            "M3UA Incoming AppID for Gateway Screening. On creation, the attribute is defaulted to M3UA_DEFAULT."
    ::= { ptSGM3UAConfiguredASPEntry 6 }

ptSGM3UAConfiguredASPName OBJECT-TYPE
    SYNTAX          DisplayString (SIZE(0..255))
    MAX-ACCESS      read-create
    STATUS          current
    DESCRIPTION     
            "M3UA configured ASP name. \nAlphanumeric with dash and underscore for a maximum of 16 characters. \nAutomatically moved to upper-case. Must be unique in M3UA. \nReserved value DYNAMIC for non-configured ASPs."
    ::= { ptSGM3UAConfiguredASPEntry 7 }

ptSGM3UAConfiguredASPRCInDATAMessage OBJECT-TYPE
    SYNTAX          INTEGER { disabled(0), enabled(1) }
    MAX-ACCESS      read-create
    STATUS          current
    DESCRIPTION     
            "When ENABLED the Routing Context parameter is included in DATA messages destined for the ASP. Per RFC4666, the inclusion of the Routing Context parameter in DATA messages is conditional. On creation, the attribute is defaulted to ENABLED."
    ::= { ptSGM3UAConfiguredASPEntry 9 }

ptSGM3UAConfiguredASPServerID OBJECT-TYPE
    SYNTAX          INTEGER { any(0) }
    MAX-ACCESS      read-create
    STATUS          current
    DESCRIPTION     
            "The Id of the server to which the configured ASP will connect"
    ::= { ptSGM3UAConfiguredASPEntry 16 }

ptSGM3UAConfiguredASPSlot OBJECT-TYPE
    SYNTAX          INTEGER { any(0) }
    MAX-ACCESS      read-create
    STATUS          current
    DESCRIPTION     
            "The Id of the slot to which the configured ASP will connect. Upon receipt of an ASP connection request, if more than one Configured ASP is found, the Configured ASP with exact slot information (exact slot number) is prioritized over the one with wildcard slot information (ANY)"
    ::= { ptSGM3UAConfiguredASPEntry 17 }

ptSGM3UAConfiguredASPUserActivated OBJECT-TYPE
    SYNTAX          INTEGER { disabled(0), enabled(1) }
    MAX-ACCESS      read-only
    STATUS          current
    DESCRIPTION     
            "M3UA ASP Association User State (ENABLED/DISABLED)."
    ::= { ptSGM3UAConfiguredASPEntry 18 }

ptSGM3UAConfiguredASPNAInDATAMessage OBJECT-TYPE
    SYNTAX          INTEGER { disabled(0), enabled(1) }
    MAX-ACCESS      read-create
    STATUS          current
    DESCRIPTION     
            "When ENABLED the Network Appearance parameter is included in DATA messages destined for the ASP. Per RFC4666, the inclusion of the Network Appearance parameter in DATA messages is optional. On creation, the attribute is defaulted to ENABLED."
    ::= { ptSGM3UAConfiguredASPEntry 19 }

ptSGM3UAConfiguredASPNATranslation OBJECT-TYPE
    SYNTAX          INTEGER { disabled(0) }
    MAX-ACCESS      read-create
    STATUS          current
    DESCRIPTION     
            "NA Translation for M3UA Configured ASPs. If enabled, all M3UA messages from the ASP containing a Network Appearance parameter of 0 will be interpreted to mean the configured value chosen. This value will be used for pertinent statistics. A default value of 0 disables the feature."
    ::= { ptSGM3UAConfiguredASPEntry 39 }

ptSGM3UAConfiguredASPDefaultNetworkAppearance OBJECT-TYPE
    SYNTAX          INTEGER { unset(-1) }
    MAX-ACCESS      read-create
    STATUS          current
    DESCRIPTION     
            "Upon receipt of an M3UA message which does not contain a Routing Context or Network Appearance parameter, the SG uses this value to determine the destination SS7 network. If this value is UNSET (-1), the Default Network Appearance specified in the M3UA SCTP Servers is used to determine the destination SS7 network. The Network Appearance must also be configured as an MTP3 NA. The default value is UNSET. \nChanging this attribute value can impact traffic."
    ::= { ptSGM3UAConfiguredASPEntry 40 }

ptSGM3UAConfiguredASPIMFSupport OBJECT-TYPE
    SYNTAX          INTEGER { disabled(0), enabled(1) }
    MAX-ACCESS      read-create
    STATUS          current
    DESCRIPTION     
            "Integrated Monitoring Feed feature support for this ASP. \nIMF must be licensed to enable this attribute. IMF Support attributes can be cleared for all configured M3UA ASPs simultaneously by using the Reset IMF action in the M3UA Configured ASPs screen."
    ::= { ptSGM3UAConfiguredASPEntry 41 }

ptSGM3UAConfiguredASPM3UAIndex OBJECT-TYPE
    SYNTAX          Integer32 (-2147483648..2147483647)
    MAX-ACCESS      not-accessible
    STATUS          current
    DESCRIPTION     
            "This is the index of the parent type for this object.
             This parent type is M3UA."
    ::= { ptSGM3UAConfiguredASPEntry 242 }

ptSGM3UAConfiguredASPM3UAConfiguredASPsIndex OBJECT-TYPE
    SYNTAX          Integer32 (-2147483648..2147483647)
    MAX-ACCESS      not-accessible
    STATUS          current
    DESCRIPTION     
            "This is the index of the parent type for this object.
             This parent type is M3UAConfiguredASPs."
    ::= { ptSGM3UAConfiguredASPEntry 243 }

ptSGM3UAConfiguredASPActions OBJECT-TYPE
    SYNTAX          INTEGER { activate(1), deactivate(2) }
    MAX-ACCESS      read-create
    STATUS          current
    DESCRIPTION     
            "The OID of all possible actions for this instance"
    ::= { ptSGM3UAConfiguredASPEntry 252 }

ptSGM3UAConfiguredASPParentOID OBJECT-TYPE
    SYNTAX          OBJECT IDENTIFIER
    MAX-ACCESS      read-create
    STATUS          current
    DESCRIPTION     
            "The OID of the parent object for this instance"
    ::= { ptSGM3UAConfiguredASPEntry 253 }

ptSGM3UAConfiguredASPRowStatus OBJECT-TYPE
    SYNTAX          RowStatus
    MAX-ACCESS      read-create
    STATUS          current
    DESCRIPTION     
            "The row status for the SGM3UAConfiguredASP table"
    ::= { ptSGM3UAConfiguredASPEntry 254 }

ptSGM3UAConfiguredASPIndex OBJECT-TYPE
    SYNTAX          Integer32 (-2147483648..2147483647)
    MAX-ACCESS      not-accessible
    STATUS          current
    DESCRIPTION     
            "The row number for the SGM3UAConfiguredASP table"
    ::= { ptSGM3UAConfiguredASPEntry 255 }

ptSGM3UARoutingContext OBJECT IDENTIFIER
    ::= { ptSGM3UAConfiguredASP 188 }

ptSGM3UARoutingContextTable OBJECT-TYPE
    SYNTAX          SEQUENCE OF PtSGM3UARoutingContextEntry
    MAX-ACCESS      not-accessible
    STATUS          current
    DESCRIPTION     
            "No description supplied in the proxy config file."
    ::= { ptSGM3UARoutingContext 1 }

ptSGM3UARoutingContextEntry OBJECT-TYPE
    SYNTAX          PtSGM3UARoutingContextEntry
    MAX-ACCESS      not-accessible
    STATUS          current
    DESCRIPTION     
            "A sequence of SGM3UARoutingContext attributes."
    INDEX           { ptConnGroupIndex, ptSGM3UARoutingContextM3UAIndex, 
                      ptSGM3UARoutingContextM3UAConfiguredASPsIndex, 
                      ptSGM3UARoutingContextM3UAConfiguredASPIndex, 
                      ptSGM3UARoutingContextIndex }
    ::= { ptSGM3UARoutingContextTable 1 }

PtSGM3UARoutingContextEntry ::=
    SEQUENCE {
        ptSGM3UARoutingContextRoutingContext    Integer32,
        ptSGM3UARoutingContextRemoteRoutingContext          INTEGER,
        ptSGM3UARoutingContextM3UAIndex Integer32,
        ptSGM3UARoutingContextM3UAConfiguredASPsIndex             Integer32,
        ptSGM3UARoutingContextM3UAConfiguredASPIndex            Integer32,
        ptSGM3UARoutingContextParentOID OBJECT IDENTIFIER,
        ptSGM3UARoutingContextRowStatus RowStatus,
        ptSGM3UARoutingContextIndex     Integer32
    }

ptSGM3UARoutingContextRoutingContext OBJECT-TYPE
    SYNTAX          Integer32 (1..2147483647)
    MAX-ACCESS      read-only
    STATUS          current
    DESCRIPTION     
            "Routing context."
    ::= { ptSGM3UARoutingContextEntry 1 }

ptSGM3UARoutingContextRemoteRoutingContext OBJECT-TYPE
    SYNTAX          INTEGER { undefined(-1) }
    MAX-ACCESS      read-create
    STATUS          current
    DESCRIPTION     
            "Remote routing context is used to connect a group of configured RCs. An ASP may go active for the group of RCs by sending a single ASP Active message containing only the remote routing context. All notifications and Acks pertaining to any AS in the group will contain the remote routing context. This feature should only be used when the ASP must send a single Routing Context but needs to register for more than one routing key. It can also be used in the case where a routing context is already configured for an AS and the ASP sends a different RC in the ASPAC message. To set the value to UNDEFINED, enter -1."
    ::= { ptSGM3UARoutingContextEntry 2 }

ptSGM3UARoutingContextM3UAIndex OBJECT-TYPE
    SYNTAX          Integer32 (-2147483648..2147483647)
    MAX-ACCESS      not-accessible
    STATUS          current
    DESCRIPTION     
            "This is the index of the parent type for this object.
             This parent type is M3UA."
    ::= { ptSGM3UARoutingContextEntry 242 }

ptSGM3UARoutingContextM3UAConfiguredASPsIndex OBJECT-TYPE
    SYNTAX          Integer32 (-2147483648..2147483647)
    MAX-ACCESS      not-accessible
    STATUS          current
    DESCRIPTION     
            "This is the index of the parent type for this object.
             This parent type is M3UAConfiguredASPs."
    ::= { ptSGM3UARoutingContextEntry 243 }

ptSGM3UARoutingContextM3UAConfiguredASPIndex OBJECT-TYPE
    SYNTAX          Integer32 (-2147483648..2147483647)
    MAX-ACCESS      not-accessible
    STATUS          current
    DESCRIPTION     
            "This is the index of the parent type for this object.
             This parent type is M3UAConfiguredASP."
    ::= { ptSGM3UARoutingContextEntry 244 }

ptSGM3UARoutingContextParentOID OBJECT-TYPE
    SYNTAX          OBJECT IDENTIFIER
    MAX-ACCESS      read-create
    STATUS          current
    DESCRIPTION     
            "The OID of the parent object for this instance"
    ::= { ptSGM3UARoutingContextEntry 253 }

ptSGM3UARoutingContextRowStatus OBJECT-TYPE
    SYNTAX          RowStatus
    MAX-ACCESS      read-create
    STATUS          current
    DESCRIPTION     
            "The row status for the SGM3UARoutingContext table"
    ::= { ptSGM3UARoutingContextEntry 254 }

ptSGM3UARoutingContextIndex OBJECT-TYPE
    SYNTAX          Integer32 (-2147483648..2147483647)
    MAX-ACCESS      not-accessible
    STATUS          current
    DESCRIPTION     
            "The row number for the SGM3UARoutingContext table"
    ::= { ptSGM3UARoutingContextEntry 255 }

ptSGM3UAMultiAssociationASP OBJECT IDENTIFIER
    ::= { ptSGM3UAConfiguredASPs 189 }

ptSGM3UAMultiAssociationASPTable OBJECT-TYPE
    SYNTAX          SEQUENCE OF PtSGM3UAMultiAssociationASPEntry
    MAX-ACCESS      not-accessible
    STATUS          current
    DESCRIPTION     
            "No description supplied in the proxy config file."
    ::= { ptSGM3UAMultiAssociationASP 1 }

ptSGM3UAMultiAssociationASPEntry OBJECT-TYPE
    SYNTAX          PtSGM3UAMultiAssociationASPEntry
    MAX-ACCESS      not-accessible
    STATUS          current
    DESCRIPTION     
            "A sequence of SGM3UAMultiAssociationASP attributes."
    INDEX           { ptConnGroupIndex, 
                      ptSGM3UAMultiAssociationASPM3UAIndex, 
                      ptSGM3UAMultiAssociationASPM3UAConfiguredASPsIndex, 
                      ptSGM3UAMultiAssociationASPIndex }
    ::= { ptSGM3UAMultiAssociationASPTable 1 }

PtSGM3UAMultiAssociationASPEntry ::=
    SEQUENCE {
        ptSGM3UAMultiAssociationASPID   Integer32,
        ptSGM3UAMultiAssociationASPName DisplayString,
        ptSGM3UAMultiAssociationASPASPIDValidation          INTEGER,
        ptSGM3UAMultiAssociationASPIncomingAppID        DisplayString,
        ptSGM3UAMultiAssociationASPRCInDATAMessage          INTEGER,
        ptSGM3UAMultiAssociationASPSCTPRole   INTEGER,
        ptSGM3UAMultiAssociationASPASPType  INTEGER,
        ptSGM3UAMultiAssociationASPHeartbeatInterval            Integer32,
        ptSGM3UAMultiAssociationASPRTOInitial     Integer32,
        ptSGM3UAMultiAssociationASPRTOMinimum     Integer32,
        ptSGM3UAMultiAssociationASPRTOMaximum     Integer32,
        ptSGM3UAMultiAssociationASPMaximumInitRetrans             Integer32,
        ptSGM3UAMultiAssociationASPMaximumAssocRetrans              Integer32,
        ptSGM3UAMultiAssociationASPMaximumPathRetrans             Integer32,
        ptSGM3UAMultiAssociationASPBundling   INTEGER,
        ptSGM3UAMultiAssociationASPBundlingTimeout          Integer32,
        ptSGM3UAMultiAssociationASPDelayedAckTimeout            Integer32,
        ptSGM3UAMultiAssociationASPChecksum   INTEGER,
        ptSGM3UAMultiAssociationASPInStreams    Integer32,
        ptSGM3UAMultiAssociationASPOutStreams     Integer32,
        ptSGM3UAMultiAssociationASPM3UAVersion      INTEGER,
        ptSGM3UAMultiAssociationASPHeartbeat    INTEGER,
        ptSGM3UAMultiAssociationASPNATranslation        INTEGER,
        ptSGM3UAMultiAssociationASPDefaultNetworkAppearance                   INTEGER,
        ptSGM3UAMultiAssociationASPNAInDATAMessage          INTEGER,
        ptSGM3UAMultiAssociationASPIMFSupport     INTEGER,
        ptSGM3UAMultiAssociationASPM3UAIndex    Integer32,
        ptSGM3UAMultiAssociationASPM3UAConfiguredASPsIndex                  Integer32,
        ptSGM3UAMultiAssociationASPParentOID    OBJECT IDENTIFIER,
        ptSGM3UAMultiAssociationASPRowStatus    RowStatus,
        ptSGM3UAMultiAssociationASPIndex Integer32
    }

ptSGM3UAMultiAssociationASPID OBJECT-TYPE
    SYNTAX          Integer32 (-2147483648..2147483647)
    MAX-ACCESS      read-only
    STATUS          current
    DESCRIPTION     
            "M3UA Multi Association ASP unique identifier."
    ::= { ptSGM3UAMultiAssociationASPEntry 1 }

ptSGM3UAMultiAssociationASPName OBJECT-TYPE
    SYNTAX          DisplayString (SIZE(0..255))
    MAX-ACCESS      read-create
    STATUS          current
    DESCRIPTION     
            "M3UA configured ASP name. \nAlphanumeric with dash and underscore for a maximum of 16 characters. \nAutomatically moved to upper-case. Must be unique in M3UA. \nReserved value DYNAMIC for non-configured ASPs."
    ::= { ptSGM3UAMultiAssociationASPEntry 2 }

ptSGM3UAMultiAssociationASPASPIDValidation OBJECT-TYPE
    SYNTAX          INTEGER { disabled(0), enabled(1) }
    MAX-ACCESS      read-create
    STATUS          current
    DESCRIPTION     
            "It is highly recommended that for increased security that this attribute remain enabled. When enabled the ASP using the configured endpoint MUST either NOT send the ASP ID parameter OR send the preconfigured ID. If an ASP ID parameter contains an identifier other than what is preconfigured, an ERROR (Invalid ASP Identifier) will be sent. When disabled, the ASP Identifier contained in the ASPUP is not validated. This is typically useful when changing the ID used by the ASP is especially troublesome"
    ::= { ptSGM3UAMultiAssociationASPEntry 3 }

ptSGM3UAMultiAssociationASPIncomingAppID OBJECT-TYPE
    SYNTAX          DisplayString (SIZE(0..255))
    MAX-ACCESS      read-create
    STATUS          current
    DESCRIPTION     
            "M3UA Incoming AppID for Gateway Screening. On creation, the attribute is defaulted to M3UA_DEFAULT."
    ::= { ptSGM3UAMultiAssociationASPEntry 4 }

ptSGM3UAMultiAssociationASPRCInDATAMessage OBJECT-TYPE
    SYNTAX          INTEGER { disabled(0), enabled(1) }
    MAX-ACCESS      read-create
    STATUS          current
    DESCRIPTION     
            "When ENABLED the Routing Context parameter is included in DATA messages destined for the ASP. Per RFC4666, the inclusion of the Routing Context parameter in DATA messages is conditional. On creation, the attribute is defaulted to ENABLED. This setting has no affect when using M3UA Version M3UAv2."
    ::= { ptSGM3UAMultiAssociationASPEntry 5 }

ptSGM3UAMultiAssociationASPSCTPRole OBJECT-TYPE
    SYNTAX          INTEGER { client(0), server(1) }
    MAX-ACCESS      read-only
    STATUS          current
    DESCRIPTION     
            "M3UA Multi Association ASP SCTP Role (CLIENT/SERVER). In a client configuration, each association (once activated) opens its SCTP pipe and tries to connect to the remote end point. In a server configuration, each association (once activated) starts listening for incoming connections on the local end point."
    ::= { ptSGM3UAMultiAssociationASPEntry 6 }

ptSGM3UAMultiAssociationASPASPType OBJECT-TYPE
    SYNTAX          INTEGER { standard(0), c20Core(1), c20Gwc(2) }
    MAX-ACCESS      read-only
    STATUS          current
    DESCRIPTION     
            "Type of ASP."
    ::= { ptSGM3UAMultiAssociationASPEntry 7 }

ptSGM3UAMultiAssociationASPHeartbeatInterval OBJECT-TYPE
    SYNTAX          Integer32 (0..65355)
    MAX-ACCESS      read-create
    STATUS          current
    DESCRIPTION     
            "Heartbeat interval (ms). \nSCTP Association must be de-activated and re-activated to take effect."
    ::= { ptSGM3UAMultiAssociationASPEntry 8 }

ptSGM3UAMultiAssociationASPRTOInitial OBJECT-TYPE
    SYNTAX          Integer32 (0..2147483647)
    MAX-ACCESS      read-create
    STATUS          current
    DESCRIPTION     
            "Initial Retransmission Timeout (ms). \nSCTP Association must be de-activated and re-activated to take effect."
    ::= { ptSGM3UAMultiAssociationASPEntry 9 }

ptSGM3UAMultiAssociationASPRTOMinimum OBJECT-TYPE
    SYNTAX          Integer32 (0..2147483647)
    MAX-ACCESS      read-create
    STATUS          current
    DESCRIPTION     
            "Minimum Retransmission Timeout (ms). \nSCTP Association must be de-activated and re-activated to take effect."
    ::= { ptSGM3UAMultiAssociationASPEntry 10 }

ptSGM3UAMultiAssociationASPRTOMaximum OBJECT-TYPE
    SYNTAX          Integer32 (0..2147483647)
    MAX-ACCESS      read-create
    STATUS          current
    DESCRIPTION     
            "Maximum Retransmission Timeout (ms). \nSCTP Association must be de-activated and re-activated to take effect."
    ::= { ptSGM3UAMultiAssociationASPEntry 11 }

ptSGM3UAMultiAssociationASPMaximumInitRetrans OBJECT-TYPE
    SYNTAX          Integer32 (0..2147483647)
    MAX-ACCESS      read-create
    STATUS          current
    DESCRIPTION     
            "Maximum initial retransmissions. \nSCTP Association must be de-activated and re-activated to take effect."
    ::= { ptSGM3UAMultiAssociationASPEntry 12 }

ptSGM3UAMultiAssociationASPMaximumAssocRetrans OBJECT-TYPE
    SYNTAX          Integer32 (0..2147483647)
    MAX-ACCESS      read-create
    STATUS          current
    DESCRIPTION     
            "Maximum association retransmissions. \nSCTP Association must be de-activated and re-activated to take effect."
    ::= { ptSGM3UAMultiAssociationASPEntry 13 }

ptSGM3UAMultiAssociationASPMaximumPathRetrans OBJECT-TYPE
    SYNTAX          Integer32 (0..2147483647)
    MAX-ACCESS      read-create
    STATUS          current
    DESCRIPTION     
            "Maximum path retransmissions. \nSCTP Association must be de-activated and re-activated to take effect."
    ::= { ptSGM3UAMultiAssociationASPEntry 14 }

ptSGM3UAMultiAssociationASPBundling OBJECT-TYPE
    SYNTAX          INTEGER { disabled(0), enabled(1) }
    MAX-ACCESS      read-create
    STATUS          current
    DESCRIPTION     
            "Enable or disable the Bundling feature. \nSCTP Association must be de-activated and re-activated to take effect."
    ::= { ptSGM3UAMultiAssociationASPEntry 15 }

ptSGM3UAMultiAssociationASPBundlingTimeout OBJECT-TYPE
    SYNTAX          Integer32 (0..2147483647)
    MAX-ACCESS      read-create
    STATUS          current
    DESCRIPTION     
            "Bundling timeout (msecs). \nSCTP Association must be de-activated and re-activated to take effect."
    ::= { ptSGM3UAMultiAssociationASPEntry 16 }

ptSGM3UAMultiAssociationASPDelayedAckTimeout OBJECT-TYPE
    SYNTAX          Integer32 (0..500)
    MAX-ACCESS      read-create
    STATUS          current
    DESCRIPTION     
            "Delayed acknowledgement timeout. \nSCTP Association must be de-activated and re-activated to take effect."
    ::= { ptSGM3UAMultiAssociationASPEntry 17 }

ptSGM3UAMultiAssociationASPChecksum OBJECT-TYPE
    SYNTAX          INTEGER { adler32(0), crc32c(1), none(2) }
    MAX-ACCESS      read-only
    STATUS          current
    DESCRIPTION     
            "Checksum algorithm. \nSCTP Association must be de-activated and re-activated to take effect."
    ::= { ptSGM3UAMultiAssociationASPEntry 18 }

ptSGM3UAMultiAssociationASPInStreams OBJECT-TYPE
    SYNTAX          Integer32 (0..65355)
    MAX-ACCESS      read-create
    STATUS          current
    DESCRIPTION     
            "Number of in streams. \nSCTP Association must be de-activated and re-activated to take effect."
    ::= { ptSGM3UAMultiAssociationASPEntry 19 }

ptSGM3UAMultiAssociationASPOutStreams OBJECT-TYPE
    SYNTAX          Integer32 (0..65355)
    MAX-ACCESS      read-create
    STATUS          current
    DESCRIPTION     
            "Number of out streams. \nSCTP Association must be de-activated and re-activated to take effect."
    ::= { ptSGM3UAMultiAssociationASPEntry 20 }

ptSGM3UAMultiAssociationASPM3UAVersion OBJECT-TYPE
    SYNTAX          INTEGER { m3uaVrfc(0), m3uaV2(1) }
    MAX-ACCESS      read-only
    STATUS          current
    DESCRIPTION     
            "M3UA Multi Association ASP M3UA Version (M3UAvRFC/M3UAv2). On Creation, this attribute is defaulted to M3UAvRFC"
    ::= { ptSGM3UAMultiAssociationASPEntry 21 }

ptSGM3UAMultiAssociationASPHeartbeat OBJECT-TYPE
    SYNTAX          INTEGER { disabled(0), enabled(1) }
    MAX-ACCESS      read-create
    STATUS          current
    DESCRIPTION     
            "Enable or disable the Heartbeat feature. \nSCTP Association must be de-activated and re-activated to take effect."
    ::= { ptSGM3UAMultiAssociationASPEntry 22 }

ptSGM3UAMultiAssociationASPNATranslation OBJECT-TYPE
    SYNTAX          INTEGER { disabled(0) }
    MAX-ACCESS      read-create
    STATUS          current
    DESCRIPTION     
            "NA Translation for M3UA Multi Association ASPs. If enabled, all M3UA messages from the ASP containing a Network Appearance parameter of 0 will be interpreted to mean the configured value chosen. This value will be used for pertinent statistics. A default value of 0 disables the feature."
    ::= { ptSGM3UAMultiAssociationASPEntry 23 }

ptSGM3UAMultiAssociationASPDefaultNetworkAppearance OBJECT-TYPE
    SYNTAX          INTEGER { unset(-1) }
    MAX-ACCESS      read-create
    STATUS          current
    DESCRIPTION     
            "Upon receipt of an M3UA message which does not contain a Routing Context or Network Appearance parameter, the SG uses this value to determine the destination SS7 network. If this value is UNSET (-1), the Default Network Appearance specified in the M3UA SCTP Servers is used to determine the destination SS7 network. The Network Appearance must also be configured as an MTP3 NA. The default value is UNSET. \nChanging this attribute value can impact traffic."
    ::= { ptSGM3UAMultiAssociationASPEntry 24 }

ptSGM3UAMultiAssociationASPNAInDATAMessage OBJECT-TYPE
    SYNTAX          INTEGER { disabled(0), enabled(1) }
    MAX-ACCESS      read-create
    STATUS          current
    DESCRIPTION     
            "When ENABLED the Network Appearance parameter is included in DATA messages destined for the ASP. Per RFC4666, the inclusion of the Network Appearance parameter in DATA messages is optional. On creation, the attribute is defaulted to ENABLED. This setting has no affect when using M3UA Version M3UAv2."
    ::= { ptSGM3UAMultiAssociationASPEntry 25 }

ptSGM3UAMultiAssociationASPIMFSupport OBJECT-TYPE
    SYNTAX          INTEGER { disabled(0), enabled(1) }
    MAX-ACCESS      read-create
    STATUS          current
    DESCRIPTION     
            "Integrated Monitoring Feed feature support for this ASP. \nIMF must be licensed to enable this attribute. IMF Support attributes can be cleared for all configured M3UA ASPs simultaneously by using the Reset IMF action in the M3UA Configured ASPs screen."
    ::= { ptSGM3UAMultiAssociationASPEntry 45 }

ptSGM3UAMultiAssociationASPM3UAIndex OBJECT-TYPE
    SYNTAX          Integer32 (-2147483648..2147483647)
    MAX-ACCESS      not-accessible
    STATUS          current
    DESCRIPTION     
            "This is the index of the parent type for this object.
             This parent type is M3UA."
    ::= { ptSGM3UAMultiAssociationASPEntry 242 }

ptSGM3UAMultiAssociationASPM3UAConfiguredASPsIndex OBJECT-TYPE
    SYNTAX          Integer32 (-2147483648..2147483647)
    MAX-ACCESS      not-accessible
    STATUS          current
    DESCRIPTION     
            "This is the index of the parent type for this object.
             This parent type is M3UAConfiguredASPs."
    ::= { ptSGM3UAMultiAssociationASPEntry 243 }

ptSGM3UAMultiAssociationASPParentOID OBJECT-TYPE
    SYNTAX          OBJECT IDENTIFIER
    MAX-ACCESS      read-create
    STATUS          current
    DESCRIPTION     
            "The OID of the parent object for this instance"
    ::= { ptSGM3UAMultiAssociationASPEntry 253 }

ptSGM3UAMultiAssociationASPRowStatus OBJECT-TYPE
    SYNTAX          RowStatus
    MAX-ACCESS      read-create
    STATUS          current
    DESCRIPTION     
            "The row status for the SGM3UAMultiAssociationASP table"
    ::= { ptSGM3UAMultiAssociationASPEntry 254 }

ptSGM3UAMultiAssociationASPIndex OBJECT-TYPE
    SYNTAX          Integer32 (-2147483648..2147483647)
    MAX-ACCESS      not-accessible
    STATUS          current
    DESCRIPTION     
            "The row number for the SGM3UAMultiAssociationASP table"
    ::= { ptSGM3UAMultiAssociationASPEntry 255 }

ptSGM3UAASPAssociation OBJECT IDENTIFIER
    ::= { ptSGM3UAMultiAssociationASP 190 }

ptSGM3UAASPAssociationTable OBJECT-TYPE
    SYNTAX          SEQUENCE OF PtSGM3UAASPAssociationEntry
    MAX-ACCESS      not-accessible
    STATUS          current
    DESCRIPTION     
            "No description supplied in the proxy config file."
    ::= { ptSGM3UAASPAssociation 1 }

ptSGM3UAASPAssociationEntry OBJECT-TYPE
    SYNTAX          PtSGM3UAASPAssociationEntry
    MAX-ACCESS      not-accessible
    STATUS          current
    DESCRIPTION     
            "A sequence of SGM3UAASPAssociation attributes."
    INDEX           { ptConnGroupIndex, ptSGM3UAASPAssociationM3UAIndex, 
                      ptSGM3UAASPAssociationM3UAConfiguredASPsIndex, 
                      ptSGM3UAASPAssociationM3UAMultiAssociationASPIndex, 
                      ptSGM3UAASPAssociationIndex }
    ::= { ptSGM3UAASPAssociationTable 1 }

PtSGM3UAASPAssociationEntry ::=
    SEQUENCE {
        ptSGM3UAASPAssociationAssociationID   Integer32,
        ptSGM3UAASPAssociationSlot      Integer32,
        ptSGM3UAASPAssociationRemoteIPAddress1      DisplayString,
        ptSGM3UAASPAssociationRemoteIPAddress2      DisplayString,
        ptSGM3UAASPAssociationRemotePort Integer32,
        ptSGM3UAASPAssociationLocalIPAddress1     DisplayString,
        ptSGM3UAASPAssociationLocalIPAddress2     DisplayString,
        ptSGM3UAASPAssociationLocalPort Integer32,
        ptSGM3UAASPAssociationUserActivated   INTEGER,
        ptSGM3UAASPAssociationSCTPState INTEGER,
        ptSGM3UAASPAssociationM3UAState INTEGER,
        ptSGM3UAASPAssociationRxMSGCount Integer32,
        ptSGM3UAASPAssociationTxMSGCount Integer32,
        ptSGM3UAASPAssociationM3UAIndex Integer32,
        ptSGM3UAASPAssociationM3UAConfiguredASPsIndex             Integer32,
        ptSGM3UAASPAssociationM3UAMultiAssociationASPIndex                  Integer32,
        ptSGM3UAASPAssociationActions   INTEGER,
        ptSGM3UAASPAssociationParentOID OBJECT IDENTIFIER,
        ptSGM3UAASPAssociationRowStatus RowStatus,
        ptSGM3UAASPAssociationIndex     Integer32
    }

ptSGM3UAASPAssociationAssociationID OBJECT-TYPE
    SYNTAX          Integer32 (-2147483648..2147483647)
    MAX-ACCESS      read-only
    STATUS          current
    DESCRIPTION     
            "M3UA ASP Association unique identifier."
    ::= { ptSGM3UAASPAssociationEntry 1 }

ptSGM3UAASPAssociationSlot OBJECT-TYPE
    SYNTAX          Integer32 (-2147483648..2147483647)
    MAX-ACCESS      read-only
    STATUS          current
    DESCRIPTION     
            "M3UA ASP Association corresponding slot."
    ::= { ptSGM3UAASPAssociationEntry 2 }

ptSGM3UAASPAssociationRemoteIPAddress1 OBJECT-TYPE
    SYNTAX          DisplayString (SIZE(0..255))
    MAX-ACCESS      read-only
    STATUS          current
    DESCRIPTION     
            "M3UA ASP Association primary remote address. This may be a hostname or an IP Address. If a hostname is used it must be provisioned either in /etc/hosts or via a properly-configured DNS Server and should resolve to a subset of the remote IP Addresses configured for the host where the ASP terminates. Hostname resolution is attempted periodically. This attribute defines the primary IP address specifying the SCTP primary path to the remote SCTP endpoint. If the resolution returns more than one IP address, no guarantee is made as to non-ambiguous definition of the SCTP primary path."
    ::= { ptSGM3UAASPAssociationEntry 3 }

ptSGM3UAASPAssociationRemoteIPAddress2 OBJECT-TYPE
    SYNTAX          DisplayString (SIZE(0..255))
    MAX-ACCESS      read-only
    STATUS          current
    DESCRIPTION     
            "M3UA ASP Association secondary remote address. This may be a hostname or an IP Address. If a hostname is used it must be provisioned either in /etc/hosts or via a properly-configured DNS Server and should resolve to a subset of the remote IP Addresses configured for the host where the ASP terminates. Hostname resolution is attempted periodically."
    ::= { ptSGM3UAASPAssociationEntry 4 }

ptSGM3UAASPAssociationRemotePort OBJECT-TYPE
    SYNTAX          Integer32 (-2147483648..2147483647)
    MAX-ACCESS      read-only
    STATUS          current
    DESCRIPTION     
            "Remote port from/to which ASP Association will connect."
    ::= { ptSGM3UAASPAssociationEntry 5 }

ptSGM3UAASPAssociationLocalIPAddress1 OBJECT-TYPE
    SYNTAX          DisplayString (SIZE(0..255))
    MAX-ACCESS      read-only
    STATUS          current
    DESCRIPTION     
            "M3UA ASP Association primary local address. This may be a hostname or an IP Address. If a hostname is used it must be provisioned either in /etc/hosts or via a properly-configured DNS Server and should resolve to a subset of the local IP Addresses configured for the slot where the ASP terminates. Hostname resolution is attempted periodically."
    ::= { ptSGM3UAASPAssociationEntry 6 }

ptSGM3UAASPAssociationLocalIPAddress2 OBJECT-TYPE
    SYNTAX          DisplayString (SIZE(0..255))
    MAX-ACCESS      read-only
    STATUS          current
    DESCRIPTION     
            "M3UA ASP Association secondary local address. This may be a hostname or an IP Address. If a hostname is used it must be provisioned either in /etc/hosts or via a properly-configured DNS Server and should resolve to a subset of the local IP Addresses configured for the slot where the ASP terminates. Hostname resolution is attempted periodically."
    ::= { ptSGM3UAASPAssociationEntry 7 }

ptSGM3UAASPAssociationLocalPort OBJECT-TYPE
    SYNTAX          Integer32 (-2147483648..2147483647)
    MAX-ACCESS      read-only
    STATUS          current
    DESCRIPTION     
            "Local port from/to which ASP Association will connect."
    ::= { ptSGM3UAASPAssociationEntry 8 }

ptSGM3UAASPAssociationUserActivated OBJECT-TYPE
    SYNTAX          INTEGER { disabled(0), enabled(1) }
    MAX-ACCESS      read-only
    STATUS          current
    DESCRIPTION     
            "M3UA ASP Association User State (ENABLED/DISABLED)."
    ::= { ptSGM3UAASPAssociationEntry 9 }

ptSGM3UAASPAssociationSCTPState OBJECT-TYPE
    SYNTAX          INTEGER { down(0), up(1) }
    MAX-ACCESS      read-only
    STATUS          current
    DESCRIPTION     
            "M3UA ASP Association SCTP State (UP/DOWN)."
    ::= { ptSGM3UAASPAssociationEntry 10 }

ptSGM3UAASPAssociationM3UAState OBJECT-TYPE
    SYNTAX          INTEGER { down(0), up(1) }
    MAX-ACCESS      read-only
    STATUS          current
    DESCRIPTION     
            "M3UA ASP Association M3UA State (UP/DOWN)."
    ::= { ptSGM3UAASPAssociationEntry 11 }

ptSGM3UAASPAssociationRxMSGCount OBJECT-TYPE
    SYNTAX          Integer32 (-2147483648..2147483647)
    MAX-ACCESS      read-only
    STATUS          current
    DESCRIPTION     
            "Number Received Messages per second"
    ::= { ptSGM3UAASPAssociationEntry 12 }

ptSGM3UAASPAssociationTxMSGCount OBJECT-TYPE
    SYNTAX          Integer32 (-2147483648..2147483647)
    MAX-ACCESS      read-only
    STATUS          current
    DESCRIPTION     
            "Number Transmitted Messages per second"
    ::= { ptSGM3UAASPAssociationEntry 13 }

ptSGM3UAASPAssociationM3UAIndex OBJECT-TYPE
    SYNTAX          Integer32 (-2147483648..2147483647)
    MAX-ACCESS      not-accessible
    STATUS          current
    DESCRIPTION     
            "This is the index of the parent type for this object.
             This parent type is M3UA."
    ::= { ptSGM3UAASPAssociationEntry 242 }

ptSGM3UAASPAssociationM3UAConfiguredASPsIndex OBJECT-TYPE
    SYNTAX          Integer32 (-2147483648..2147483647)
    MAX-ACCESS      not-accessible
    STATUS          current
    DESCRIPTION     
            "This is the index of the parent type for this object.
             This parent type is M3UAConfiguredASPs."
    ::= { ptSGM3UAASPAssociationEntry 243 }

ptSGM3UAASPAssociationM3UAMultiAssociationASPIndex OBJECT-TYPE
    SYNTAX          Integer32 (-2147483648..2147483647)
    MAX-ACCESS      not-accessible
    STATUS          current
    DESCRIPTION     
            "This is the index of the parent type for this object.
             This parent type is M3UAMultiAssociationASP."
    ::= { ptSGM3UAASPAssociationEntry 244 }

ptSGM3UAASPAssociationActions OBJECT-TYPE
    SYNTAX          INTEGER { activate(1), deactivate(2), shutdown(3) }
    MAX-ACCESS      read-create
    STATUS          current
    DESCRIPTION     
            "The OID of all possible actions for this instance"
    ::= { ptSGM3UAASPAssociationEntry 252 }

ptSGM3UAASPAssociationParentOID OBJECT-TYPE
    SYNTAX          OBJECT IDENTIFIER
    MAX-ACCESS      read-create
    STATUS          current
    DESCRIPTION     
            "The OID of the parent object for this instance"
    ::= { ptSGM3UAASPAssociationEntry 253 }

ptSGM3UAASPAssociationRowStatus OBJECT-TYPE
    SYNTAX          RowStatus
    MAX-ACCESS      read-create
    STATUS          current
    DESCRIPTION     
            "The row status for the SGM3UAASPAssociation table"
    ::= { ptSGM3UAASPAssociationEntry 254 }

ptSGM3UAASPAssociationIndex OBJECT-TYPE
    SYNTAX          Integer32 (-2147483648..2147483647)
    MAX-ACCESS      not-accessible
    STATUS          current
    DESCRIPTION     
            "The row number for the SGM3UAASPAssociation table"
    ::= { ptSGM3UAASPAssociationEntry 255 }

ptSGM3UAMultiAssociationRC OBJECT IDENTIFIER
    ::= { ptSGM3UAMultiAssociationASP 192 }

ptSGM3UAMultiAssociationRCTable OBJECT-TYPE
    SYNTAX          SEQUENCE OF PtSGM3UAMultiAssociationRCEntry
    MAX-ACCESS      not-accessible
    STATUS          current
    DESCRIPTION     
            "No description supplied in the proxy config file."
    ::= { ptSGM3UAMultiAssociationRC 1 }

ptSGM3UAMultiAssociationRCEntry OBJECT-TYPE
    SYNTAX          PtSGM3UAMultiAssociationRCEntry
    MAX-ACCESS      not-accessible
    STATUS          current
    DESCRIPTION     
            "A sequence of SGM3UAMultiAssociationRC attributes."
    INDEX           { ptConnGroupIndex, 
                      ptSGM3UAMultiAssociationRCM3UAIndex, 
                      ptSGM3UAMultiAssociationRCM3UAConfiguredASPsIndex, 
                      ptSGM3UAMultiAssociationRCM3UAMultiAssociationASPIndex, 
                      ptSGM3UAMultiAssociationRCIndex }
    ::= { ptSGM3UAMultiAssociationRCTable 1 }

PtSGM3UAMultiAssociationRCEntry ::=
    SEQUENCE {
        ptSGM3UAMultiAssociationRCRoutingContext        Integer32,
        ptSGM3UAMultiAssociationRCRemoteRoutingContext              INTEGER,
        ptSGM3UAMultiAssociationRCM3UAIndex   Integer32,
        ptSGM3UAMultiAssociationRCM3UAConfiguredASPsIndex                 Integer32,
        ptSGM3UAMultiAssociationRCM3UAMultiAssociationASPIndex                      Integer32,
        ptSGM3UAMultiAssociationRCParentOID   OBJECT IDENTIFIER,
        ptSGM3UAMultiAssociationRCRowStatus   RowStatus,
        ptSGM3UAMultiAssociationRCIndex Integer32
    }

ptSGM3UAMultiAssociationRCRoutingContext OBJECT-TYPE
    SYNTAX          Integer32 (1..2147483647)
    MAX-ACCESS      read-only
    STATUS          current
    DESCRIPTION     
            "Routing context."
    ::= { ptSGM3UAMultiAssociationRCEntry 1 }

ptSGM3UAMultiAssociationRCRemoteRoutingContext OBJECT-TYPE
    SYNTAX          INTEGER { undefined(-1) }
    MAX-ACCESS      read-create
    STATUS          current
    DESCRIPTION     
            "Remote routing context is used to connect a group of configured RCs. An ASP may go active for the group of RCs by sending a single ASP Active message containing only the remote routing context. All notifications and Acks pertaining to any AS in the group will contain the remote routing context. This feature should only be used when the ASP must send a single Routing Context but it needs register for more than one routing key. It can also be used in the case where a routing context is already configured for an AS and the ASP sends a different RC in the ASPAC message. To set the value to UNDEFINED, enter -1."
    ::= { ptSGM3UAMultiAssociationRCEntry 2 }

ptSGM3UAMultiAssociationRCM3UAIndex OBJECT-TYPE
    SYNTAX          Integer32 (-2147483648..2147483647)
    MAX-ACCESS      not-accessible
    STATUS          current
    DESCRIPTION     
            "This is the index of the parent type for this object.
             This parent type is M3UA."
    ::= { ptSGM3UAMultiAssociationRCEntry 242 }

ptSGM3UAMultiAssociationRCM3UAConfiguredASPsIndex OBJECT-TYPE
    SYNTAX          Integer32 (-2147483648..2147483647)
    MAX-ACCESS      not-accessible
    STATUS          current
    DESCRIPTION     
            "This is the index of the parent type for this object.
             This parent type is M3UAConfiguredASPs."
    ::= { ptSGM3UAMultiAssociationRCEntry 243 }

ptSGM3UAMultiAssociationRCM3UAMultiAssociationASPIndex OBJECT-TYPE
    SYNTAX          Integer32 (-2147483648..2147483647)
    MAX-ACCESS      not-accessible
    STATUS          current
    DESCRIPTION     
            "This is the index of the parent type for this object.
             This parent type is M3UAMultiAssociationASP."
    ::= { ptSGM3UAMultiAssociationRCEntry 244 }

ptSGM3UAMultiAssociationRCParentOID OBJECT-TYPE
    SYNTAX          OBJECT IDENTIFIER
    MAX-ACCESS      read-create
    STATUS          current
    DESCRIPTION     
            "The OID of the parent object for this instance"
    ::= { ptSGM3UAMultiAssociationRCEntry 253 }

ptSGM3UAMultiAssociationRCRowStatus OBJECT-TYPE
    SYNTAX          RowStatus
    MAX-ACCESS      read-create
    STATUS          current
    DESCRIPTION     
            "The row status for the SGM3UAMultiAssociationRC table"
    ::= { ptSGM3UAMultiAssociationRCEntry 254 }

ptSGM3UAMultiAssociationRCIndex OBJECT-TYPE
    SYNTAX          Integer32 (-2147483648..2147483647)
    MAX-ACCESS      not-accessible
    STATUS          current
    DESCRIPTION     
            "The row number for the SGM3UAMultiAssociationRC table"
    ::= { ptSGM3UAMultiAssociationRCEntry 255 }

ptSGSUA OBJECT IDENTIFIER
    ::= { ptConnGroup 200 }

ptSGSUATable OBJECT-TYPE
    SYNTAX          SEQUENCE OF PtSGSUAEntry
    MAX-ACCESS      not-accessible
    STATUS          current
    DESCRIPTION     
            "No description supplied in the proxy config file."
    ::= { ptSGSUA 1 }

ptSGSUAEntry OBJECT-TYPE
    SYNTAX          PtSGSUAEntry
    MAX-ACCESS      not-accessible
    STATUS          current
    DESCRIPTION     
            "A sequence of SGSUA attributes."
    INDEX           { ptConnGroupIndex, ptSGSUAIndex }
    ::= { ptSGSUATable 1 }

PtSGSUAEntry ::=
    SEQUENCE {
        ptSGSUAPendingTimer             INTEGER,
        ptSGSUAMonitoring               INTEGER,
        ptSGSUAAssociationCapacity      Integer32,
        ptSGSUAHighUsageOnset           INTEGER,
        ptSGSUAHighUsageAbatement       INTEGER,
        ptSGSUAUsageIntervalSeconds     Integer32,
        ptSGSUAConnectionEstablished    INTEGER,
        ptSGSUAInactivitySend           INTEGER,
        ptSGSUAInactivityReceive        INTEGER,
        ptSGSUARelease                  INTEGER,
        ptSGSUARepeatRelease            INTEGER,
        ptSGSUASRNFreeze                INTEGER,
        ptSGSUAIMFSupport               INTEGER,
        ptSGSUASCTPProtocolIDValidation INTEGER,
        ptSGSUAActions                  INTEGER,
        ptSGSUAParentOID                OBJECT IDENTIFIER,
        ptSGSUARowStatus                RowStatus,
        ptSGSUAIndex                    Integer32
    }

ptSGSUAPendingTimer OBJECT-TYPE
    SYNTAX          INTEGER { disabled(0) }
    MAX-ACCESS      read-create
    STATUS          current
    DESCRIPTION     
            "Duration of PENDING state in msecs for an SUA AS. Pending timer is started when an AS transitions out of ACTIVE state. \nIf an ASP sends an ASPAC before the timer expires, the AS will immediately transition back to the ACTIVE status. Otherwise, when the timer expires the AS will either transition to INACTIVE or DOWN state. \nMessages will be queued while in PENDING state. \nValid range of this timer is 1 to 2000. \nTo disable the timer, set to 0. \nDefault value is 2000 msecs."
    ::= { ptSGSUAEntry 2 }

ptSGSUAMonitoring OBJECT-TYPE
    SYNTAX          INTEGER { disabled(0), enabled(1) }
    MAX-ACCESS      read-only
    STATUS          current
    DESCRIPTION     
            "Monitoring feature (ENABLED/DISABLED)."
    ::= { ptSGSUAEntry 3 }

ptSGSUAAssociationCapacity OBJECT-TYPE
    SYNTAX          Integer32 (0..2147483647)
    MAX-ACCESS      read-create
    STATUS          current
    DESCRIPTION     
            "Maximum number of bytes per second sent on a AS association."
    ::= { ptSGSUAEntry 4 }

ptSGSUAHighUsageOnset OBJECT-TYPE
    SYNTAX          INTEGER { default(-1) }
    MAX-ACCESS      read-create
    STATUS          current
    DESCRIPTION     
            "Traffic level at which high usage alarms are triggered. (% of association capacity).\n This setting is used for both the transmit and receive high usage alarms for SCTP associations used by SUA ASPs.\n The alarm is automatically cleared when traffic levels fall below the High Usage Abatement setting."
    ::= { ptSGSUAEntry 5 }

ptSGSUAHighUsageAbatement OBJECT-TYPE
    SYNTAX          INTEGER { default(-1) }
    MAX-ACCESS      read-create
    STATUS          current
    DESCRIPTION     
            "Traffic level at which high usage alarms are cleared. (% of association capacity).\n This setting is used for both the transmit and receive high usage alarms for SCTP associations used by SUA ASPs."
    ::= { ptSGSUAEntry 6 }

ptSGSUAUsageIntervalSeconds OBJECT-TYPE
    SYNTAX          Integer32 (-2147483648..2147483647)
    MAX-ACCESS      read-only
    STATUS          current
    DESCRIPTION     
            "Interval in seconds used to calculate average traffic load."
    ::= { ptSGSUAEntry 8 }

ptSGSUAConnectionEstablished OBJECT-TYPE
    SYNTAX          INTEGER { disabled(0) }
    MAX-ACCESS      read-create
    STATUS          current
    DESCRIPTION     
            "Connection establish timer."
    ::= { ptSGSUAEntry 9 }

ptSGSUAInactivitySend OBJECT-TYPE
    SYNTAX          INTEGER { disabled(0) }
    MAX-ACCESS      read-create
    STATUS          current
    DESCRIPTION     
            "Inactivity send timer."
    ::= { ptSGSUAEntry 10 }

ptSGSUAInactivityReceive OBJECT-TYPE
    SYNTAX          INTEGER { disabled(0) }
    MAX-ACCESS      read-create
    STATUS          current
    DESCRIPTION     
            "Inactivity receive timer."
    ::= { ptSGSUAEntry 11 }

ptSGSUARelease OBJECT-TYPE
    SYNTAX          INTEGER { disabled(0) }
    MAX-ACCESS      read-create
    STATUS          current
    DESCRIPTION     
            "Release timer."
    ::= { ptSGSUAEntry 12 }

ptSGSUARepeatRelease OBJECT-TYPE
    SYNTAX          INTEGER { disabled(0) }
    MAX-ACCESS      read-create
    STATUS          current
    DESCRIPTION     
            "Repeat release timer."
    ::= { ptSGSUAEntry 13 }

ptSGSUASRNFreeze OBJECT-TYPE
    SYNTAX          INTEGER { disabled(0) }
    MAX-ACCESS      read-create
    STATUS          current
    DESCRIPTION     
            "SRN freeze timer."
    ::= { ptSGSUAEntry 14 }

ptSGSUAIMFSupport OBJECT-TYPE
    SYNTAX          INTEGER { disabled(0), enabled(1) }
    MAX-ACCESS      read-create
    STATUS          current
    DESCRIPTION     
            "Integrated Monitoring Feed feature support for SUA. \nIMF must be licensed to enable this attribute."
    ::= { ptSGSUAEntry 15 }

ptSGSUASCTPProtocolIDValidation OBJECT-TYPE
    SYNTAX          INTEGER { disabled(0), enabled(1) }
    MAX-ACCESS      read-create
    STATUS          current
    DESCRIPTION     
            "Validation of protocol ID of received data. \nWhen enabled, the SG will discard all SUA messages that do not have an SCTP Protocol ID of either 0 or 4 as described in RFC 3868. \nWhen disabled, the SG will not inspect the SCTP protocol ID and accept all SUA messages."
    ::= { ptSGSUAEntry 16 }

ptSGSUAActions OBJECT-TYPE
    SYNTAX          INTEGER { startMonitoring(1), stopMonitoring(2) }
    MAX-ACCESS      read-create
    STATUS          current
    DESCRIPTION     
            "The OID of all possible actions for this instance"
    ::= { ptSGSUAEntry 252 }

ptSGSUAParentOID OBJECT-TYPE
    SYNTAX          OBJECT IDENTIFIER
    MAX-ACCESS      read-create
    STATUS          current
    DESCRIPTION     
            "The OID of the parent object for this instance"
    ::= { ptSGSUAEntry 253 }

ptSGSUARowStatus OBJECT-TYPE
    SYNTAX          RowStatus
    MAX-ACCESS      read-create
    STATUS          current
    DESCRIPTION     
            "The row status for the SGSUA table"
    ::= { ptSGSUAEntry 254 }

ptSGSUAIndex OBJECT-TYPE
    SYNTAX          Integer32 (-2147483648..2147483647)
    MAX-ACCESS      not-accessible
    STATUS          current
    DESCRIPTION     
            "The row number for the SGSUA table"
    ::= { ptSGSUAEntry 255 }

ptSGSUAAppServers OBJECT IDENTIFIER
    ::= { ptSGSUA 201 }

ptSGSUAAppServersTable OBJECT-TYPE
    SYNTAX          SEQUENCE OF PtSGSUAAppServersEntry
    MAX-ACCESS      not-accessible
    STATUS          current
    DESCRIPTION     
            "No description supplied in the proxy config file."
    ::= { ptSGSUAAppServers 1 }

ptSGSUAAppServersEntry OBJECT-TYPE
    SYNTAX          PtSGSUAAppServersEntry
    MAX-ACCESS      not-accessible
    STATUS          current
    DESCRIPTION     
            "A sequence of SGSUAAppServers attributes."
    INDEX           { ptConnGroupIndex, ptSGSUAAppServersSUAIndex, 
                      ptSGSUAAppServersIndex }
    ::= { ptSGSUAAppServersTable 1 }

PtSGSUAAppServersEntry ::=
    SEQUENCE {
        ptSGSUAAppServersSUAIndex       Integer32,
        ptSGSUAAppServersParentOID      OBJECT IDENTIFIER,
        ptSGSUAAppServersRowStatus      RowStatus,
        ptSGSUAAppServersIndex          Integer32
    }

ptSGSUAAppServersSUAIndex OBJECT-TYPE
    SYNTAX          Integer32 (-2147483648..2147483647)
    MAX-ACCESS      not-accessible
    STATUS          current
    DESCRIPTION     
            "This is the index of the parent type for this object.
             This parent type is SUA."
    ::= { ptSGSUAAppServersEntry 242 }

ptSGSUAAppServersParentOID OBJECT-TYPE
    SYNTAX          OBJECT IDENTIFIER
    MAX-ACCESS      read-create
    STATUS          current
    DESCRIPTION     
            "The OID of the parent object for this instance"
    ::= { ptSGSUAAppServersEntry 253 }

ptSGSUAAppServersRowStatus OBJECT-TYPE
    SYNTAX          RowStatus
    MAX-ACCESS      read-create
    STATUS          current
    DESCRIPTION     
            "The row status for the SGSUAAppServers table"
    ::= { ptSGSUAAppServersEntry 254 }

ptSGSUAAppServersIndex OBJECT-TYPE
    SYNTAX          Integer32 (-2147483648..2147483647)
    MAX-ACCESS      not-accessible
    STATUS          current
    DESCRIPTION     
            "The row number for the SGSUAAppServers table"
    ::= { ptSGSUAAppServersEntry 255 }

ptSGSUAAppServer OBJECT IDENTIFIER
    ::= { ptSGSUAAppServers 202 }

ptSGSUAAppServerTable OBJECT-TYPE
    SYNTAX          SEQUENCE OF PtSGSUAAppServerEntry
    MAX-ACCESS      not-accessible
    STATUS          current
    DESCRIPTION     
            "No description supplied in the proxy config file."
    ::= { ptSGSUAAppServer 1 }

ptSGSUAAppServerEntry OBJECT-TYPE
    SYNTAX          PtSGSUAAppServerEntry
    MAX-ACCESS      not-accessible
    STATUS          current
    DESCRIPTION     
            "A sequence of SGSUAAppServer attributes."
    INDEX           { ptConnGroupIndex, ptSGSUAAppServerSUAIndex, 
                      ptSGSUAAppServerSUAAppServersIndex, 
                      ptSGSUAAppServerIndex }
    ::= { ptSGSUAAppServerTable 1 }

PtSGSUAAppServerEntry ::=
    SEQUENCE {
        ptSGSUAAppServerStatus          INTEGER,
        ptSGSUAAppServerRoutingContext  Integer32,
        ptSGSUAAppServerDPC             Integer32,
        ptSGSUAAppServerSSN             Integer32,
        ptSGSUAAppServerNetworkAppearance Integer32,
        ptSGSUAAppServerTrafficMode     INTEGER,
        ptSGSUAAppServerApplicationID   DisplayString,
        ptSGSUAAppServerSUAIndex        Integer32,
        ptSGSUAAppServerSUAAppServersIndex  Integer32,
        ptSGSUAAppServerParentOID       OBJECT IDENTIFIER,
        ptSGSUAAppServerRowStatus       RowStatus,
        ptSGSUAAppServerIndex           Integer32
    }

ptSGSUAAppServerStatus OBJECT-TYPE
    SYNTAX          INTEGER { active(0), inactive(1), pendingReg(2), 
                        down(3), offLine(4), pending(5) }
    MAX-ACCESS      read-only
    STATUS          current
    DESCRIPTION     
            "SUA AS Status."
    ::= { ptSGSUAAppServerEntry 1 }

ptSGSUAAppServerRoutingContext OBJECT-TYPE
    SYNTAX          Integer32 (1..2147483647)
    MAX-ACCESS      read-only
    STATUS          current
    DESCRIPTION     
            "SUA AS Routing context."
    ::= { ptSGSUAAppServerEntry 2 }

ptSGSUAAppServerDPC OBJECT-TYPE
    SYNTAX          Integer32 (-2147483648..2147483647)
    MAX-ACCESS      read-only
    STATUS          current
    DESCRIPTION     
            "Point Codes are set to UNSET when routing on Application ID is configured"
    ::= { ptSGSUAAppServerEntry 3 }

ptSGSUAAppServerSSN OBJECT-TYPE
    SYNTAX          Integer32 (-2147483648..2147483647)
    MAX-ACCESS      read-only
    STATUS          current
    DESCRIPTION     
            "SSNs are set to 0 when routing on Application ID is configured"
    ::= { ptSGSUAAppServerEntry 4 }

ptSGSUAAppServerNetworkAppearance OBJECT-TYPE
    SYNTAX          Integer32 (-2147483648..2147483647)
    MAX-ACCESS      read-only
    STATUS          current
    DESCRIPTION     
            "SUA AS Network appearance."
    ::= { ptSGSUAAppServerEntry 5 }

ptSGSUAAppServerTrafficMode OBJECT-TYPE
    SYNTAX          INTEGER { override(0), loadshare(1), broadcast(2) }
    MAX-ACCESS      read-only
    STATUS          current
    DESCRIPTION     
            "SUA Application Server Traffic Mode. Traffic modes, override, loadshare and broadcast are supported."
    ::= { ptSGSUAAppServerEntry 6 }

ptSGSUAAppServerApplicationID OBJECT-TYPE
    SYNTAX          DisplayString (SIZE(0..255))
    MAX-ACCESS      read-only
    STATUS          current
    DESCRIPTION     
            "SUA AS Application ID (optional)."
    ::= { ptSGSUAAppServerEntry 9 }

ptSGSUAAppServerSUAIndex OBJECT-TYPE
    SYNTAX          Integer32 (-2147483648..2147483647)
    MAX-ACCESS      not-accessible
    STATUS          current
    DESCRIPTION     
            "This is the index of the parent type for this object.
             This parent type is SUA."
    ::= { ptSGSUAAppServerEntry 242 }

ptSGSUAAppServerSUAAppServersIndex OBJECT-TYPE
    SYNTAX          Integer32 (-2147483648..2147483647)
    MAX-ACCESS      not-accessible
    STATUS          current
    DESCRIPTION     
            "This is the index of the parent type for this object.
             This parent type is SUAAppServers."
    ::= { ptSGSUAAppServerEntry 243 }

ptSGSUAAppServerParentOID OBJECT-TYPE
    SYNTAX          OBJECT IDENTIFIER
    MAX-ACCESS      read-create
    STATUS          current
    DESCRIPTION     
            "The OID of the parent object for this instance"
    ::= { ptSGSUAAppServerEntry 253 }

ptSGSUAAppServerRowStatus OBJECT-TYPE
    SYNTAX          RowStatus
    MAX-ACCESS      read-create
    STATUS          current
    DESCRIPTION     
            "The row status for the SGSUAAppServer table"
    ::= { ptSGSUAAppServerEntry 254 }

ptSGSUAAppServerIndex OBJECT-TYPE
    SYNTAX          Integer32 (-2147483648..2147483647)
    MAX-ACCESS      not-accessible
    STATUS          current
    DESCRIPTION     
            "The row number for the SGSUAAppServer table"
    ::= { ptSGSUAAppServerEntry 255 }

ptSGSUAASPStatus OBJECT IDENTIFIER
    ::= { ptSGSUAAppServer 203 }

ptSGSUAASPStatusTable OBJECT-TYPE
    SYNTAX          SEQUENCE OF PtSGSUAASPStatusEntry
    MAX-ACCESS      not-accessible
    STATUS          current
    DESCRIPTION     
            "No description supplied in the proxy config file."
    ::= { ptSGSUAASPStatus 1 }

ptSGSUAASPStatusEntry OBJECT-TYPE
    SYNTAX          PtSGSUAASPStatusEntry
    MAX-ACCESS      not-accessible
    STATUS          current
    DESCRIPTION     
            "A sequence of SGSUAASPStatus attributes."
    INDEX           { ptConnGroupIndex, ptSGSUAASPStatusSUAIndex, 
                      ptSGSUAASPStatusSUAAppServersIndex, 
                      ptSGSUAASPStatusSUAAppServerIndex, 
                      ptSGSUAASPStatusIndex }
    ::= { ptSGSUAASPStatusTable 1 }

PtSGSUAASPStatusEntry ::=
    SEQUENCE {
        ptSGSUAASPStatusASPID           Integer32,
        ptSGSUAASPStatusState           INTEGER,
        ptSGSUAASPStatusSlot            Integer32,
        ptSGSUAASPStatusServerID        Integer32,
        ptSGSUAASPStatusName            DisplayString,
        ptSGSUAASPStatusSUAIndex        Integer32,
        ptSGSUAASPStatusSUAAppServersIndex  Integer32,
        ptSGSUAASPStatusSUAAppServerIndex Integer32,
        ptSGSUAASPStatusParentOID       OBJECT IDENTIFIER,
        ptSGSUAASPStatusRowStatus       RowStatus,
        ptSGSUAASPStatusIndex           Integer32
    }

ptSGSUAASPStatusASPID OBJECT-TYPE
    SYNTAX          Integer32 (-2147483648..2147483647)
    MAX-ACCESS      read-only
    STATUS          current
    DESCRIPTION     
            "SUA AS ASP unique identifier for given slot."
    ::= { ptSGSUAASPStatusEntry 1 }

ptSGSUAASPStatusState OBJECT-TYPE
    SYNTAX          INTEGER { up(0), active(1), inactive(2), down(3) }
    MAX-ACCESS      read-only
    STATUS          current
    DESCRIPTION     
            "SUA AS ASP status."
    ::= { ptSGSUAASPStatusEntry 2 }

ptSGSUAASPStatusSlot OBJECT-TYPE
    SYNTAX          Integer32 (-2147483648..2147483647)
    MAX-ACCESS      read-only
    STATUS          current
    DESCRIPTION     
            "SUA AS ASP corresponding slot."
    ::= { ptSGSUAASPStatusEntry 3 }

ptSGSUAASPStatusServerID OBJECT-TYPE
    SYNTAX          Integer32 (-2147483648..2147483647)
    MAX-ACCESS      read-only
    STATUS          current
    DESCRIPTION     
            "SUA AS ASP corresponding server ID."
    ::= { ptSGSUAASPStatusEntry 4 }

ptSGSUAASPStatusName OBJECT-TYPE
    SYNTAX          DisplayString (SIZE(0..255))
    MAX-ACCESS      read-only
    STATUS          current
    DESCRIPTION     
            "SUA AS ASP corresponding name."
    ::= { ptSGSUAASPStatusEntry 5 }

ptSGSUAASPStatusSUAIndex OBJECT-TYPE
    SYNTAX          Integer32 (-2147483648..2147483647)
    MAX-ACCESS      not-accessible
    STATUS          current
    DESCRIPTION     
            "This is the index of the parent type for this object.
             This parent type is SUA."
    ::= { ptSGSUAASPStatusEntry 242 }

ptSGSUAASPStatusSUAAppServersIndex OBJECT-TYPE
    SYNTAX          Integer32 (-2147483648..2147483647)
    MAX-ACCESS      not-accessible
    STATUS          current
    DESCRIPTION     
            "This is the index of the parent type for this object.
             This parent type is SUAAppServers."
    ::= { ptSGSUAASPStatusEntry 243 }

ptSGSUAASPStatusSUAAppServerIndex OBJECT-TYPE
    SYNTAX          Integer32 (-2147483648..2147483647)
    MAX-ACCESS      not-accessible
    STATUS          current
    DESCRIPTION     
            "This is the index of the parent type for this object.
             This parent type is SUAAppServer."
    ::= { ptSGSUAASPStatusEntry 244 }

ptSGSUAASPStatusParentOID OBJECT-TYPE
    SYNTAX          OBJECT IDENTIFIER
    MAX-ACCESS      read-create
    STATUS          current
    DESCRIPTION     
            "The OID of the parent object for this instance"
    ::= { ptSGSUAASPStatusEntry 253 }

ptSGSUAASPStatusRowStatus OBJECT-TYPE
    SYNTAX          RowStatus
    MAX-ACCESS      read-create
    STATUS          current
    DESCRIPTION     
            "The row status for the SGSUAASPStatus table"
    ::= { ptSGSUAASPStatusEntry 254 }

ptSGSUAASPStatusIndex OBJECT-TYPE
    SYNTAX          Integer32 (-2147483648..2147483647)
    MAX-ACCESS      not-accessible
    STATUS          current
    DESCRIPTION     
            "The row number for the SGSUAASPStatus table"
    ::= { ptSGSUAASPStatusEntry 255 }

ptSGSUAASPs OBJECT IDENTIFIER
    ::= { ptSGSUA 207 }

ptSGSUAASPsTable OBJECT-TYPE
    SYNTAX          SEQUENCE OF PtSGSUAASPsEntry
    MAX-ACCESS      not-accessible
    STATUS          current
    DESCRIPTION     
            "No description supplied in the proxy config file."
    ::= { ptSGSUAASPs 1 }

ptSGSUAASPsEntry OBJECT-TYPE
    SYNTAX          PtSGSUAASPsEntry
    MAX-ACCESS      not-accessible
    STATUS          current
    DESCRIPTION     
            "A sequence of SGSUAASPs attributes."
    INDEX           { ptConnGroupIndex, ptSGSUAASPsSUAIndex, 
                      ptSGSUAASPsIndex }
    ::= { ptSGSUAASPsTable 1 }

PtSGSUAASPsEntry ::=
    SEQUENCE {
        ptSGSUAASPsSUAIndex             Integer32,
        ptSGSUAASPsParentOID            OBJECT IDENTIFIER,
        ptSGSUAASPsRowStatus            RowStatus,
        ptSGSUAASPsIndex                Integer32
    }

ptSGSUAASPsSUAIndex OBJECT-TYPE
    SYNTAX          Integer32 (-2147483648..2147483647)
    MAX-ACCESS      not-accessible
    STATUS          current
    DESCRIPTION     
            "This is the index of the parent type for this object.
             This parent type is SUA."
    ::= { ptSGSUAASPsEntry 242 }

ptSGSUAASPsParentOID OBJECT-TYPE
    SYNTAX          OBJECT IDENTIFIER
    MAX-ACCESS      read-create
    STATUS          current
    DESCRIPTION     
            "The OID of the parent object for this instance"
    ::= { ptSGSUAASPsEntry 253 }

ptSGSUAASPsRowStatus OBJECT-TYPE
    SYNTAX          RowStatus
    MAX-ACCESS      read-create
    STATUS          current
    DESCRIPTION     
            "The row status for the SGSUAASPs table"
    ::= { ptSGSUAASPsEntry 254 }

ptSGSUAASPsIndex OBJECT-TYPE
    SYNTAX          Integer32 (-2147483648..2147483647)
    MAX-ACCESS      not-accessible
    STATUS          current
    DESCRIPTION     
            "The row number for the SGSUAASPs table"
    ::= { ptSGSUAASPsEntry 255 }

ptSGSUAASP OBJECT IDENTIFIER
    ::= { ptSGSUAASPs 208 }

ptSGSUAASPTable OBJECT-TYPE
    SYNTAX          SEQUENCE OF PtSGSUAASPEntry
    MAX-ACCESS      not-accessible
    STATUS          current
    DESCRIPTION     
            "No description supplied in the proxy config file."
    ::= { ptSGSUAASP 1 }

ptSGSUAASPEntry OBJECT-TYPE
    SYNTAX          PtSGSUAASPEntry
    MAX-ACCESS      not-accessible
    STATUS          current
    DESCRIPTION     
            "A sequence of SGSUAASP attributes."
    INDEX           { ptConnGroupIndex, ptSGSUAASPSUAIndex, 
                      ptSGSUAASPSUAASPsIndex, ptSGSUAASPIndex }
    ::= { ptSGSUAASPTable 1 }

PtSGSUAASPEntry ::=
    SEQUENCE {
        ptSGSUAASPIPAddress1            DisplayString,
        ptSGSUAASPIPAddress2            DisplayString,
        ptSGSUAASPAssocID               Integer32,
        ptSGSUAASPPort                  Integer32,
        ptSGSUAASPID                    Integer32,
        ptSGSUAASPState                 INTEGER,
        ptSGSUAASPSlot                  Integer32,
        ptSGSUAASPServerID              Integer32,
        ptSGSUAASPHeartbeat             INTEGER,
        ptSGSUAASPHeartbeatInterval     Integer32,
        ptSGSUAASPRTOInitial            Integer32,
        ptSGSUAASPRTOMinimum            Integer32,
        ptSGSUAASPRTOMaximum            Integer32,
        ptSGSUAASPMaximumInitRetrans    Integer32,
        ptSGSUAASPMaximumAssocRetrans   Integer32,
        ptSGSUAASPMaximumPathRetrans    Integer32,
        ptSGSUAASPBundling              INTEGER,
        ptSGSUAASPBundlingTimeout       Integer32,
        ptSGSUAASPDelayedAckTimeout     Integer32,
        ptSGSUAASPChecksum              INTEGER,
        ptSGSUAASPInStreams             Integer32,
        ptSGSUAASPOutStreams            Integer32,
        ptSGSUAASPUserASPID             DisplayString,
        ptSGSUAASPName                  DisplayString,
        ptSGSUAASPRxMSGCount            Integer32,
        ptSGSUAASPTxMSGCount            Integer32,
        ptSGSUAASPSUAIndex              Integer32,
        ptSGSUAASPSUAASPsIndex          Integer32,
        ptSGSUAASPActions               INTEGER,
        ptSGSUAASPParentOID             OBJECT IDENTIFIER,
        ptSGSUAASPRowStatus             RowStatus,
        ptSGSUAASPIndex                 Integer32
    }

ptSGSUAASPIPAddress1 OBJECT-TYPE
    SYNTAX          DisplayString (SIZE(0..255))
    MAX-ACCESS      read-only
    STATUS          current
    DESCRIPTION     
            "SUA ASP primary IP address."
    ::= { ptSGSUAASPEntry 1 }

ptSGSUAASPIPAddress2 OBJECT-TYPE
    SYNTAX          DisplayString (SIZE(0..255))
    MAX-ACCESS      read-only
    STATUS          current
    DESCRIPTION     
            "SUA ASP secondary IP address."
    ::= { ptSGSUAASPEntry 2 }

ptSGSUAASPAssocID OBJECT-TYPE
    SYNTAX          Integer32 (-2147483648..2147483647)
    MAX-ACCESS      read-only
    STATUS          current
    DESCRIPTION     
            "SUA ASP Association ID."
    ::= { ptSGSUAASPEntry 3 }

ptSGSUAASPPort OBJECT-TYPE
    SYNTAX          Integer32 (-2147483648..2147483647)
    MAX-ACCESS      read-only
    STATUS          current
    DESCRIPTION     
            "SUA ASP port."
    ::= { ptSGSUAASPEntry 5 }

ptSGSUAASPID OBJECT-TYPE
    SYNTAX          Integer32 (-2147483648..2147483647)
    MAX-ACCESS      read-only
    STATUS          current
    DESCRIPTION     
            "SUA ASP unique identifier."
    ::= { ptSGSUAASPEntry 6 }

ptSGSUAASPState OBJECT-TYPE
    SYNTAX          INTEGER { up(0), active(1), inactive(2), down(3) }
    MAX-ACCESS      read-only
    STATUS          current
    DESCRIPTION     
            "SUA ASP status."
    ::= { ptSGSUAASPEntry 7 }

ptSGSUAASPSlot OBJECT-TYPE
    SYNTAX          Integer32 (-2147483648..2147483647)
    MAX-ACCESS      read-only
    STATUS          current
    DESCRIPTION     
            "No description supplied in the proxy config file."
    ::= { ptSGSUAASPEntry 8 }

ptSGSUAASPServerID OBJECT-TYPE
    SYNTAX          Integer32 (-2147483648..2147483647)
    MAX-ACCESS      read-only
    STATUS          current
    DESCRIPTION     
            "SUA SCTP Server ID."
    ::= { ptSGSUAASPEntry 9 }

ptSGSUAASPHeartbeat OBJECT-TYPE
    SYNTAX          INTEGER { disabled(0), enabled(1) }
    MAX-ACCESS      read-create
    STATUS          current
    DESCRIPTION     
            "Enable or disable the Heartbeat feature."
    ::= { ptSGSUAASPEntry 10 }

ptSGSUAASPHeartbeatInterval OBJECT-TYPE
    SYNTAX          Integer32 (0..65355)
    MAX-ACCESS      read-create
    STATUS          current
    DESCRIPTION     
            "Heartbeat interval (ms)."
    ::= { ptSGSUAASPEntry 11 }

ptSGSUAASPRTOInitial OBJECT-TYPE
    SYNTAX          Integer32 (0..2147483647)
    MAX-ACCESS      read-create
    STATUS          current
    DESCRIPTION     
            "Initial Retransmission Timeout (ms)."
    ::= { ptSGSUAASPEntry 12 }

ptSGSUAASPRTOMinimum OBJECT-TYPE
    SYNTAX          Integer32 (0..2147483647)
    MAX-ACCESS      read-create
    STATUS          current
    DESCRIPTION     
            "Minimum Retransmission Timeout (ms)."
    ::= { ptSGSUAASPEntry 13 }

ptSGSUAASPRTOMaximum OBJECT-TYPE
    SYNTAX          Integer32 (0..2147483647)
    MAX-ACCESS      read-create
    STATUS          current
    DESCRIPTION     
            "Maximum Retransmission Timeout (ms)."
    ::= { ptSGSUAASPEntry 14 }

ptSGSUAASPMaximumInitRetrans OBJECT-TYPE
    SYNTAX          Integer32 (0..2147483647)
    MAX-ACCESS      read-create
    STATUS          current
    DESCRIPTION     
            "Maximum initial retransmissions."
    ::= { ptSGSUAASPEntry 15 }

ptSGSUAASPMaximumAssocRetrans OBJECT-TYPE
    SYNTAX          Integer32 (0..2147483647)
    MAX-ACCESS      read-create
    STATUS          current
    DESCRIPTION     
            "Maximum association retransmissions."
    ::= { ptSGSUAASPEntry 16 }

ptSGSUAASPMaximumPathRetrans OBJECT-TYPE
    SYNTAX          Integer32 (0..2147483647)
    MAX-ACCESS      read-create
    STATUS          current
    DESCRIPTION     
            "Maximum path retransmissions."
    ::= { ptSGSUAASPEntry 17 }

ptSGSUAASPBundling OBJECT-TYPE
    SYNTAX          INTEGER { disabled(0), enabled(1) }
    MAX-ACCESS      read-create
    STATUS          current
    DESCRIPTION     
            "Enable or disable the Bundling feature."
    ::= { ptSGSUAASPEntry 18 }

ptSGSUAASPBundlingTimeout OBJECT-TYPE
    SYNTAX          Integer32 (0..2147483647)
    MAX-ACCESS      read-create
    STATUS          current
    DESCRIPTION     
            "Bundling timeout (msecs)."
    ::= { ptSGSUAASPEntry 19 }

ptSGSUAASPDelayedAckTimeout OBJECT-TYPE
    SYNTAX          Integer32 (0..500)
    MAX-ACCESS      read-create
    STATUS          current
    DESCRIPTION     
            "Delayed acknowledgement timeout."
    ::= { ptSGSUAASPEntry 20 }

ptSGSUAASPChecksum OBJECT-TYPE
    SYNTAX          INTEGER { adler32(0), crc32c(1), none(2) }
    MAX-ACCESS      read-only
    STATUS          current
    DESCRIPTION     
            "Checksum algorithm"
    ::= { ptSGSUAASPEntry 21 }

ptSGSUAASPInStreams OBJECT-TYPE
    SYNTAX          Integer32 (0..65355)
    MAX-ACCESS      read-create
    STATUS          current
    DESCRIPTION     
            "Number of in streams."
    ::= { ptSGSUAASPEntry 22 }

ptSGSUAASPOutStreams OBJECT-TYPE
    SYNTAX          Integer32 (0..65355)
    MAX-ACCESS      read-create
    STATUS          current
    DESCRIPTION     
            "Number of out streams."
    ::= { ptSGSUAASPEntry 23 }

ptSGSUAASPUserASPID OBJECT-TYPE
    SYNTAX          DisplayString (SIZE(0..255))
    MAX-ACCESS      read-only
    STATUS          current
    DESCRIPTION     
            "SUA ASP Identifier received from a preconfigured user. This value can differ from the ID if ASP ID Validation for the pre-configured ASP has been set to DISABLED. The User ASP ID is used (rather than the ID) when sending NOTIFY messages concerning this ASP."
    ::= { ptSGSUAASPEntry 24 }

ptSGSUAASPName OBJECT-TYPE
    SYNTAX          DisplayString (SIZE(0..255))
    MAX-ACCESS      read-only
    STATUS          current
    DESCRIPTION     
            "SUA ASP name."
    ::= { ptSGSUAASPEntry 25 }

ptSGSUAASPRxMSGCount OBJECT-TYPE
    SYNTAX          Integer32 (-2147483648..2147483647)
    MAX-ACCESS      read-only
    STATUS          current
    DESCRIPTION     
            "Number Received Messages per second"
    ::= { ptSGSUAASPEntry 26 }

ptSGSUAASPTxMSGCount OBJECT-TYPE
    SYNTAX          Integer32 (-2147483648..2147483647)
    MAX-ACCESS      read-only
    STATUS          current
    DESCRIPTION     
            "Number Transmitted Messages per second"
    ::= { ptSGSUAASPEntry 27 }

ptSGSUAASPSUAIndex OBJECT-TYPE
    SYNTAX          Integer32 (-2147483648..2147483647)
    MAX-ACCESS      not-accessible
    STATUS          current
    DESCRIPTION     
            "This is the index of the parent type for this object.
             This parent type is SUA."
    ::= { ptSGSUAASPEntry 242 }

ptSGSUAASPSUAASPsIndex OBJECT-TYPE
    SYNTAX          Integer32 (-2147483648..2147483647)
    MAX-ACCESS      not-accessible
    STATUS          current
    DESCRIPTION     
            "This is the index of the parent type for this object.
             This parent type is SUAASPs."
    ::= { ptSGSUAASPEntry 243 }

ptSGSUAASPActions OBJECT-TYPE
    SYNTAX          INTEGER { terminate(1), shutdown(2) }
    MAX-ACCESS      read-create
    STATUS          current
    DESCRIPTION     
            "The OID of all possible actions for this instance"
    ::= { ptSGSUAASPEntry 252 }

ptSGSUAASPParentOID OBJECT-TYPE
    SYNTAX          OBJECT IDENTIFIER
    MAX-ACCESS      read-create
    STATUS          current
    DESCRIPTION     
            "The OID of the parent object for this instance"
    ::= { ptSGSUAASPEntry 253 }

ptSGSUAASPRowStatus OBJECT-TYPE
    SYNTAX          RowStatus
    MAX-ACCESS      read-create
    STATUS          current
    DESCRIPTION     
            "The row status for the SGSUAASP table"
    ::= { ptSGSUAASPEntry 254 }

ptSGSUAASPIndex OBJECT-TYPE
    SYNTAX          Integer32 (-2147483648..2147483647)
    MAX-ACCESS      not-accessible
    STATUS          current
    DESCRIPTION     
            "The row number for the SGSUAASP table"
    ::= { ptSGSUAASPEntry 255 }

ptSGSUASCTPServers OBJECT IDENTIFIER
    ::= { ptSGSUA 209 }

ptSGSUASCTPServersTable OBJECT-TYPE
    SYNTAX          SEQUENCE OF PtSGSUASCTPServersEntry
    MAX-ACCESS      not-accessible
    STATUS          current
    DESCRIPTION     
            "No description supplied in the proxy config file."
    ::= { ptSGSUASCTPServers 1 }

ptSGSUASCTPServersEntry OBJECT-TYPE
    SYNTAX          PtSGSUASCTPServersEntry
    MAX-ACCESS      not-accessible
    STATUS          current
    DESCRIPTION     
            "A sequence of SGSUASCTPServers attributes."
    INDEX           { ptConnGroupIndex, ptSGSUASCTPServersSUAIndex, 
                      ptSGSUASCTPServersIndex }
    ::= { ptSGSUASCTPServersTable 1 }

PtSGSUASCTPServersEntry ::=
    SEQUENCE {
        ptSGSUASCTPServersASPManagement INTEGER,
        ptSGSUASCTPServersStatus        INTEGER,
        ptSGSUASCTPServersHeartbeat     INTEGER,
        ptSGSUASCTPServersHeartbeatInterval   Integer32,
        ptSGSUASCTPServersMaximumAssocRetrans     Integer32,
        ptSGSUASCTPServersMaximumPathRetrans    Integer32,
        ptSGSUASCTPServersMaximumInitRetrans    Integer32,
        ptSGSUASCTPServersBundling      INTEGER,
        ptSGSUASCTPServersBundlingTimeout Integer32,
        ptSGSUASCTPServersDelayedAckTimeout   Integer32,
        ptSGSUASCTPServersRTOInitial    Integer32,
        ptSGSUASCTPServersRTOMinimum    Integer32,
        ptSGSUASCTPServersRTOMaximum    Integer32,
        ptSGSUASCTPServersChecksum      INTEGER,
        ptSGSUASCTPServersInStreams     Integer32,
        ptSGSUASCTPServersOutStreams    Integer32,
        ptSGSUASCTPServersDefaultNetworkAppearance          Integer32,
        ptSGSUASCTPServersSUAIndex      Integer32,
        ptSGSUASCTPServersActions       INTEGER,
        ptSGSUASCTPServersParentOID     OBJECT IDENTIFIER,
        ptSGSUASCTPServersRowStatus     RowStatus,
        ptSGSUASCTPServersIndex         Integer32
    }

ptSGSUASCTPServersASPManagement OBJECT-TYPE
    SYNTAX          INTEGER { configuredAndDynamic(0), configuredOnly(1) }
    MAX-ACCESS      read-create
    STATUS          current
    DESCRIPTION     
            "ASP Dynamic and/or preconfigured setup."
    ::= { ptSGSUASCTPServersEntry 1 }

ptSGSUASCTPServersStatus OBJECT-TYPE
    SYNTAX          INTEGER { disabled(0), enabled(1) }
    MAX-ACCESS      read-only
    STATUS          current
    DESCRIPTION     
            "SUA SCTP Server status."
    ::= { ptSGSUASCTPServersEntry 2 }

ptSGSUASCTPServersHeartbeat OBJECT-TYPE
    SYNTAX          INTEGER { disabled(0), enabled(1) }
    MAX-ACCESS      read-create
    STATUS          current
    DESCRIPTION     
            "Enable or disable the Heartbeat feature. \nSCTP Server must be de-activated and re-activated to take effect."
    ::= { ptSGSUASCTPServersEntry 6 }

ptSGSUASCTPServersHeartbeatInterval OBJECT-TYPE
    SYNTAX          Integer32 (0..65355)
    MAX-ACCESS      read-create
    STATUS          current
    DESCRIPTION     
            "Heartbeat interval (ms). \nSCTP Server must be de-activated and re-activated to take effect."
    ::= { ptSGSUASCTPServersEntry 7 }

ptSGSUASCTPServersMaximumAssocRetrans OBJECT-TYPE
    SYNTAX          Integer32 (0..2147483647)
    MAX-ACCESS      read-create
    STATUS          current
    DESCRIPTION     
            "Maximum association retransmissions. \nSCTP Server must be de-activated and re-activated to take effect."
    ::= { ptSGSUASCTPServersEntry 8 }

ptSGSUASCTPServersMaximumPathRetrans OBJECT-TYPE
    SYNTAX          Integer32 (0..2147483647)
    MAX-ACCESS      read-create
    STATUS          current
    DESCRIPTION     
            "Maximum path retransmissions. \nSCTP Server must be de-activated and re-activated to take effect."
    ::= { ptSGSUASCTPServersEntry 9 }

ptSGSUASCTPServersMaximumInitRetrans OBJECT-TYPE
    SYNTAX          Integer32 (0..2147483647)
    MAX-ACCESS      read-create
    STATUS          current
    DESCRIPTION     
            "Maximum initial retransmissions. \nSCTP Server must be de-activated and re-activated to take effect."
    ::= { ptSGSUASCTPServersEntry 10 }

ptSGSUASCTPServersBundling OBJECT-TYPE
    SYNTAX          INTEGER { disabled(0), enabled(1) }
    MAX-ACCESS      read-create
    STATUS          current
    DESCRIPTION     
            "Enable or disable the Bundling feature. \nSCTP Server must be de-activated and re-activated to take effect."
    ::= { ptSGSUASCTPServersEntry 11 }

ptSGSUASCTPServersBundlingTimeout OBJECT-TYPE
    SYNTAX          Integer32 (0..2147483647)
    MAX-ACCESS      read-create
    STATUS          current
    DESCRIPTION     
            "Bundling timeout (msecs). \nSCTP Server must be de-activated and re-activated to take effect."
    ::= { ptSGSUASCTPServersEntry 12 }

ptSGSUASCTPServersDelayedAckTimeout OBJECT-TYPE
    SYNTAX          Integer32 (0..500)
    MAX-ACCESS      read-create
    STATUS          current
    DESCRIPTION     
            "Delayed acknowledgement timeout. \nSCTP Server must be de-activated and re-activated to take effect."
    ::= { ptSGSUASCTPServersEntry 13 }

ptSGSUASCTPServersRTOInitial OBJECT-TYPE
    SYNTAX          Integer32 (0..2147483647)
    MAX-ACCESS      read-create
    STATUS          current
    DESCRIPTION     
            "Initial Retransmission Timeout (ms). \nSCTP Server must be de-activated and re-activated to take effect."
    ::= { ptSGSUASCTPServersEntry 15 }

ptSGSUASCTPServersRTOMinimum OBJECT-TYPE
    SYNTAX          Integer32 (0..2147483647)
    MAX-ACCESS      read-create
    STATUS          current
    DESCRIPTION     
            "Minimum Retransmission Timeout (ms). \nSCTP Server must be de-activated and re-activated to take effect."
    ::= { ptSGSUASCTPServersEntry 16 }

ptSGSUASCTPServersRTOMaximum OBJECT-TYPE
    SYNTAX          Integer32 (0..2147483647)
    MAX-ACCESS      read-create
    STATUS          current
    DESCRIPTION     
            "Maximum Retransmission Timeout (ms). \nSCTP Server must be de-activated and re-activated to take effect."
    ::= { ptSGSUASCTPServersEntry 17 }

ptSGSUASCTPServersChecksum OBJECT-TYPE
    SYNTAX          INTEGER { adler32(0), crc32c(1), none(2) }
    MAX-ACCESS      read-only
    STATUS          current
    DESCRIPTION     
            "Checksum algorithm. \nSCTP Server must be de-activated and re-activated to take effect."
    ::= { ptSGSUASCTPServersEntry 18 }

ptSGSUASCTPServersInStreams OBJECT-TYPE
    SYNTAX          Integer32 (0..65355)
    MAX-ACCESS      read-create
    STATUS          current
    DESCRIPTION     
            "Number of in streams. \nSCTP Server must be de-activated and re-activated to take effect."
    ::= { ptSGSUASCTPServersEntry 19 }

ptSGSUASCTPServersOutStreams OBJECT-TYPE
    SYNTAX          Integer32 (0..65355)
    MAX-ACCESS      read-create
    STATUS          current
    DESCRIPTION     
            "Number of out streams. \nSCTP Server must be de-activated and re-activated to take effect."
    ::= { ptSGSUASCTPServersEntry 20 }

ptSGSUASCTPServersDefaultNetworkAppearance OBJECT-TYPE
    SYNTAX          Integer32 (-2147483648..2147483647)
    MAX-ACCESS      read-create
    STATUS          current
    DESCRIPTION     
            "SUA default network appearance. \nIf the NA is not provided in the transfer message and the connected ASP is either dynamic or the default NA of its corresponding configured ASP object is UNSET (-1), this value is used to select the SCCP NA Connection. \nChanging this attribute value can impact traffic."
    ::= { ptSGSUASCTPServersEntry 21 }

ptSGSUASCTPServersSUAIndex OBJECT-TYPE
    SYNTAX          Integer32 (-2147483648..2147483647)
    MAX-ACCESS      not-accessible
    STATUS          current
    DESCRIPTION     
            "This is the index of the parent type for this object.
             This parent type is SUA."
    ::= { ptSGSUASCTPServersEntry 242 }

ptSGSUASCTPServersActions OBJECT-TYPE
    SYNTAX          INTEGER { activateAll(1), deactivateAll(2) }
    MAX-ACCESS      read-create
    STATUS          current
    DESCRIPTION     
            "The OID of all possible actions for this instance"
    ::= { ptSGSUASCTPServersEntry 252 }

ptSGSUASCTPServersParentOID OBJECT-TYPE
    SYNTAX          OBJECT IDENTIFIER
    MAX-ACCESS      read-create
    STATUS          current
    DESCRIPTION     
            "The OID of the parent object for this instance"
    ::= { ptSGSUASCTPServersEntry 253 }

ptSGSUASCTPServersRowStatus OBJECT-TYPE
    SYNTAX          RowStatus
    MAX-ACCESS      read-create
    STATUS          current
    DESCRIPTION     
            "The row status for the SGSUASCTPServers table"
    ::= { ptSGSUASCTPServersEntry 254 }

ptSGSUASCTPServersIndex OBJECT-TYPE
    SYNTAX          Integer32 (-2147483648..2147483647)
    MAX-ACCESS      not-accessible
    STATUS          current
    DESCRIPTION     
            "The row number for the SGSUASCTPServers table"
    ::= { ptSGSUASCTPServersEntry 255 }

ptSGSUASCTPServer OBJECT IDENTIFIER
    ::= { ptSGSUASCTPServers 210 }

ptSGSUASCTPServerTable OBJECT-TYPE
    SYNTAX          SEQUENCE OF PtSGSUASCTPServerEntry
    MAX-ACCESS      not-accessible
    STATUS          current
    DESCRIPTION     
            "No description supplied in the proxy config file."
    ::= { ptSGSUASCTPServer 1 }

ptSGSUASCTPServerEntry OBJECT-TYPE
    SYNTAX          PtSGSUASCTPServerEntry
    MAX-ACCESS      not-accessible
    STATUS          current
    DESCRIPTION     
            "A sequence of SGSUASCTPServer attributes."
    INDEX           { ptConnGroupIndex, ptSGSUASCTPServerSUAIndex, 
                      ptSGSUASCTPServerSUASCTPServersIndex, 
                      ptSGSUASCTPServerIndex }
    ::= { ptSGSUASCTPServerTable 1 }

PtSGSUASCTPServerEntry ::=
    SEQUENCE {
        ptSGSUASCTPServerSlot           Integer32,
        ptSGSUASCTPServerIPAddress1     DisplayString,
        ptSGSUASCTPServerIPAddress2     DisplayString,
        ptSGSUASCTPServerPort           Integer32,
        ptSGSUASCTPServerServerID       Integer32,
        ptSGSUASCTPServerStatus         INTEGER,
        ptSGSUASCTPServerHeartbeat      INTEGER,
        ptSGSUASCTPServerHeartbeatInterval  Integer32,
        ptSGSUASCTPServerRTOInitial     Integer32,
        ptSGSUASCTPServerRTOMinimum     Integer32,
        ptSGSUASCTPServerRTOMaximum     Integer32,
        ptSGSUASCTPServerMaximumInitRetrans   Integer32,
        ptSGSUASCTPServerMaximumAssocRetrans    Integer32,
        ptSGSUASCTPServerMaximumPathRetrans   Integer32,
        ptSGSUASCTPServerBundling       INTEGER,
        ptSGSUASCTPServerBundlingTimeout Integer32,
        ptSGSUASCTPServerDelayedAckTimeout  Integer32,
        ptSGSUASCTPServerChecksum       INTEGER,
        ptSGSUASCTPServerInStreams      Integer32,
        ptSGSUASCTPServerOutStreams     Integer32,
        ptSGSUASCTPServerDefaultSCTPValues  INTEGER,
        ptSGSUASCTPServerListenStatus   INTEGER,
        ptSGSUASCTPServerSUAIndex       Integer32,
        ptSGSUASCTPServerSUASCTPServersIndex    Integer32,
        ptSGSUASCTPServerActions        INTEGER,
        ptSGSUASCTPServerParentOID      OBJECT IDENTIFIER,
        ptSGSUASCTPServerRowStatus      RowStatus,
        ptSGSUASCTPServerIndex          Integer32
    }

ptSGSUASCTPServerSlot OBJECT-TYPE
    SYNTAX          Integer32 (-2147483648..2147483647)
    MAX-ACCESS      read-only
    STATUS          current
    DESCRIPTION     
            "The Slot where the server is being configured"
    ::= { ptSGSUASCTPServerEntry 1 }

ptSGSUASCTPServerIPAddress1 OBJECT-TYPE
    SYNTAX          DisplayString (SIZE(0..255))
    MAX-ACCESS      read-create
    STATUS          current
    DESCRIPTION     
            "SUA SCTP Server primary address. This may be a hostname or an IP Address. If a hostname is used it must be provisioned either in /etc/hosts or via a properly-configured DNS Server and should resolve to a subset of the local IP Addresses configured for the slot where the SCTP server is hosted. Hostname resolution is attempted periodically. Resolution updates take effect ONLY when the server is restarted."
    ::= { ptSGSUASCTPServerEntry 2 }

ptSGSUASCTPServerIPAddress2 OBJECT-TYPE
    SYNTAX          DisplayString (SIZE(0..255))
    MAX-ACCESS      read-create
    STATUS          current
    DESCRIPTION     
            "SUA SCTP Server secondary address. This may be a hostname or an IP Address. If a hostname is used it must be provisioned either in /etc/hosts or via a properly-configured DNS Server and should resolve to a subset of the local IP Addresses configured for the slot where the SCTP server is hosted. Hostname resolution is attempted periodically. Resolution updates take effect ONLY when the server is restarted."
    ::= { ptSGSUASCTPServerEntry 3 }

ptSGSUASCTPServerPort OBJECT-TYPE
    SYNTAX          Integer32 (-2147483648..2147483647)
    MAX-ACCESS      read-create
    STATUS          current
    DESCRIPTION     
            "SUA SCTP Server port."
    ::= { ptSGSUASCTPServerEntry 4 }

ptSGSUASCTPServerServerID OBJECT-TYPE
    SYNTAX          Integer32 (-2147483648..2147483647)
    MAX-ACCESS      read-only
    STATUS          current
    DESCRIPTION     
            "SUA SCTP Server ID"
    ::= { ptSGSUASCTPServerEntry 5 }

ptSGSUASCTPServerStatus OBJECT-TYPE
    SYNTAX          INTEGER { disabled(0), enabled(1) }
    MAX-ACCESS      read-only
    STATUS          current
    DESCRIPTION     
            "SUA SCTP Over All Server status."
    ::= { ptSGSUASCTPServerEntry 6 }

ptSGSUASCTPServerHeartbeat OBJECT-TYPE
    SYNTAX          INTEGER { disabled(0), enabled(1) }
    MAX-ACCESS      read-create
    STATUS          current
    DESCRIPTION     
            "Enable or disable the Heartbeat feature. \nSCTP Server must be de-activated and re-activated to take effect."
    ::= { ptSGSUASCTPServerEntry 7 }

ptSGSUASCTPServerHeartbeatInterval OBJECT-TYPE
    SYNTAX          Integer32 (0..65355)
    MAX-ACCESS      read-create
    STATUS          current
    DESCRIPTION     
            "Heartbeat interval (ms). \nSCTP Server must be de-activated and re-activated to take effect."
    ::= { ptSGSUASCTPServerEntry 8 }

ptSGSUASCTPServerRTOInitial OBJECT-TYPE
    SYNTAX          Integer32 (0..2147483647)
    MAX-ACCESS      read-create
    STATUS          current
    DESCRIPTION     
            "Initial Retransmission Timeout (ms). \nSCTP Server must be de-activated and re-activated to take effect."
    ::= { ptSGSUASCTPServerEntry 9 }

ptSGSUASCTPServerRTOMinimum OBJECT-TYPE
    SYNTAX          Integer32 (0..2147483647)
    MAX-ACCESS      read-create
    STATUS          current
    DESCRIPTION     
            "Minimum Retransmission Timeout (ms). \nSCTP Server must be de-activated and re-activated to take effect."
    ::= { ptSGSUASCTPServerEntry 10 }

ptSGSUASCTPServerRTOMaximum OBJECT-TYPE
    SYNTAX          Integer32 (0..2147483647)
    MAX-ACCESS      read-create
    STATUS          current
    DESCRIPTION     
            "Maximum Retransmission Timeout (ms). \nSCTP Server must be de-activated and re-activated to take effect."
    ::= { ptSGSUASCTPServerEntry 11 }

ptSGSUASCTPServerMaximumInitRetrans OBJECT-TYPE
    SYNTAX          Integer32 (0..2147483647)
    MAX-ACCESS      read-create
    STATUS          current
    DESCRIPTION     
            "Maximum initial retransmissions. \nSCTP Server must be de-activated and re-activated to take effect."
    ::= { ptSGSUASCTPServerEntry 12 }

ptSGSUASCTPServerMaximumAssocRetrans OBJECT-TYPE
    SYNTAX          Integer32 (0..2147483647)
    MAX-ACCESS      read-create
    STATUS          current
    DESCRIPTION     
            "Maximum association retransmissions. \nSCTP Server must be de-activated and re-activated to take effect."
    ::= { ptSGSUASCTPServerEntry 13 }

ptSGSUASCTPServerMaximumPathRetrans OBJECT-TYPE
    SYNTAX          Integer32 (0..2147483647)
    MAX-ACCESS      read-create
    STATUS          current
    DESCRIPTION     
            "Maximum path retransmissions. \nSCTP Server must be de-activated and re-activated to take effect."
    ::= { ptSGSUASCTPServerEntry 14 }

ptSGSUASCTPServerBundling OBJECT-TYPE
    SYNTAX          INTEGER { disabled(0), enabled(1) }
    MAX-ACCESS      read-create
    STATUS          current
    DESCRIPTION     
            "Enable or disable the Bundling feature. \nSCTP Server must be de-activated and re-activated to take effect."
    ::= { ptSGSUASCTPServerEntry 15 }

ptSGSUASCTPServerBundlingTimeout OBJECT-TYPE
    SYNTAX          Integer32 (0..2147483647)
    MAX-ACCESS      read-create
    STATUS          current
    DESCRIPTION     
            "Bundling timeout (msecs). \nSCTP Server must be de-activated and re-activated to take effect."
    ::= { ptSGSUASCTPServerEntry 16 }

ptSGSUASCTPServerDelayedAckTimeout OBJECT-TYPE
    SYNTAX          Integer32 (0..500)
    MAX-ACCESS      read-create
    STATUS          current
    DESCRIPTION     
            "Delayed acknowledgement timeout. \nSCTP Server must be de-activated and re-activated to take effect."
    ::= { ptSGSUASCTPServerEntry 17 }

ptSGSUASCTPServerChecksum OBJECT-TYPE
    SYNTAX          INTEGER { adler32(0), crc32c(1), none(2) }
    MAX-ACCESS      read-only
    STATUS          current
    DESCRIPTION     
            "Checksum algorithm. \nSCTP Server must be de-activated and re-activated to take effect."
    ::= { ptSGSUASCTPServerEntry 18 }

ptSGSUASCTPServerInStreams OBJECT-TYPE
    SYNTAX          Integer32 (0..65355)
    MAX-ACCESS      read-create
    STATUS          current
    DESCRIPTION     
            "Number of in streams. \nSCTP Server must be de-activated and re-activated to take effect."
    ::= { ptSGSUASCTPServerEntry 19 }

ptSGSUASCTPServerOutStreams OBJECT-TYPE
    SYNTAX          Integer32 (0..65355)
    MAX-ACCESS      read-create
    STATUS          current
    DESCRIPTION     
            "Number of out streams. \nSCTP Server must be de-activated and re-activated to take effect."
    ::= { ptSGSUASCTPServerEntry 20 }

ptSGSUASCTPServerDefaultSCTPValues OBJECT-TYPE
    SYNTAX          INTEGER { no(0), yes(1) }
    MAX-ACCESS      read-create
    STATUS          current
    DESCRIPTION     
            "Use SUA SCTP default parameters."
    ::= { ptSGSUASCTPServerEntry 21 }

ptSGSUASCTPServerListenStatus OBJECT-TYPE
    SYNTAX          INTEGER { down(0), stopped(1), up(2), partiallyUp(3) }
    MAX-ACCESS      read-only
    STATUS          current
    DESCRIPTION     
            "SUA SCTP Server Listen Status.\n If Status is DISABLED, Listen Status must be set to 'DOWN'.\n If Status is ENABLED, Listen Status must be set to one of the following states:\n - 'DOWN': The server is not listening on any of the provided IP addresses due to a technical issue, e.g., the provided port is already in use, the provided IP addresses are not available or the provided hostnames are not resolvable.\n The alarm SUASCTPServerDown indicating that the server is down must be raised.\n - 'STOPPED': The server is not listening on any of the provided IP addresses because it has been purposefully stopped by the application. This status means that the server has been 'UP' or 'PARTIALLY UP' and it has been purposefully brought down either because the ASP license max count has been reached or because SCTP system max capacity per routing slot has been reached.\n The alarm SUASCTPServerDown indicating that the server is down must be raised.\n - 'UP': The server is listening on all the provided IP addresses\n - 'PARTIALLY UP': The server is listening on at least one, but not all, of the provided IP addresses.\n The alarm SUASCTPServerAddrListMismatch, indicating a mismatch between the list of the provided IP addresses and the list of the listening IP addresses, must be raised. PARTIALLY UP is also an indication that the server was up but the hostname has been removed from the hosts file. In this case the Server Status will be PARTIALLY UP but will continue to listen until deactivated."
    ::= { ptSGSUASCTPServerEntry 22 }

ptSGSUASCTPServerSUAIndex OBJECT-TYPE
    SYNTAX          Integer32 (-2147483648..2147483647)
    MAX-ACCESS      not-accessible
    STATUS          current
    DESCRIPTION     
            "This is the index of the parent type for this object.
             This parent type is SUA."
    ::= { ptSGSUASCTPServerEntry 242 }

ptSGSUASCTPServerSUASCTPServersIndex OBJECT-TYPE
    SYNTAX          Integer32 (-2147483648..2147483647)
    MAX-ACCESS      not-accessible
    STATUS          current
    DESCRIPTION     
            "This is the index of the parent type for this object.
             This parent type is SUASCTPServers."
    ::= { ptSGSUASCTPServerEntry 243 }

ptSGSUASCTPServerActions OBJECT-TYPE
    SYNTAX          INTEGER { activate(1), deactivate(2) }
    MAX-ACCESS      read-create
    STATUS          current
    DESCRIPTION     
            "The OID of all possible actions for this instance"
    ::= { ptSGSUASCTPServerEntry 252 }

ptSGSUASCTPServerParentOID OBJECT-TYPE
    SYNTAX          OBJECT IDENTIFIER
    MAX-ACCESS      read-create
    STATUS          current
    DESCRIPTION     
            "The OID of the parent object for this instance"
    ::= { ptSGSUASCTPServerEntry 253 }

ptSGSUASCTPServerRowStatus OBJECT-TYPE
    SYNTAX          RowStatus
    MAX-ACCESS      read-create
    STATUS          current
    DESCRIPTION     
            "The row status for the SGSUASCTPServer table"
    ::= { ptSGSUASCTPServerEntry 254 }

ptSGSUASCTPServerIndex OBJECT-TYPE
    SYNTAX          Integer32 (-2147483648..2147483647)
    MAX-ACCESS      not-accessible
    STATUS          current
    DESCRIPTION     
            "The row number for the SGSUASCTPServer table"
    ::= { ptSGSUASCTPServerEntry 255 }

ptSGSUAConfiguredASPs OBJECT IDENTIFIER
    ::= { ptSGSUA 211 }

ptSGSUAConfiguredASPsTable OBJECT-TYPE
    SYNTAX          SEQUENCE OF PtSGSUAConfiguredASPsEntry
    MAX-ACCESS      not-accessible
    STATUS          current
    DESCRIPTION     
            "No description supplied in the proxy config file."
    ::= { ptSGSUAConfiguredASPs 1 }

ptSGSUAConfiguredASPsEntry OBJECT-TYPE
    SYNTAX          PtSGSUAConfiguredASPsEntry
    MAX-ACCESS      not-accessible
    STATUS          current
    DESCRIPTION     
            "A sequence of SGSUAConfiguredASPs attributes."
    INDEX           { ptConnGroupIndex, ptSGSUAConfiguredASPsSUAIndex, 
                      ptSGSUAConfiguredASPsIndex }
    ::= { ptSGSUAConfiguredASPsTable 1 }

PtSGSUAConfiguredASPsEntry ::=
    SEQUENCE {
        ptSGSUAConfiguredASPsSUAIndex   Integer32,
        ptSGSUAConfiguredASPsActions    INTEGER,
        ptSGSUAConfiguredASPsParentOID  OBJECT IDENTIFIER,
        ptSGSUAConfiguredASPsRowStatus  RowStatus,
        ptSGSUAConfiguredASPsIndex      Integer32
    }

ptSGSUAConfiguredASPsSUAIndex OBJECT-TYPE
    SYNTAX          Integer32 (-2147483648..2147483647)
    MAX-ACCESS      not-accessible
    STATUS          current
    DESCRIPTION     
            "This is the index of the parent type for this object.
             This parent type is SUA."
    ::= { ptSGSUAConfiguredASPsEntry 242 }

ptSGSUAConfiguredASPsActions OBJECT-TYPE
    SYNTAX          INTEGER { resetIMF(1) }
    MAX-ACCESS      read-create
    STATUS          current
    DESCRIPTION     
            "The OID of all possible actions for this instance"
    ::= { ptSGSUAConfiguredASPsEntry 252 }

ptSGSUAConfiguredASPsParentOID OBJECT-TYPE
    SYNTAX          OBJECT IDENTIFIER
    MAX-ACCESS      read-create
    STATUS          current
    DESCRIPTION     
            "The OID of the parent object for this instance"
    ::= { ptSGSUAConfiguredASPsEntry 253 }

ptSGSUAConfiguredASPsRowStatus OBJECT-TYPE
    SYNTAX          RowStatus
    MAX-ACCESS      read-create
    STATUS          current
    DESCRIPTION     
            "The row status for the SGSUAConfiguredASPs table"
    ::= { ptSGSUAConfiguredASPsEntry 254 }

ptSGSUAConfiguredASPsIndex OBJECT-TYPE
    SYNTAX          Integer32 (-2147483648..2147483647)
    MAX-ACCESS      not-accessible
    STATUS          current
    DESCRIPTION     
            "The row number for the SGSUAConfiguredASPs table"
    ::= { ptSGSUAConfiguredASPsEntry 255 }

ptSGSUAConfiguredASP OBJECT IDENTIFIER
    ::= { ptSGSUAConfiguredASPs 212 }

ptSGSUAConfiguredASPTable OBJECT-TYPE
    SYNTAX          SEQUENCE OF PtSGSUAConfiguredASPEntry
    MAX-ACCESS      not-accessible
    STATUS          current
    DESCRIPTION     
            "No description supplied in the proxy config file."
    ::= { ptSGSUAConfiguredASP 1 }

ptSGSUAConfiguredASPEntry OBJECT-TYPE
    SYNTAX          PtSGSUAConfiguredASPEntry
    MAX-ACCESS      not-accessible
    STATUS          current
    DESCRIPTION     
            "A sequence of SGSUAConfiguredASP attributes."
    INDEX           { ptConnGroupIndex, ptSGSUAConfiguredASPSUAIndex, 
                      ptSGSUAConfiguredASPSUAConfiguredASPsIndex, 
                      ptSGSUAConfiguredASPIndex }
    ::= { ptSGSUAConfiguredASPTable 1 }

PtSGSUAConfiguredASPEntry ::=
    SEQUENCE {
        ptSGSUAConfiguredASPID          Integer32,
        ptSGSUAConfiguredASPPort        Integer32,
        ptSGSUAConfiguredASPIPAddress1  DisplayString,
        ptSGSUAConfiguredASPIPAddress2  DisplayString,
        ptSGSUAConfiguredASPASPIDValidation   INTEGER,
        ptSGSUAConfiguredASPIncomingAppID DisplayString,
        ptSGSUAConfiguredASPName        DisplayString,
        ptSGSUAConfiguredASPExtendedMessageSupport          INTEGER,
        ptSGSUAConfiguredASPUserActivated INTEGER,
        ptSGSUAConfiguredASPDefaultNetworkAppearance            INTEGER,
        ptSGSUAConfiguredASPIMFSupport  INTEGER,
        ptSGSUAConfiguredASPSUAIndex    Integer32,
        ptSGSUAConfiguredASPSUAConfiguredASPsIndex          Integer32,
        ptSGSUAConfiguredASPActions     INTEGER,
        ptSGSUAConfiguredASPParentOID   OBJECT IDENTIFIER,
        ptSGSUAConfiguredASPRowStatus   RowStatus,
        ptSGSUAConfiguredASPIndex       Integer32
    }

ptSGSUAConfiguredASPID OBJECT-TYPE
    SYNTAX          Integer32 (1..2147483647)
    MAX-ACCESS      read-only
    STATUS          current
    DESCRIPTION     
            "SUA configured ASP unique identifier."
    ::= { ptSGSUAConfiguredASPEntry 1 }

ptSGSUAConfiguredASPPort OBJECT-TYPE
    SYNTAX          Integer32 (-2147483648..2147483647)
    MAX-ACCESS      read-only
    STATUS          current
    DESCRIPTION     
            "Remote port from which ASP will connect."
    ::= { ptSGSUAConfiguredASPEntry 2 }

ptSGSUAConfiguredASPIPAddress1 OBJECT-TYPE
    SYNTAX          DisplayString (SIZE(0..255))
    MAX-ACCESS      read-only
    STATUS          current
    DESCRIPTION     
            "SUA Configured ASP primary address. This may be a hostname or an IP Address. If a hostname is used it must be provisioned either in /etc/hosts or via a properly-configured DNS Server and should resolve to a subset of the remote IP Addresses configured for the host where the ASP terminates. Hostname resolution is attempted periodically. This attribute defines the primary IP address specifying the SCTP primary path to the remote SCTP endpoint. If the resolution returns more than one IP address, no guarantee is made as to non-ambiguous definition of the SCTP primary path."
    ::= { ptSGSUAConfiguredASPEntry 3 }

ptSGSUAConfiguredASPIPAddress2 OBJECT-TYPE
    SYNTAX          DisplayString (SIZE(0..255))
    MAX-ACCESS      read-only
    STATUS          current
    DESCRIPTION     
            "SUA Configured ASP secondary address. This may be a hostname or an IP Address. If a hostname is used it must be provisioned either in /etc/hosts or via a properly-configured DNS Server and should resolve to a subset of the remote IP Addresses configured for the host where the ASP terminates. Hostname resolution is attempted periodically."
    ::= { ptSGSUAConfiguredASPEntry 4 }

ptSGSUAConfiguredASPASPIDValidation OBJECT-TYPE
    SYNTAX          INTEGER { disabled(0), enabled(1) }
    MAX-ACCESS      read-create
    STATUS          current
    DESCRIPTION     
            "It is highly recommended that for increased security that this attribute remain enabled. When enabled the ASP using the configured endpoint MUST either NOT send the ASP ID parameter OR send the preconfigured ID. If an ASP ID parameter contains an identifier other than what is preconfigured, an ERROR (Invalid ASP Identifier) will be sent. When disabled, the ASP Identifier contained in the ASPUP is not validated. This is typically useful when changing the ID used by the ASP is especially troublesome"
    ::= { ptSGSUAConfiguredASPEntry 5 }

ptSGSUAConfiguredASPIncomingAppID OBJECT-TYPE
    SYNTAX          DisplayString (SIZE(0..255))
    MAX-ACCESS      read-create
    STATUS          current
    DESCRIPTION     
            "SUA Incoming AppID for Gateway Screening. On creation, the attribute is defaulted to SUA_DEFAULT."
    ::= { ptSGSUAConfiguredASPEntry 6 }

ptSGSUAConfiguredASPName OBJECT-TYPE
    SYNTAX          DisplayString (SIZE(0..255))
    MAX-ACCESS      read-create
    STATUS          current
    DESCRIPTION     
            "SUA configured ASP name. \nAlphanumeric with dash and underscore for a maximum of 16 characters. \nAutomatically moved to upper-case. Must be unique in SUA. \nReserved value DYNAMIC for non-configured ASPs."
    ::= { ptSGSUAConfiguredASPEntry 7 }

ptSGSUAConfiguredASPExtendedMessageSupport OBJECT-TYPE
    SYNTAX          INTEGER { disabled(0), enabled(1) }
    MAX-ACCESS      read-create
    STATUS          current
    DESCRIPTION     
            "SUA support of extended message outgoing from this ASP. \nEnabled by default, the SUA data message Hop Counter parameter is forwarded as received into the SCCP UAP QoS parameter hop counter field. SCCP automatically converts the message to a XUDT(S) to include non-zero Hop Counter values. \nDisabling this feature ignores the SUA hop counter value and always send to SCCP the UAP QoS with a hop counter 0. SCCP will only generate and XUDT(S) message in this scenario if segmentation is required (too large MSU)."
    ::= { ptSGSUAConfiguredASPEntry 8 }

ptSGSUAConfiguredASPUserActivated OBJECT-TYPE
    SYNTAX          INTEGER { disabled(0), enabled(1) }
    MAX-ACCESS      read-only
    STATUS          current
    DESCRIPTION     
            "M3UA ASP Association User State (ENABLED/DISABLED)."
    ::= { ptSGSUAConfiguredASPEntry 18 }

ptSGSUAConfiguredASPDefaultNetworkAppearance OBJECT-TYPE
    SYNTAX          INTEGER { unset(-1) }
    MAX-ACCESS      read-create
    STATUS          current
    DESCRIPTION     
            "Upon receipt of an SUA message which does not contain a Routing Context or Network Appearance parameter, the SG uses this value to determine the destination SS7 network. If this value is UNSET (-1), the Default Network Appearance specified in the SUA SCTP Servers is used to determine the destination SS7 network. The Network Appearance must also be configured as an SCCP NA. The default value is UNSET. \nChanging this attribute value can impact traffic."
    ::= { ptSGSUAConfiguredASPEntry 19 }

ptSGSUAConfiguredASPIMFSupport OBJECT-TYPE
    SYNTAX          INTEGER { disabled(0), enabled(1) }
    MAX-ACCESS      read-create
    STATUS          current
    DESCRIPTION     
            "Integrated Monitoring Feed feature support for this ASP. \nIMF must be licensed to enable this attribute. IMF Support attributes can be cleared for all configured SUA ASPs simultaneously by using the Reset IMF action in the SUA Configured ASPs screen."
    ::= { ptSGSUAConfiguredASPEntry 20 }

ptSGSUAConfiguredASPSUAIndex OBJECT-TYPE
    SYNTAX          Integer32 (-2147483648..2147483647)
    MAX-ACCESS      not-accessible
    STATUS          current
    DESCRIPTION     
            "This is the index of the parent type for this object.
             This parent type is SUA."
    ::= { ptSGSUAConfiguredASPEntry 242 }

ptSGSUAConfiguredASPSUAConfiguredASPsIndex OBJECT-TYPE
    SYNTAX          Integer32 (-2147483648..2147483647)
    MAX-ACCESS      not-accessible
    STATUS          current
    DESCRIPTION     
            "This is the index of the parent type for this object.
             This parent type is SUAConfiguredASPs."
    ::= { ptSGSUAConfiguredASPEntry 243 }

ptSGSUAConfiguredASPActions OBJECT-TYPE
    SYNTAX          INTEGER { activate(1), deactivate(2) }
    MAX-ACCESS      read-create
    STATUS          current
    DESCRIPTION     
            "The OID of all possible actions for this instance"
    ::= { ptSGSUAConfiguredASPEntry 252 }

ptSGSUAConfiguredASPParentOID OBJECT-TYPE
    SYNTAX          OBJECT IDENTIFIER
    MAX-ACCESS      read-create
    STATUS          current
    DESCRIPTION     
            "The OID of the parent object for this instance"
    ::= { ptSGSUAConfiguredASPEntry 253 }

ptSGSUAConfiguredASPRowStatus OBJECT-TYPE
    SYNTAX          RowStatus
    MAX-ACCESS      read-create
    STATUS          current
    DESCRIPTION     
            "The row status for the SGSUAConfiguredASP table"
    ::= { ptSGSUAConfiguredASPEntry 254 }

ptSGSUAConfiguredASPIndex OBJECT-TYPE
    SYNTAX          Integer32 (-2147483648..2147483647)
    MAX-ACCESS      not-accessible
    STATUS          current
    DESCRIPTION     
            "The row number for the SGSUAConfiguredASP table"
    ::= { ptSGSUAConfiguredASPEntry 255 }

ptSGSUARoutingContext OBJECT IDENTIFIER
    ::= { ptSGSUAConfiguredASP 214 }

ptSGSUARoutingContextTable OBJECT-TYPE
    SYNTAX          SEQUENCE OF PtSGSUARoutingContextEntry
    MAX-ACCESS      not-accessible
    STATUS          current
    DESCRIPTION     
            "No description supplied in the proxy config file."
    ::= { ptSGSUARoutingContext 1 }

ptSGSUARoutingContextEntry OBJECT-TYPE
    SYNTAX          PtSGSUARoutingContextEntry
    MAX-ACCESS      not-accessible
    STATUS          current
    DESCRIPTION     
            "A sequence of SGSUARoutingContext attributes."
    INDEX           { ptConnGroupIndex, ptSGSUARoutingContextSUAIndex, 
                      ptSGSUARoutingContextSUAConfiguredASPsIndex, 
                      ptSGSUARoutingContextSUAConfiguredASPIndex, 
                      ptSGSUARoutingContextIndex }
    ::= { ptSGSUARoutingContextTable 1 }

PtSGSUARoutingContextEntry ::=
    SEQUENCE {
        ptSGSUARoutingContextRoutingContext   Integer32,
        ptSGSUARoutingContextRemoteRoutingContext         INTEGER,
        ptSGSUARoutingContextSUAIndex   Integer32,
        ptSGSUARoutingContextSUAConfiguredASPsIndex           Integer32,
        ptSGSUARoutingContextSUAConfiguredASPIndex          Integer32,
        ptSGSUARoutingContextParentOID  OBJECT IDENTIFIER,
        ptSGSUARoutingContextRowStatus  RowStatus,
        ptSGSUARoutingContextIndex      Integer32
    }

ptSGSUARoutingContextRoutingContext OBJECT-TYPE
    SYNTAX          Integer32 (1..2147483647)
    MAX-ACCESS      read-only
    STATUS          current
    DESCRIPTION     
            "Routing context."
    ::= { ptSGSUARoutingContextEntry 1 }

ptSGSUARoutingContextRemoteRoutingContext OBJECT-TYPE
    SYNTAX          INTEGER { undefined(-1) }
    MAX-ACCESS      read-create
    STATUS          current
    DESCRIPTION     
            "Remote routing context is used to connect a group of configured RCs. An ASP may go active for the group of RCs by sending a single ASP Active message containing only the remote routing context. All notifications and Acks pertaining to any AS in the group will contain the remote routing context. This feature should only be used when the ASP must send a single Routing Context but it needs register for more than one routing key. It can also be used in the case where a routing context is already configured for an AS and the ASP sends a different RC in the ASPAC message. To set the value to UNDEFINED, enter -1."
    ::= { ptSGSUARoutingContextEntry 2 }

ptSGSUARoutingContextSUAIndex OBJECT-TYPE
    SYNTAX          Integer32 (-2147483648..2147483647)
    MAX-ACCESS      not-accessible
    STATUS          current
    DESCRIPTION     
            "This is the index of the parent type for this object.
             This parent type is SUA."
    ::= { ptSGSUARoutingContextEntry 242 }

ptSGSUARoutingContextSUAConfiguredASPsIndex OBJECT-TYPE
    SYNTAX          Integer32 (-2147483648..2147483647)
    MAX-ACCESS      not-accessible
    STATUS          current
    DESCRIPTION     
            "This is the index of the parent type for this object.
             This parent type is SUAConfiguredASPs."
    ::= { ptSGSUARoutingContextEntry 243 }

ptSGSUARoutingContextSUAConfiguredASPIndex OBJECT-TYPE
    SYNTAX          Integer32 (-2147483648..2147483647)
    MAX-ACCESS      not-accessible
    STATUS          current
    DESCRIPTION     
            "This is the index of the parent type for this object.
             This parent type is SUAConfiguredASP."
    ::= { ptSGSUARoutingContextEntry 244 }

ptSGSUARoutingContextParentOID OBJECT-TYPE
    SYNTAX          OBJECT IDENTIFIER
    MAX-ACCESS      read-create
    STATUS          current
    DESCRIPTION     
            "The OID of the parent object for this instance"
    ::= { ptSGSUARoutingContextEntry 253 }

ptSGSUARoutingContextRowStatus OBJECT-TYPE
    SYNTAX          RowStatus
    MAX-ACCESS      read-create
    STATUS          current
    DESCRIPTION     
            "The row status for the SGSUARoutingContext table"
    ::= { ptSGSUARoutingContextEntry 254 }

ptSGSUARoutingContextIndex OBJECT-TYPE
    SYNTAX          Integer32 (-2147483648..2147483647)
    MAX-ACCESS      not-accessible
    STATUS          current
    DESCRIPTION     
            "The row number for the SGSUARoutingContext table"
    ::= { ptSGSUARoutingContextEntry 255 }

ptSGCICUA OBJECT IDENTIFIER
    ::= { ptConnGroup 217 }

ptSGCICUATable OBJECT-TYPE
    SYNTAX          SEQUENCE OF PtSGCICUAEntry
    MAX-ACCESS      not-accessible
    STATUS          current
    DESCRIPTION     
            "No description supplied in the proxy config file."
    ::= { ptSGCICUA 1 }

ptSGCICUAEntry OBJECT-TYPE
    SYNTAX          PtSGCICUAEntry
    MAX-ACCESS      not-accessible
    STATUS          current
    DESCRIPTION     
            "A sequence of SGCICUA attributes."
    INDEX           { ptConnGroupIndex, ptSGCICUAIndex }
    ::= { ptSGCICUATable 1 }

PtSGCICUAEntry ::=
    SEQUENCE {
        ptSGCICUAMessageAckTimer        INTEGER,
        ptSGCICUAExcessiveAckDelay      INTEGER,
        ptSGCICUAMessageLifespan        INTEGER,
        ptSGCICUAMonitoring             INTEGER,
        ptSGCICUAMaximumConnectionCapacity  Integer32,
        ptSGCICUAUsageLowerThreshold    INTEGER,
        ptSGCICUAUsageUpperThreshold    INTEGER,
        ptSGCICUAUsageIntervalMinutes   Integer32,
        ptSGCICUAUsageIntervalSeconds   Integer32,
        ptSGCICUAIMFSupport             INTEGER,
        ptSGCICUAActions                INTEGER,
        ptSGCICUAParentOID              OBJECT IDENTIFIER,
        ptSGCICUARowStatus              RowStatus,
        ptSGCICUAIndex                  Integer32
    }

ptSGCICUAMessageAckTimer OBJECT-TYPE
    SYNTAX          INTEGER { disabled(0) }
    MAX-ACCESS      read-create
    STATUS          current
    DESCRIPTION     
            "Message Acknowledgement Timer."
    ::= { ptSGCICUAEntry 1 }

ptSGCICUAExcessiveAckDelay OBJECT-TYPE
    SYNTAX          INTEGER { disabled(0) }
    MAX-ACCESS      read-create
    STATUS          current
    DESCRIPTION     
            "Detects excessive acknowledgement delay."
    ::= { ptSGCICUAEntry 2 }

ptSGCICUAMessageLifespan OBJECT-TYPE
    SYNTAX          INTEGER { disabled(0) }
    MAX-ACCESS      read-create
    STATUS          current
    DESCRIPTION     
            "Lifetime of a queued message."
    ::= { ptSGCICUAEntry 3 }

ptSGCICUAMonitoring OBJECT-TYPE
    SYNTAX          INTEGER { disabled(0), enabled(1) }
    MAX-ACCESS      read-only
    STATUS          current
    DESCRIPTION     
            "Monitoring feature (ENABLED/DISABLED)."
    ::= { ptSGCICUAEntry 4 }

ptSGCICUAMaximumConnectionCapacity OBJECT-TYPE
    SYNTAX          Integer32 (-2147483648..2147483647)
    MAX-ACCESS      read-create
    STATUS          current
    DESCRIPTION     
            "Maximum number of bytes per second sent on a AS connection."
    ::= { ptSGCICUAEntry 5 }

ptSGCICUAUsageLowerThreshold OBJECT-TYPE
    SYNTAX          INTEGER { default(-1) }
    MAX-ACCESS      read-create
    STATUS          current
    DESCRIPTION     
            "Percentage of the lower threshold for logging."
    ::= { ptSGCICUAEntry 6 }

ptSGCICUAUsageUpperThreshold OBJECT-TYPE
    SYNTAX          INTEGER { default(-1) }
    MAX-ACCESS      read-create
    STATUS          current
    DESCRIPTION     
            "Percentage of the upper threshold for logging."
    ::= { ptSGCICUAEntry 7 }

ptSGCICUAUsageIntervalMinutes OBJECT-TYPE
    SYNTAX          Integer32 (-2147483648..2147483647)
    MAX-ACCESS      read-create
    STATUS          current
    DESCRIPTION     
            "Interval in minutes used to calculate average traffic load."
    ::= { ptSGCICUAEntry 8 }

ptSGCICUAUsageIntervalSeconds OBJECT-TYPE
    SYNTAX          Integer32 (-2147483648..2147483647)
    MAX-ACCESS      read-create
    STATUS          current
    DESCRIPTION     
            "Interval in seconds used to calculate average traffic load."
    ::= { ptSGCICUAEntry 9 }

ptSGCICUAIMFSupport OBJECT-TYPE
    SYNTAX          INTEGER { disabled(0), enabled(1) }
    MAX-ACCESS      read-create
    STATUS          current
    DESCRIPTION     
            "Integrated Monitoring Feed feature support for CIC UA. \nIMF must be licensed to enable this attribute."
    ::= { ptSGCICUAEntry 10 }

ptSGCICUAActions OBJECT-TYPE
    SYNTAX          INTEGER { startMonitoring(1), stopMonitoring(2) }
    MAX-ACCESS      read-create
    STATUS          current
    DESCRIPTION     
            "The OID of all possible actions for this instance"
    ::= { ptSGCICUAEntry 252 }

ptSGCICUAParentOID OBJECT-TYPE
    SYNTAX          OBJECT IDENTIFIER
    MAX-ACCESS      read-create
    STATUS          current
    DESCRIPTION     
            "The OID of the parent object for this instance"
    ::= { ptSGCICUAEntry 253 }

ptSGCICUARowStatus OBJECT-TYPE
    SYNTAX          RowStatus
    MAX-ACCESS      read-create
    STATUS          current
    DESCRIPTION     
            "The row status for the SGCICUA table"
    ::= { ptSGCICUAEntry 254 }

ptSGCICUAIndex OBJECT-TYPE
    SYNTAX          Integer32 (-2147483648..2147483647)
    MAX-ACCESS      not-accessible
    STATUS          current
    DESCRIPTION     
            "The row number for the SGCICUA table"
    ::= { ptSGCICUAEntry 255 }

ptSGCICUAAppServers OBJECT IDENTIFIER
    ::= { ptSGCICUA 218 }

ptSGCICUAAppServersTable OBJECT-TYPE
    SYNTAX          SEQUENCE OF PtSGCICUAAppServersEntry
    MAX-ACCESS      not-accessible
    STATUS          current
    DESCRIPTION     
            "No description supplied in the proxy config file."
    ::= { ptSGCICUAAppServers 1 }

ptSGCICUAAppServersEntry OBJECT-TYPE
    SYNTAX          PtSGCICUAAppServersEntry
    MAX-ACCESS      not-accessible
    STATUS          current
    DESCRIPTION     
            "A sequence of SGCICUAAppServers attributes."
    INDEX           { ptConnGroupIndex, ptSGCICUAAppServersCICUAIndex, 
                      ptSGCICUAAppServersIndex }
    ::= { ptSGCICUAAppServersTable 1 }

PtSGCICUAAppServersEntry ::=
    SEQUENCE {
        ptSGCICUAAppServersCICUAIndex   Integer32,
        ptSGCICUAAppServersParentOID    OBJECT IDENTIFIER,
        ptSGCICUAAppServersRowStatus    RowStatus,
        ptSGCICUAAppServersIndex        Integer32
    }

ptSGCICUAAppServersCICUAIndex OBJECT-TYPE
    SYNTAX          Integer32 (-2147483648..2147483647)
    MAX-ACCESS      not-accessible
    STATUS          current
    DESCRIPTION     
            "This is the index of the parent type for this object.
             This parent type is CICUA."
    ::= { ptSGCICUAAppServersEntry 242 }

ptSGCICUAAppServersParentOID OBJECT-TYPE
    SYNTAX          OBJECT IDENTIFIER
    MAX-ACCESS      read-create
    STATUS          current
    DESCRIPTION     
            "The OID of the parent object for this instance"
    ::= { ptSGCICUAAppServersEntry 253 }

ptSGCICUAAppServersRowStatus OBJECT-TYPE
    SYNTAX          RowStatus
    MAX-ACCESS      read-create
    STATUS          current
    DESCRIPTION     
            "The row status for the SGCICUAAppServers table"
    ::= { ptSGCICUAAppServersEntry 254 }

ptSGCICUAAppServersIndex OBJECT-TYPE
    SYNTAX          Integer32 (-2147483648..2147483647)
    MAX-ACCESS      not-accessible
    STATUS          current
    DESCRIPTION     
            "The row number for the SGCICUAAppServers table"
    ::= { ptSGCICUAAppServersEntry 255 }

ptSGCICUAAppServer OBJECT IDENTIFIER
    ::= { ptSGCICUAAppServers 219 }

ptSGCICUAAppServerTable OBJECT-TYPE
    SYNTAX          SEQUENCE OF PtSGCICUAAppServerEntry
    MAX-ACCESS      not-accessible
    STATUS          current
    DESCRIPTION     
            "No description supplied in the proxy config file."
    ::= { ptSGCICUAAppServer 1 }

ptSGCICUAAppServerEntry OBJECT-TYPE
    SYNTAX          PtSGCICUAAppServerEntry
    MAX-ACCESS      not-accessible
    STATUS          current
    DESCRIPTION     
            "A sequence of SGCICUAAppServer attributes."
    INDEX           { ptConnGroupIndex, ptSGCICUAAppServerCICUAIndex, 
                      ptSGCICUAAppServerCICUAAppServersIndex, 
                      ptSGCICUAAppServerIndex }
    ::= { ptSGCICUAAppServerTable 1 }

PtSGCICUAAppServerEntry ::=
    SEQUENCE {
        ptSGCICUAAppServerNetworkAppearance   Integer32,
        ptSGCICUAAppServerDPC           Integer32,
        ptSGCICUAAppServerOPC           Integer32,
        ptSGCICUAAppServerSI            Integer32,
        ptSGCICUAAppServerStatus        INTEGER,
        ptSGCICUAAppServerCICUAIndex    Integer32,
        ptSGCICUAAppServerCICUAAppServersIndex      Integer32,
        ptSGCICUAAppServerParentOID     OBJECT IDENTIFIER,
        ptSGCICUAAppServerRowStatus     RowStatus,
        ptSGCICUAAppServerIndex         Integer32
    }

ptSGCICUAAppServerNetworkAppearance OBJECT-TYPE
    SYNTAX          Integer32 (-2147483648..2147483647)
    MAX-ACCESS      read-only
    STATUS          current
    DESCRIPTION     
            "CIC UA App Server Network Appearance."
    ::= { ptSGCICUAAppServerEntry 1 }

ptSGCICUAAppServerDPC OBJECT-TYPE
    SYNTAX          Integer32 (-2147483648..2147483647)
    MAX-ACCESS      read-only
    STATUS          current
    DESCRIPTION     
            "CIC UA App Server Destination Point Code."
    ::= { ptSGCICUAAppServerEntry 2 }

ptSGCICUAAppServerOPC OBJECT-TYPE
    SYNTAX          Integer32 (-2147483648..2147483647)
    MAX-ACCESS      read-only
    STATUS          current
    DESCRIPTION     
            "CIC UA App Server Originating Point Code."
    ::= { ptSGCICUAAppServerEntry 3 }

ptSGCICUAAppServerSI OBJECT-TYPE
    SYNTAX          Integer32 (-2147483648..2147483647)
    MAX-ACCESS      read-only
    STATUS          current
    DESCRIPTION     
            "CIC UA App Server Signaling Indicator."
    ::= { ptSGCICUAAppServerEntry 4 }

ptSGCICUAAppServerStatus OBJECT-TYPE
    SYNTAX          INTEGER { down(0), pendingReg(1), up(2) }
    MAX-ACCESS      read-only
    STATUS          current
    DESCRIPTION     
            "CIC UA App Server Status (UP/DOWN/PENDING REG)."
    ::= { ptSGCICUAAppServerEntry 5 }

ptSGCICUAAppServerCICUAIndex OBJECT-TYPE
    SYNTAX          Integer32 (-2147483648..2147483647)
    MAX-ACCESS      not-accessible
    STATUS          current
    DESCRIPTION     
            "This is the index of the parent type for this object.
             This parent type is CICUA."
    ::= { ptSGCICUAAppServerEntry 242 }

ptSGCICUAAppServerCICUAAppServersIndex OBJECT-TYPE
    SYNTAX          Integer32 (-2147483648..2147483647)
    MAX-ACCESS      not-accessible
    STATUS          current
    DESCRIPTION     
            "This is the index of the parent type for this object.
             This parent type is CICUAAppServers."
    ::= { ptSGCICUAAppServerEntry 243 }

ptSGCICUAAppServerParentOID OBJECT-TYPE
    SYNTAX          OBJECT IDENTIFIER
    MAX-ACCESS      read-create
    STATUS          current
    DESCRIPTION     
            "The OID of the parent object for this instance"
    ::= { ptSGCICUAAppServerEntry 253 }

ptSGCICUAAppServerRowStatus OBJECT-TYPE
    SYNTAX          RowStatus
    MAX-ACCESS      read-create
    STATUS          current
    DESCRIPTION     
            "The row status for the SGCICUAAppServer table"
    ::= { ptSGCICUAAppServerEntry 254 }

ptSGCICUAAppServerIndex OBJECT-TYPE
    SYNTAX          Integer32 (-2147483648..2147483647)
    MAX-ACCESS      not-accessible
    STATUS          current
    DESCRIPTION     
            "The row number for the SGCICUAAppServer table"
    ::= { ptSGCICUAAppServerEntry 255 }

ptSGCICUAASCIC OBJECT IDENTIFIER
    ::= { ptSGCICUAAppServer 220 }

ptSGCICUAASCICTable OBJECT-TYPE
    SYNTAX          SEQUENCE OF PtSGCICUAASCICEntry
    MAX-ACCESS      not-accessible
    STATUS          current
    DESCRIPTION     
            "No description supplied in the proxy config file."
    ::= { ptSGCICUAASCIC 1 }

ptSGCICUAASCICEntry OBJECT-TYPE
    SYNTAX          PtSGCICUAASCICEntry
    MAX-ACCESS      not-accessible
    STATUS          current
    DESCRIPTION     
            "A sequence of SGCICUAASCIC attributes."
    INDEX           { ptConnGroupIndex, ptSGCICUAASCICCICUAIndex, 
                      ptSGCICUAASCICCICUAAppServersIndex, 
                      ptSGCICUAASCICCICUAAppServerIndex, 
                      ptSGCICUAASCICIndex }
    ::= { ptSGCICUAASCICTable 1 }

PtSGCICUAASCICEntry ::=
    SEQUENCE {
        ptSGCICUAASCICASPID             Integer32,
        ptSGCICUAASCICCICMinimum        Integer32,
        ptSGCICUAASCICCICMaximum        Integer32,
        ptSGCICUAASCICCost              Integer32,
        ptSGCICUAASCICTransferType      INTEGER,
        ptSGCICUAASCICSlot              Integer32,
        ptSGCICUAASCICCICUAIndex        Integer32,
        ptSGCICUAASCICCICUAAppServersIndex  Integer32,
        ptSGCICUAASCICCICUAAppServerIndex Integer32,
        ptSGCICUAASCICParentOID         OBJECT IDENTIFIER,
        ptSGCICUAASCICRowStatus         RowStatus,
        ptSGCICUAASCICIndex             Integer32
    }

ptSGCICUAASCICASPID OBJECT-TYPE
    SYNTAX          Integer32 (-2147483648..2147483647)
    MAX-ACCESS      read-only
    STATUS          current
    DESCRIPTION     
            "Correlated ASP ID."
    ::= { ptSGCICUAASCICEntry 2 }

ptSGCICUAASCICCICMinimum OBJECT-TYPE
    SYNTAX          Integer32 (0..65355)
    MAX-ACCESS      read-only
    STATUS          current
    DESCRIPTION     
            "The minimum CIC in range."
    ::= { ptSGCICUAASCICEntry 3 }

ptSGCICUAASCICCICMaximum OBJECT-TYPE
    SYNTAX          Integer32 (0..65355)
    MAX-ACCESS      read-only
    STATUS          current
    DESCRIPTION     
            "The maximum CIC in range."
    ::= { ptSGCICUAASCICEntry 4 }

ptSGCICUAASCICCost OBJECT-TYPE
    SYNTAX          Integer32 (0..255)
    MAX-ACCESS      read-only
    STATUS          current
    DESCRIPTION     
            "The associated cost."
    ::= { ptSGCICUAASCICEntry 5 }

ptSGCICUAASCICTransferType OBJECT-TYPE
    SYNTAX          INTEGER { native(0), routingLabel(1), 
                        nativeConfirmed(2), routingLabelConfirmed(3) }
    MAX-ACCESS      read-only
    STATUS          current
    DESCRIPTION     
            "The associated transfer type."
    ::= { ptSGCICUAASCICEntry 6 }

ptSGCICUAASCICSlot OBJECT-TYPE
    SYNTAX          Integer32 (-2147483648..2147483647)
    MAX-ACCESS      read-only
    STATUS          current
    DESCRIPTION     
            "The associated slot."
    ::= { ptSGCICUAASCICEntry 7 }

ptSGCICUAASCICCICUAIndex OBJECT-TYPE
    SYNTAX          Integer32 (-2147483648..2147483647)
    MAX-ACCESS      not-accessible
    STATUS          current
    DESCRIPTION     
            "This is the index of the parent type for this object.
             This parent type is CICUA."
    ::= { ptSGCICUAASCICEntry 242 }

ptSGCICUAASCICCICUAAppServersIndex OBJECT-TYPE
    SYNTAX          Integer32 (-2147483648..2147483647)
    MAX-ACCESS      not-accessible
    STATUS          current
    DESCRIPTION     
            "This is the index of the parent type for this object.
             This parent type is CICUAAppServers."
    ::= { ptSGCICUAASCICEntry 243 }

ptSGCICUAASCICCICUAAppServerIndex OBJECT-TYPE
    SYNTAX          Integer32 (-2147483648..2147483647)
    MAX-ACCESS      not-accessible
    STATUS          current
    DESCRIPTION     
            "This is the index of the parent type for this object.
             This parent type is CICUAAppServer."
    ::= { ptSGCICUAASCICEntry 244 }

ptSGCICUAASCICParentOID OBJECT-TYPE
    SYNTAX          OBJECT IDENTIFIER
    MAX-ACCESS      read-create
    STATUS          current
    DESCRIPTION     
            "The OID of the parent object for this instance"
    ::= { ptSGCICUAASCICEntry 253 }

ptSGCICUAASCICRowStatus OBJECT-TYPE
    SYNTAX          RowStatus
    MAX-ACCESS      read-create
    STATUS          current
    DESCRIPTION     
            "The row status for the SGCICUAASCIC table"
    ::= { ptSGCICUAASCICEntry 254 }

ptSGCICUAASCICIndex OBJECT-TYPE
    SYNTAX          Integer32 (-2147483648..2147483647)
    MAX-ACCESS      not-accessible
    STATUS          current
    DESCRIPTION     
            "The row number for the SGCICUAASCIC table"
    ::= { ptSGCICUAASCICEntry 255 }

ptSGCICUAASPs OBJECT IDENTIFIER
    ::= { ptSGCICUA 222 }

ptSGCICUAASPsTable OBJECT-TYPE
    SYNTAX          SEQUENCE OF PtSGCICUAASPsEntry
    MAX-ACCESS      not-accessible
    STATUS          current
    DESCRIPTION     
            "No description supplied in the proxy config file."
    ::= { ptSGCICUAASPs 1 }

ptSGCICUAASPsEntry OBJECT-TYPE
    SYNTAX          PtSGCICUAASPsEntry
    MAX-ACCESS      not-accessible
    STATUS          current
    DESCRIPTION     
            "A sequence of SGCICUAASPs attributes."
    INDEX           { ptConnGroupIndex, ptSGCICUAASPsCICUAIndex, 
                      ptSGCICUAASPsIndex }
    ::= { ptSGCICUAASPsTable 1 }

PtSGCICUAASPsEntry ::=
    SEQUENCE {
        ptSGCICUAASPsCICUAIndex         Integer32,
        ptSGCICUAASPsParentOID          OBJECT IDENTIFIER,
        ptSGCICUAASPsRowStatus          RowStatus,
        ptSGCICUAASPsIndex              Integer32
    }

ptSGCICUAASPsCICUAIndex OBJECT-TYPE
    SYNTAX          Integer32 (-2147483648..2147483647)
    MAX-ACCESS      not-accessible
    STATUS          current
    DESCRIPTION     
            "This is the index of the parent type for this object.
             This parent type is CICUA."
    ::= { ptSGCICUAASPsEntry 242 }

ptSGCICUAASPsParentOID OBJECT-TYPE
    SYNTAX          OBJECT IDENTIFIER
    MAX-ACCESS      read-create
    STATUS          current
    DESCRIPTION     
            "The OID of the parent object for this instance"
    ::= { ptSGCICUAASPsEntry 253 }

ptSGCICUAASPsRowStatus OBJECT-TYPE
    SYNTAX          RowStatus
    MAX-ACCESS      read-create
    STATUS          current
    DESCRIPTION     
            "The row status for the SGCICUAASPs table"
    ::= { ptSGCICUAASPsEntry 254 }

ptSGCICUAASPsIndex OBJECT-TYPE
    SYNTAX          Integer32 (-2147483648..2147483647)
    MAX-ACCESS      not-accessible
    STATUS          current
    DESCRIPTION     
            "The row number for the SGCICUAASPs table"
    ::= { ptSGCICUAASPsEntry 255 }

ptSGCICUAASP OBJECT IDENTIFIER
    ::= { ptSGCICUAASPs 223 }

ptSGCICUAASPTable OBJECT-TYPE
    SYNTAX          SEQUENCE OF PtSGCICUAASPEntry
    MAX-ACCESS      not-accessible
    STATUS          current
    DESCRIPTION     
            "No description supplied in the proxy config file."
    ::= { ptSGCICUAASP 1 }

ptSGCICUAASPEntry OBJECT-TYPE
    SYNTAX          PtSGCICUAASPEntry
    MAX-ACCESS      not-accessible
    STATUS          current
    DESCRIPTION     
            "A sequence of SGCICUAASP attributes."
    INDEX           { ptConnGroupIndex, ptSGCICUAASPCICUAIndex, 
                      ptSGCICUAASPCICUAASPsIndex, ptSGCICUAASPIndex }
    ::= { ptSGCICUAASPTable 1 }

PtSGCICUAASPEntry ::=
    SEQUENCE {
        ptSGCICUAASPHost                DisplayString,
        ptSGCICUAASPPort                Integer32,
        ptSGCICUAASPASPID               Integer32,
        ptSGCICUAASPSlot                Integer32,
        ptSGCICUAASPCICUAIndex          Integer32,
        ptSGCICUAASPCICUAASPsIndex      Integer32,
        ptSGCICUAASPParentOID           OBJECT IDENTIFIER,
        ptSGCICUAASPRowStatus           RowStatus,
        ptSGCICUAASPIndex               Integer32
    }

ptSGCICUAASPHost OBJECT-TYPE
    SYNTAX          DisplayString (SIZE(0..255))
    MAX-ACCESS      read-only
    STATUS          current
    DESCRIPTION     
            "CIC UA ASP Host (remote)."
    ::= { ptSGCICUAASPEntry 1 }

ptSGCICUAASPPort OBJECT-TYPE
    SYNTAX          Integer32 (-2147483648..2147483647)
    MAX-ACCESS      read-only
    STATUS          current
    DESCRIPTION     
            "CIC UA ASP Port (remote)."
    ::= { ptSGCICUAASPEntry 2 }

ptSGCICUAASPASPID OBJECT-TYPE
    SYNTAX          Integer32 (-2147483648..2147483647)
    MAX-ACCESS      read-only
    STATUS          current
    DESCRIPTION     
            "CIC UA ASP unique identifier."
    ::= { ptSGCICUAASPEntry 3 }

ptSGCICUAASPSlot OBJECT-TYPE
    SYNTAX          Integer32 (-2147483648..2147483647)
    MAX-ACCESS      read-only
    STATUS          current
    DESCRIPTION     
            "CIC UA ASP Slot."
    ::= { ptSGCICUAASPEntry 4 }

ptSGCICUAASPCICUAIndex OBJECT-TYPE
    SYNTAX          Integer32 (-2147483648..2147483647)
    MAX-ACCESS      not-accessible
    STATUS          current
    DESCRIPTION     
            "This is the index of the parent type for this object.
             This parent type is CICUA."
    ::= { ptSGCICUAASPEntry 242 }

ptSGCICUAASPCICUAASPsIndex OBJECT-TYPE
    SYNTAX          Integer32 (-2147483648..2147483647)
    MAX-ACCESS      not-accessible
    STATUS          current
    DESCRIPTION     
            "This is the index of the parent type for this object.
             This parent type is CICUAASPs."
    ::= { ptSGCICUAASPEntry 243 }

ptSGCICUAASPParentOID OBJECT-TYPE
    SYNTAX          OBJECT IDENTIFIER
    MAX-ACCESS      read-create
    STATUS          current
    DESCRIPTION     
            "The OID of the parent object for this instance"
    ::= { ptSGCICUAASPEntry 253 }

ptSGCICUAASPRowStatus OBJECT-TYPE
    SYNTAX          RowStatus
    MAX-ACCESS      read-create
    STATUS          current
    DESCRIPTION     
            "The row status for the SGCICUAASP table"
    ::= { ptSGCICUAASPEntry 254 }

ptSGCICUAASPIndex OBJECT-TYPE
    SYNTAX          Integer32 (-2147483648..2147483647)
    MAX-ACCESS      not-accessible
    STATUS          current
    DESCRIPTION     
            "The row number for the SGCICUAASP table"
    ::= { ptSGCICUAASPEntry 255 }

ptSGCICUATCPServer OBJECT IDENTIFIER
    ::= { ptSGCICUA 224 }

ptSGCICUATCPServerTable OBJECT-TYPE
    SYNTAX          SEQUENCE OF PtSGCICUATCPServerEntry
    MAX-ACCESS      not-accessible
    STATUS          current
    DESCRIPTION     
            "No description supplied in the proxy config file."
    ::= { ptSGCICUATCPServer 1 }

ptSGCICUATCPServerEntry OBJECT-TYPE
    SYNTAX          PtSGCICUATCPServerEntry
    MAX-ACCESS      not-accessible
    STATUS          current
    DESCRIPTION     
            "A sequence of SGCICUATCPServer attributes."
    INDEX           { ptConnGroupIndex, ptSGCICUATCPServerCICUAIndex, 
                      ptSGCICUATCPServerIndex }
    ::= { ptSGCICUATCPServerTable 1 }

PtSGCICUATCPServerEntry ::=
    SEQUENCE {
        ptSGCICUATCPServerDefaultNetworkAppearance          Integer32,
        ptSGCICUATCPServerPort          Integer32,
        ptSGCICUATCPServerStatus        INTEGER,
        ptSGCICUATCPServerKeepAliveTimer INTEGER,
        ptSGCICUATCPServerCICUAIndex    Integer32,
        ptSGCICUATCPServerActions       INTEGER,
        ptSGCICUATCPServerParentOID     OBJECT IDENTIFIER,
        ptSGCICUATCPServerRowStatus     RowStatus,
        ptSGCICUATCPServerIndex         Integer32
    }

ptSGCICUATCPServerDefaultNetworkAppearance OBJECT-TYPE
    SYNTAX          Integer32 (-2147483648..2147483647)
    MAX-ACCESS      read-create
    STATUS          current
    DESCRIPTION     
            "CIC UA default network appearance. \nIf the NA is not provided in the transfer message the default NA is used to select the MTP3 NA Connection. \nChanging this attribute value can impact traffic."
    ::= { ptSGCICUATCPServerEntry 1 }

ptSGCICUATCPServerPort OBJECT-TYPE
    SYNTAX          Integer32 (-2147483648..2147483647)
    MAX-ACCESS      read-create
    STATUS          current
    DESCRIPTION     
            "CIC UA TCP Server Port"
    ::= { ptSGCICUATCPServerEntry 2 }

ptSGCICUATCPServerStatus OBJECT-TYPE
    SYNTAX          INTEGER { disabled(0), enabled(1) }
    MAX-ACCESS      read-only
    STATUS          current
    DESCRIPTION     
            "CIC UA TCP Server Status."
    ::= { ptSGCICUATCPServerEntry 3 }

ptSGCICUATCPServerKeepAliveTimer OBJECT-TYPE
    SYNTAX          INTEGER { disabled(0) }
    MAX-ACCESS      read-create
    STATUS          current
    DESCRIPTION     
            "The Keep Alive timer is the interval between Keep Alive pulses on the TCP server connections. (ms)."
    ::= { ptSGCICUATCPServerEntry 4 }

ptSGCICUATCPServerCICUAIndex OBJECT-TYPE
    SYNTAX          Integer32 (-2147483648..2147483647)
    MAX-ACCESS      not-accessible
    STATUS          current
    DESCRIPTION     
            "This is the index of the parent type for this object.
             This parent type is CICUA."
    ::= { ptSGCICUATCPServerEntry 242 }

ptSGCICUATCPServerActions OBJECT-TYPE
    SYNTAX          INTEGER { activate(1), deactivate(2) }
    MAX-ACCESS      read-create
    STATUS          current
    DESCRIPTION     
            "The OID of all possible actions for this instance"
    ::= { ptSGCICUATCPServerEntry 252 }

ptSGCICUATCPServerParentOID OBJECT-TYPE
    SYNTAX          OBJECT IDENTIFIER
    MAX-ACCESS      read-create
    STATUS          current
    DESCRIPTION     
            "The OID of the parent object for this instance"
    ::= { ptSGCICUATCPServerEntry 253 }

ptSGCICUATCPServerRowStatus OBJECT-TYPE
    SYNTAX          RowStatus
    MAX-ACCESS      read-create
    STATUS          current
    DESCRIPTION     
            "The row status for the SGCICUATCPServer table"
    ::= { ptSGCICUATCPServerEntry 254 }

ptSGCICUATCPServerIndex OBJECT-TYPE
    SYNTAX          Integer32 (-2147483648..2147483647)
    MAX-ACCESS      not-accessible
    STATUS          current
    DESCRIPTION     
            "The row number for the SGCICUATCPServer table"
    ::= { ptSGCICUATCPServerEntry 255 }

ptSGMTP3NAs OBJECT IDENTIFIER
    ::= { ptConnGroup 250 }

ptSGMTP3NAsTable OBJECT-TYPE
    SYNTAX          SEQUENCE OF PtSGMTP3NAsEntry
    MAX-ACCESS      not-accessible
    STATUS          current
    DESCRIPTION     
            "No description supplied in the proxy config file."
    ::= { ptSGMTP3NAs 1 }

ptSGMTP3NAsEntry OBJECT-TYPE
    SYNTAX          PtSGMTP3NAsEntry
    MAX-ACCESS      not-accessible
    STATUS          current
    DESCRIPTION     
            "A sequence of SGMTP3NAs attributes."
    INDEX           { ptConnGroupIndex, ptSGMTP3NAsIndex }
    ::= { ptSGMTP3NAsTable 1 }

PtSGMTP3NAsEntry ::=
    SEQUENCE {
        ptSGMTP3NAsParentOID            OBJECT IDENTIFIER,
        ptSGMTP3NAsRowStatus            RowStatus,
        ptSGMTP3NAsIndex                Integer32
    }

ptSGMTP3NAsParentOID OBJECT-TYPE
    SYNTAX          OBJECT IDENTIFIER
    MAX-ACCESS      read-create
    STATUS          current
    DESCRIPTION     
            "The OID of the parent object for this instance"
    ::= { ptSGMTP3NAsEntry 253 }

ptSGMTP3NAsRowStatus OBJECT-TYPE
    SYNTAX          RowStatus
    MAX-ACCESS      read-create
    STATUS          current
    DESCRIPTION     
            "The row status for the SGMTP3NAs table"
    ::= { ptSGMTP3NAsEntry 254 }

ptSGMTP3NAsIndex OBJECT-TYPE
    SYNTAX          Integer32 (-2147483648..2147483647)
    MAX-ACCESS      not-accessible
    STATUS          current
    DESCRIPTION     
            "The row number for the SGMTP3NAs table"
    ::= { ptSGMTP3NAsEntry 255 }

ptSGMTP3NA OBJECT IDENTIFIER
    ::= { ptSGMTP3NAs 251 }

ptSGMTP3NATable OBJECT-TYPE
    SYNTAX          SEQUENCE OF PtSGMTP3NAEntry
    MAX-ACCESS      not-accessible
    STATUS          current
    DESCRIPTION     
            "No description supplied in the proxy config file."
    ::= { ptSGMTP3NA 1 }

ptSGMTP3NAEntry OBJECT-TYPE
    SYNTAX          PtSGMTP3NAEntry
    MAX-ACCESS      not-accessible
    STATUS          current
    DESCRIPTION     
            "A sequence of SGMTP3NA attributes."
    INDEX           { ptConnGroupIndex, ptSGMTP3NAMTP3NAsIndex, 
                      ptSGMTP3NAIndex }
    ::= { ptSGMTP3NATable 1 }

PtSGMTP3NAEntry ::=
    SEQUENCE {
        ptSGMTP3NANetworkAppearance     Integer32,
        ptSGMTP3NASS7Variant            INTEGER,
        ptSGMTP3NALocalPointCode        Integer32,
        ptSGMTP3NANAStatus              INTEGER,
        ptSGMTP3NAMTP3LocalStatus       INTEGER,
        ptSGMTP3NAKeepAliveTimer        INTEGER,
        ptSGMTP3NADeleteStatus          INTEGER,
        ptSGMTP3NARxMSGCount            Integer32,
        ptSGMTP3NATxMSGCount            Integer32,
        ptSGMTP3NAMTP3NAsIndex          Integer32,
        ptSGMTP3NAActions               INTEGER,
        ptSGMTP3NAParentOID             OBJECT IDENTIFIER,
        ptSGMTP3NARowStatus             RowStatus,
        ptSGMTP3NAIndex                 Integer32
    }

ptSGMTP3NANetworkAppearance OBJECT-TYPE
    SYNTAX          Integer32 (-2147483648..2147483647)
    MAX-ACCESS      read-only
    STATUS          current
    DESCRIPTION     
            "The MTP3 corresponding network appearance."
    ::= { ptSGMTP3NAEntry 1 }

ptSGMTP3NASS7Variant OBJECT-TYPE
    SYNTAX          INTEGER { undefined(255), ansi(1), itu(2), china(3), 
                        ntt(4), ttc(5) }
    MAX-ACCESS      read-only
    STATUS          current
    DESCRIPTION     
            "The MTP3 SS7 Variant for the given NA."
    ::= { ptSGMTP3NAEntry 2 }

ptSGMTP3NALocalPointCode OBJECT-TYPE
    SYNTAX          Integer32 (-2147483648..2147483647)
    MAX-ACCESS      read-only
    STATUS          current
    DESCRIPTION     
            "The MTP3 local point code for the given NA. \nA value of Undefined indicates that the LPC has not yet been received from the MTP3."
    ::= { ptSGMTP3NAEntry 3 }

ptSGMTP3NANAStatus OBJECT-TYPE
    SYNTAX          INTEGER { inactive(0), active(1) }
    MAX-ACCESS      read-only
    STATUS          current
    DESCRIPTION     
            "MTP3 NA activation status."
    ::= { ptSGMTP3NAEntry 4 }

ptSGMTP3NAMTP3LocalStatus OBJECT-TYPE
    SYNTAX          INTEGER { unavailable(0), available(1) }
    MAX-ACCESS      read-only
    STATUS          current
    DESCRIPTION     
            "Obsolete as of 9.1. MTP3 NA local status."
    ::= { ptSGMTP3NAEntry 5 }

ptSGMTP3NAKeepAliveTimer OBJECT-TYPE
    SYNTAX          INTEGER { disabled(0) }
    MAX-ACCESS      read-create
    STATUS          current
    DESCRIPTION     
            "The Keep Alive timer is the interval between Keep Alive pulses on the MTP3 NA Connections (ms)."
    ::= { ptSGMTP3NAEntry 6 }

ptSGMTP3NADeleteStatus OBJECT-TYPE
    SYNTAX          INTEGER { deletable(0), undeletable(1) }
    MAX-ACCESS      read-only
    STATUS          current
    DESCRIPTION     
            "MTP3 NA Delete status. If the NA is the C20 Core NA and it has previously synchronised with the C20 Core then the NA can only be deleted if the C20 Core has successfully responded to an NA Delete provisioning message."
    ::= { ptSGMTP3NAEntry 7 }

ptSGMTP3NARxMSGCount OBJECT-TYPE
    SYNTAX          Integer32 (-2147483648..2147483647)
    MAX-ACCESS      read-only
    STATUS          current
    DESCRIPTION     
            "Number Received Messages per second"
    ::= { ptSGMTP3NAEntry 8 }

ptSGMTP3NATxMSGCount OBJECT-TYPE
    SYNTAX          Integer32 (-2147483648..2147483647)
    MAX-ACCESS      read-only
    STATUS          current
    DESCRIPTION     
            "Number Transmitted Messages per second"
    ::= { ptSGMTP3NAEntry 9 }

ptSGMTP3NAMTP3NAsIndex OBJECT-TYPE
    SYNTAX          Integer32 (-2147483648..2147483647)
    MAX-ACCESS      not-accessible
    STATUS          current
    DESCRIPTION     
            "This is the index of the parent type for this object.
             This parent type is MTP3NAs."
    ::= { ptSGMTP3NAEntry 242 }

ptSGMTP3NAActions OBJECT-TYPE
    SYNTAX          INTEGER { activate(1), deactivate(2), 
                        c20CoreDelete(3), forceC20CoreDelete(4) }
    MAX-ACCESS      read-create
    STATUS          current
    DESCRIPTION     
            "The OID of all possible actions for this instance"
    ::= { ptSGMTP3NAEntry 252 }

ptSGMTP3NAParentOID OBJECT-TYPE
    SYNTAX          OBJECT IDENTIFIER
    MAX-ACCESS      read-create
    STATUS          current
    DESCRIPTION     
            "The OID of the parent object for this instance"
    ::= { ptSGMTP3NAEntry 253 }

ptSGMTP3NARowStatus OBJECT-TYPE
    SYNTAX          RowStatus
    MAX-ACCESS      read-create
    STATUS          current
    DESCRIPTION     
            "The row status for the SGMTP3NA table"
    ::= { ptSGMTP3NAEntry 254 }

ptSGMTP3NAIndex OBJECT-TYPE
    SYNTAX          Integer32 (-2147483648..2147483647)
    MAX-ACCESS      not-accessible
    STATUS          current
    DESCRIPTION     
            "The row number for the SGMTP3NA table"
    ::= { ptSGMTP3NAEntry 255 }

ptSGMTP3NAConnection OBJECT IDENTIFIER
    ::= { ptSGMTP3NA 252 }

ptSGMTP3NAConnectionTable OBJECT-TYPE
    SYNTAX          SEQUENCE OF PtSGMTP3NAConnectionEntry
    MAX-ACCESS      not-accessible
    STATUS          current
    DESCRIPTION     
            "No description supplied in the proxy config file."
    ::= { ptSGMTP3NAConnection 1 }

ptSGMTP3NAConnectionEntry OBJECT-TYPE
    SYNTAX          PtSGMTP3NAConnectionEntry
    MAX-ACCESS      not-accessible
    STATUS          current
    DESCRIPTION     
            "A sequence of SGMTP3NAConnection attributes."
    INDEX           { ptConnGroupIndex, ptSGMTP3NAConnectionMTP3NAsIndex, 
                      ptSGMTP3NAConnectionMTP3NAIndex, 
                      ptSGMTP3NAConnectionIndex }
    ::= { ptSGMTP3NAConnectionTable 1 }

PtSGMTP3NAConnectionEntry ::=
    SEQUENCE {
        ptSGMTP3NAConnectionSlot        Integer32,
        ptSGMTP3NAConnectionStatus      INTEGER,
        ptSGMTP3NAConnectionMTP3NAsIndex Integer32,
        ptSGMTP3NAConnectionMTP3NAIndex Integer32,
        ptSGMTP3NAConnectionParentOID   OBJECT IDENTIFIER,
        ptSGMTP3NAConnectionRowStatus   RowStatus,
        ptSGMTP3NAConnectionIndex       Integer32
    }

ptSGMTP3NAConnectionSlot OBJECT-TYPE
    SYNTAX          Integer32 (-2147483648..2147483647)
    MAX-ACCESS      read-only
    STATUS          current
    DESCRIPTION     
            "The MTP3 NA Connection corresponding slot."
    ::= { ptSGMTP3NAConnectionEntry 1 }

ptSGMTP3NAConnectionStatus OBJECT-TYPE
    SYNTAX          INTEGER { notConnected(0), connected(1) }
    MAX-ACCESS      read-only
    STATUS          current
    DESCRIPTION     
            "The MTP3 NA Connection status (CONNECTED/NOT CONNECTED)."
    ::= { ptSGMTP3NAConnectionEntry 2 }

ptSGMTP3NAConnectionMTP3NAsIndex OBJECT-TYPE
    SYNTAX          Integer32 (-2147483648..2147483647)
    MAX-ACCESS      not-accessible
    STATUS          current
    DESCRIPTION     
            "This is the index of the parent type for this object.
             This parent type is MTP3NAs."
    ::= { ptSGMTP3NAConnectionEntry 242 }

ptSGMTP3NAConnectionMTP3NAIndex OBJECT-TYPE
    SYNTAX          Integer32 (-2147483648..2147483647)
    MAX-ACCESS      not-accessible
    STATUS          current
    DESCRIPTION     
            "This is the index of the parent type for this object.
             This parent type is MTP3NA."
    ::= { ptSGMTP3NAConnectionEntry 243 }

ptSGMTP3NAConnectionParentOID OBJECT-TYPE
    SYNTAX          OBJECT IDENTIFIER
    MAX-ACCESS      read-create
    STATUS          current
    DESCRIPTION     
            "The OID of the parent object for this instance"
    ::= { ptSGMTP3NAConnectionEntry 253 }

ptSGMTP3NAConnectionRowStatus OBJECT-TYPE
    SYNTAX          RowStatus
    MAX-ACCESS      read-create
    STATUS          current
    DESCRIPTION     
            "The row status for the SGMTP3NAConnection table"
    ::= { ptSGMTP3NAConnectionEntry 254 }

ptSGMTP3NAConnectionIndex OBJECT-TYPE
    SYNTAX          Integer32 (-2147483648..2147483647)
    MAX-ACCESS      not-accessible
    STATUS          current
    DESCRIPTION     
            "The row number for the SGMTP3NAConnection table"
    ::= { ptSGMTP3NAConnectionEntry 255 }

ptSGSCCPNAs OBJECT IDENTIFIER
    ::= { ptConnGroup 255 }

ptSGSCCPNAsTable OBJECT-TYPE
    SYNTAX          SEQUENCE OF PtSGSCCPNAsEntry
    MAX-ACCESS      not-accessible
    STATUS          current
    DESCRIPTION     
            "No description supplied in the proxy config file."
    ::= { ptSGSCCPNAs 1 }

ptSGSCCPNAsEntry OBJECT-TYPE
    SYNTAX          PtSGSCCPNAsEntry
    MAX-ACCESS      not-accessible
    STATUS          current
    DESCRIPTION     
            "A sequence of SGSCCPNAs attributes."
    INDEX           { ptConnGroupIndex, ptSGSCCPNAsIndex }
    ::= { ptSGSCCPNAsTable 1 }

PtSGSCCPNAsEntry ::=
    SEQUENCE {
        ptSGSCCPNAsParentOID            OBJECT IDENTIFIER,
        ptSGSCCPNAsRowStatus            RowStatus,
        ptSGSCCPNAsIndex                Integer32
    }

ptSGSCCPNAsParentOID OBJECT-TYPE
    SYNTAX          OBJECT IDENTIFIER
    MAX-ACCESS      read-create
    STATUS          current
    DESCRIPTION     
            "The OID of the parent object for this instance"
    ::= { ptSGSCCPNAsEntry 253 }

ptSGSCCPNAsRowStatus OBJECT-TYPE
    SYNTAX          RowStatus
    MAX-ACCESS      read-create
    STATUS          current
    DESCRIPTION     
            "The row status for the SGSCCPNAs table"
    ::= { ptSGSCCPNAsEntry 254 }

ptSGSCCPNAsIndex OBJECT-TYPE
    SYNTAX          Integer32 (-2147483648..2147483647)
    MAX-ACCESS      not-accessible
    STATUS          current
    DESCRIPTION     
            "The row number for the SGSCCPNAs table"
    ::= { ptSGSCCPNAsEntry 255 }

ptSGSCCPNA OBJECT IDENTIFIER
    ::= { ptSGSCCPNAs 256 }

ptSGSCCPNATable OBJECT-TYPE
    SYNTAX          SEQUENCE OF PtSGSCCPNAEntry
    MAX-ACCESS      not-accessible
    STATUS          current
    DESCRIPTION     
            "No description supplied in the proxy config file."
    ::= { ptSGSCCPNA 1 }

ptSGSCCPNAEntry OBJECT-TYPE
    SYNTAX          PtSGSCCPNAEntry
    MAX-ACCESS      not-accessible
    STATUS          current
    DESCRIPTION     
            "A sequence of SGSCCPNA attributes."
    INDEX           { ptConnGroupIndex, ptSGSCCPNASCCPNAsIndex, 
                      ptSGSCCPNAIndex }
    ::= { ptSGSCCPNATable 1 }

PtSGSCCPNAEntry ::=
    SEQUENCE {
        ptSGSCCPNANetworkAppearance     Integer32,
        ptSGSCCPNASS7Variant            INTEGER,
        ptSGSCCPNALocalPointCode        Integer32,
        ptSGSCCPNANAStatus              INTEGER,
        ptSGSCCPNASCCPLocalStatus       INTEGER,
        ptSGSCCPNAKeepAliveTimer        INTEGER,
        ptSGSCCPNAAddressIndicatorEncoding  INTEGER,
        ptSGSCCPNARxMSGCount            Integer32,
        ptSGSCCPNATxMSGCount            Integer32,
        ptSGSCCPNASCCPNAsIndex          Integer32,
        ptSGSCCPNAActions               INTEGER,
        ptSGSCCPNAParentOID             OBJECT IDENTIFIER,
        ptSGSCCPNARowStatus             RowStatus,
        ptSGSCCPNAIndex                 Integer32
    }

ptSGSCCPNANetworkAppearance OBJECT-TYPE
    SYNTAX          Integer32 (-2147483648..2147483647)
    MAX-ACCESS      read-only
    STATUS          current
    DESCRIPTION     
            "The SCCP corresponding network appearance."
    ::= { ptSGSCCPNAEntry 1 }

ptSGSCCPNASS7Variant OBJECT-TYPE
    SYNTAX          INTEGER { undefined(255), ansi(1), itu(2), china(3), 
                        ntt(4), ttc(5) }
    MAX-ACCESS      read-only
    STATUS          current
    DESCRIPTION     
            "The SCCP SS7 Variant for the given NA."
    ::= { ptSGSCCPNAEntry 2 }

ptSGSCCPNALocalPointCode OBJECT-TYPE
    SYNTAX          Integer32 (-2147483648..2147483647)
    MAX-ACCESS      read-only
    STATUS          current
    DESCRIPTION     
            "The MTP3 local point code for the given NA. \nA value of Undefined indicates that the LPC has not yet been received from the SCCP."
    ::= { ptSGSCCPNAEntry 3 }

ptSGSCCPNANAStatus OBJECT-TYPE
    SYNTAX          INTEGER { inactive(0), active(1) }
    MAX-ACCESS      read-only
    STATUS          current
    DESCRIPTION     
            "SCCP NA activation status."
    ::= { ptSGSCCPNAEntry 4 }

ptSGSCCPNASCCPLocalStatus OBJECT-TYPE
    SYNTAX          INTEGER { unavailable(0), available(1) }
    MAX-ACCESS      read-only
    STATUS          current
    DESCRIPTION     
            "Obsolete as of 9.1. SCCP NA local status."
    ::= { ptSGSCCPNAEntry 5 }

ptSGSCCPNAKeepAliveTimer OBJECT-TYPE
    SYNTAX          INTEGER { disabled(0) }
    MAX-ACCESS      read-create
    STATUS          current
    DESCRIPTION     
            "The Keep Alive timer is the interval between Keep Alive pulses on the SCCP NA Connections (ms)."
    ::= { ptSGSCCPNAEntry 6 }

ptSGSCCPNAAddressIndicatorEncoding OBJECT-TYPE
    SYNTAX          INTEGER { international(0), national(1) }
    MAX-ACCESS      read-create
    STATUS          current
    DESCRIPTION     
            "Address Indicator Encoding is used to specify the encoding method of the SCCP Address parameters in message destined for the SS7 network.\n The default value is INTERNATIONAL and can only be set to NATIONAL for ANSI networks."
    ::= { ptSGSCCPNAEntry 7 }

ptSGSCCPNARxMSGCount OBJECT-TYPE
    SYNTAX          Integer32 (-2147483648..2147483647)
    MAX-ACCESS      read-only
    STATUS          current
    DESCRIPTION     
            "Number Received Messages per second"
    ::= { ptSGSCCPNAEntry 8 }

ptSGSCCPNATxMSGCount OBJECT-TYPE
    SYNTAX          Integer32 (-2147483648..2147483647)
    MAX-ACCESS      read-only
    STATUS          current
    DESCRIPTION     
            "Number Transmitted Messages per second"
    ::= { ptSGSCCPNAEntry 9 }

ptSGSCCPNASCCPNAsIndex OBJECT-TYPE
    SYNTAX          Integer32 (-2147483648..2147483647)
    MAX-ACCESS      not-accessible
    STATUS          current
    DESCRIPTION     
            "This is the index of the parent type for this object.
             This parent type is SCCPNAs."
    ::= { ptSGSCCPNAEntry 242 }

ptSGSCCPNAActions OBJECT-TYPE
    SYNTAX          INTEGER { activate(1), deactivate(2) }
    MAX-ACCESS      read-create
    STATUS          current
    DESCRIPTION     
            "The OID of all possible actions for this instance"
    ::= { ptSGSCCPNAEntry 252 }

ptSGSCCPNAParentOID OBJECT-TYPE
    SYNTAX          OBJECT IDENTIFIER
    MAX-ACCESS      read-create
    STATUS          current
    DESCRIPTION     
            "The OID of the parent object for this instance"
    ::= { ptSGSCCPNAEntry 253 }

ptSGSCCPNARowStatus OBJECT-TYPE
    SYNTAX          RowStatus
    MAX-ACCESS      read-create
    STATUS          current
    DESCRIPTION     
            "The row status for the SGSCCPNA table"
    ::= { ptSGSCCPNAEntry 254 }

ptSGSCCPNAIndex OBJECT-TYPE
    SYNTAX          Integer32 (-2147483648..2147483647)
    MAX-ACCESS      not-accessible
    STATUS          current
    DESCRIPTION     
            "The row number for the SGSCCPNA table"
    ::= { ptSGSCCPNAEntry 255 }

ptSGSCCPNAConnection OBJECT IDENTIFIER
    ::= { ptSGSCCPNA 257 }

ptSGSCCPNAConnectionTable OBJECT-TYPE
    SYNTAX          SEQUENCE OF PtSGSCCPNAConnectionEntry
    MAX-ACCESS      not-accessible
    STATUS          current
    DESCRIPTION     
            "No description supplied in the proxy config file."
    ::= { ptSGSCCPNAConnection 1 }

ptSGSCCPNAConnectionEntry OBJECT-TYPE
    SYNTAX          PtSGSCCPNAConnectionEntry
    MAX-ACCESS      not-accessible
    STATUS          current
    DESCRIPTION     
            "A sequence of SGSCCPNAConnection attributes."
    INDEX           { ptConnGroupIndex, ptSGSCCPNAConnectionSCCPNAsIndex, 
                      ptSGSCCPNAConnectionSCCPNAIndex, 
                      ptSGSCCPNAConnectionIndex }
    ::= { ptSGSCCPNAConnectionTable 1 }

PtSGSCCPNAConnectionEntry ::=
    SEQUENCE {
        ptSGSCCPNAConnectionSlot        Integer32,
        ptSGSCCPNAConnectionStatus      INTEGER,
        ptSGSCCPNAConnectionSCCPNAsIndex Integer32,
        ptSGSCCPNAConnectionSCCPNAIndex Integer32,
        ptSGSCCPNAConnectionParentOID   OBJECT IDENTIFIER,
        ptSGSCCPNAConnectionRowStatus   RowStatus,
        ptSGSCCPNAConnectionIndex       Integer32
    }

ptSGSCCPNAConnectionSlot OBJECT-TYPE
    SYNTAX          Integer32 (-2147483648..2147483647)
    MAX-ACCESS      read-only
    STATUS          current
    DESCRIPTION     
            "The SCCP NA Connection corresponding slot."
    ::= { ptSGSCCPNAConnectionEntry 1 }

ptSGSCCPNAConnectionStatus OBJECT-TYPE
    SYNTAX          INTEGER { notConnected(0), connected(1) }
    MAX-ACCESS      read-only
    STATUS          current
    DESCRIPTION     
            "The SCCP NA Connection status (CONNECTED/NOT CONNECTED)."
    ::= { ptSGSCCPNAConnectionEntry 2 }

ptSGSCCPNAConnectionSCCPNAsIndex OBJECT-TYPE
    SYNTAX          Integer32 (-2147483648..2147483647)
    MAX-ACCESS      not-accessible
    STATUS          current
    DESCRIPTION     
            "This is the index of the parent type for this object.
             This parent type is SCCPNAs."
    ::= { ptSGSCCPNAConnectionEntry 242 }

ptSGSCCPNAConnectionSCCPNAIndex OBJECT-TYPE
    SYNTAX          Integer32 (-2147483648..2147483647)
    MAX-ACCESS      not-accessible
    STATUS          current
    DESCRIPTION     
            "This is the index of the parent type for this object.
             This parent type is SCCPNA."
    ::= { ptSGSCCPNAConnectionEntry 243 }

ptSGSCCPNAConnectionParentOID OBJECT-TYPE
    SYNTAX          OBJECT IDENTIFIER
    MAX-ACCESS      read-create
    STATUS          current
    DESCRIPTION     
            "The OID of the parent object for this instance"
    ::= { ptSGSCCPNAConnectionEntry 253 }

ptSGSCCPNAConnectionRowStatus OBJECT-TYPE
    SYNTAX          RowStatus
    MAX-ACCESS      read-create
    STATUS          current
    DESCRIPTION     
            "The row status for the SGSCCPNAConnection table"
    ::= { ptSGSCCPNAConnectionEntry 254 }

ptSGSCCPNAConnectionIndex OBJECT-TYPE
    SYNTAX          Integer32 (-2147483648..2147483647)
    MAX-ACCESS      not-accessible
    STATUS          current
    DESCRIPTION     
            "The row number for the SGSCCPNAConnection table"
    ::= { ptSGSCCPNAConnectionEntry 255 }

ptSGSFGUA OBJECT IDENTIFIER
    ::= { ptConnGroup 260 }

ptSGSFGUATable OBJECT-TYPE
    SYNTAX          SEQUENCE OF PtSGSFGUAEntry
    MAX-ACCESS      not-accessible
    STATUS          current
    DESCRIPTION     
            "No description supplied in the proxy config file."
    ::= { ptSGSFGUA 1 }

ptSGSFGUAEntry OBJECT-TYPE
    SYNTAX          PtSGSFGUAEntry
    MAX-ACCESS      not-accessible
    STATUS          current
    DESCRIPTION     
            "A sequence of SGSFGUA attributes."
    INDEX           { ptConnGroupIndex, ptSGSFGUAIndex }
    ::= { ptSGSFGUATable 1 }

PtSGSFGUAEntry ::=
    SEQUENCE {
        ptSGSFGUAExchangeName           DisplayString,
        ptSGSFGUAExchangeStatus         INTEGER,
        ptSGSFGUAIncomingAppID          DisplayString,
        ptSGSFGUAParentOID              OBJECT IDENTIFIER,
        ptSGSFGUARowStatus              RowStatus,
        ptSGSFGUAIndex                  Integer32
    }

ptSGSFGUAExchangeName OBJECT-TYPE
    SYNTAX          DisplayString (SIZE(0..255))
    MAX-ACCESS      read-only
    STATUS          current
    DESCRIPTION     
            "SFG UA Exchange Name."
    ::= { ptSGSFGUAEntry 1 }

ptSGSFGUAExchangeStatus OBJECT-TYPE
    SYNTAX          INTEGER { notConnected(0), connected(1) }
    MAX-ACCESS      read-only
    STATUS          current
    DESCRIPTION     
            "SFG UA Exchange Status."
    ::= { ptSGSFGUAEntry 2 }

ptSGSFGUAIncomingAppID OBJECT-TYPE
    SYNTAX          DisplayString (SIZE(0..255))
    MAX-ACCESS      read-create
    STATUS          current
    DESCRIPTION     
            "SFG UA Incoming AppID for Gateway Screening."
    ::= { ptSGSFGUAEntry 3 }

ptSGSFGUAParentOID OBJECT-TYPE
    SYNTAX          OBJECT IDENTIFIER
    MAX-ACCESS      read-create
    STATUS          current
    DESCRIPTION     
            "The OID of the parent object for this instance"
    ::= { ptSGSFGUAEntry 253 }

ptSGSFGUARowStatus OBJECT-TYPE
    SYNTAX          RowStatus
    MAX-ACCESS      read-create
    STATUS          current
    DESCRIPTION     
            "The row status for the SGSFGUA table"
    ::= { ptSGSFGUAEntry 254 }

ptSGSFGUAIndex OBJECT-TYPE
    SYNTAX          Integer32 (-2147483648..2147483647)
    MAX-ACCESS      not-accessible
    STATUS          current
    DESCRIPTION     
            "The row number for the SGSFGUA table"
    ::= { ptSGSFGUAEntry 255 }

ptSGSFGUAAppServers OBJECT IDENTIFIER
    ::= { ptSGSFGUA 261 }

ptSGSFGUAAppServersTable OBJECT-TYPE
    SYNTAX          SEQUENCE OF PtSGSFGUAAppServersEntry
    MAX-ACCESS      not-accessible
    STATUS          current
    DESCRIPTION     
            "No description supplied in the proxy config file."
    ::= { ptSGSFGUAAppServers 1 }

ptSGSFGUAAppServersEntry OBJECT-TYPE
    SYNTAX          PtSGSFGUAAppServersEntry
    MAX-ACCESS      not-accessible
    STATUS          current
    DESCRIPTION     
            "A sequence of SGSFGUAAppServers attributes."
    INDEX           { ptConnGroupIndex, ptSGSFGUAAppServersSFGUAIndex, 
                      ptSGSFGUAAppServersIndex }
    ::= { ptSGSFGUAAppServersTable 1 }

PtSGSFGUAAppServersEntry ::=
    SEQUENCE {
        ptSGSFGUAAppServersSFGUAIndex   Integer32,
        ptSGSFGUAAppServersParentOID    OBJECT IDENTIFIER,
        ptSGSFGUAAppServersRowStatus    RowStatus,
        ptSGSFGUAAppServersIndex        Integer32
    }

ptSGSFGUAAppServersSFGUAIndex OBJECT-TYPE
    SYNTAX          Integer32 (-2147483648..2147483647)
    MAX-ACCESS      not-accessible
    STATUS          current
    DESCRIPTION     
            "This is the index of the parent type for this object.
             This parent type is SFGUA."
    ::= { ptSGSFGUAAppServersEntry 242 }

ptSGSFGUAAppServersParentOID OBJECT-TYPE
    SYNTAX          OBJECT IDENTIFIER
    MAX-ACCESS      read-create
    STATUS          current
    DESCRIPTION     
            "The OID of the parent object for this instance"
    ::= { ptSGSFGUAAppServersEntry 253 }

ptSGSFGUAAppServersRowStatus OBJECT-TYPE
    SYNTAX          RowStatus
    MAX-ACCESS      read-create
    STATUS          current
    DESCRIPTION     
            "The row status for the SGSFGUAAppServers table"
    ::= { ptSGSFGUAAppServersEntry 254 }

ptSGSFGUAAppServersIndex OBJECT-TYPE
    SYNTAX          Integer32 (-2147483648..2147483647)
    MAX-ACCESS      not-accessible
    STATUS          current
    DESCRIPTION     
            "The row number for the SGSFGUAAppServers table"
    ::= { ptSGSFGUAAppServersEntry 255 }

ptSGSFGUAMTP3AppServer OBJECT IDENTIFIER
    ::= { ptSGSFGUAAppServers 262 }

ptSGSFGUAMTP3AppServerTable OBJECT-TYPE
    SYNTAX          SEQUENCE OF PtSGSFGUAMTP3AppServerEntry
    MAX-ACCESS      not-accessible
    STATUS          current
    DESCRIPTION     
            "No description supplied in the proxy config file."
    ::= { ptSGSFGUAMTP3AppServer 1 }

ptSGSFGUAMTP3AppServerEntry OBJECT-TYPE
    SYNTAX          PtSGSFGUAMTP3AppServerEntry
    MAX-ACCESS      not-accessible
    STATUS          current
    DESCRIPTION     
            "A sequence of SGSFGUAMTP3AppServer attributes."
    INDEX           { ptConnGroupIndex, ptSGSFGUAMTP3AppServerSFGUAIndex, 
                      ptSGSFGUAMTP3AppServerSFGUAAppServersIndex, 
                      ptSGSFGUAMTP3AppServerIndex }
    ::= { ptSGSFGUAMTP3AppServerTable 1 }

PtSGSFGUAMTP3AppServerEntry ::=
    SEQUENCE {
        ptSGSFGUAMTP3AppServerRoutingContext    Integer32,
        ptSGSFGUAMTP3AppServerNetworkAppearance       Integer32,
        ptSGSFGUAMTP3AppServerPC        Integer32,
        ptSGSFGUAMTP3AppServerSI        Integer32,
        ptSGSFGUAMTP3AppServerApplicationID   DisplayString,
        ptSGSFGUAMTP3AppServerServiceHandlerID      Integer32,
        ptSGSFGUAMTP3AppServerStatus    INTEGER,
        ptSGSFGUAMTP3AppServerSFGUAIndex Integer32,
        ptSGSFGUAMTP3AppServerSFGUAAppServersIndex          Integer32,
        ptSGSFGUAMTP3AppServerParentOID OBJECT IDENTIFIER,
        ptSGSFGUAMTP3AppServerRowStatus RowStatus,
        ptSGSFGUAMTP3AppServerIndex     Integer32
    }

ptSGSFGUAMTP3AppServerRoutingContext OBJECT-TYPE
    SYNTAX          Integer32 (1..2147483647)
    MAX-ACCESS      read-only
    STATUS          current
    DESCRIPTION     
            "SFG UA MTP3 App Server Routing Context."
    ::= { ptSGSFGUAMTP3AppServerEntry 1 }

ptSGSFGUAMTP3AppServerNetworkAppearance OBJECT-TYPE
    SYNTAX          Integer32 (-2147483648..2147483647)
    MAX-ACCESS      read-only
    STATUS          current
    DESCRIPTION     
            "SFG UA MTP3 App Server Network Appearance."
    ::= { ptSGSFGUAMTP3AppServerEntry 2 }

ptSGSFGUAMTP3AppServerPC OBJECT-TYPE
    SYNTAX          Integer32 (-2147483648..2147483647)
    MAX-ACCESS      read-only
    STATUS          current
    DESCRIPTION     
            "SFG UA MTP3 App Server Point Code (optional)."
    ::= { ptSGSFGUAMTP3AppServerEntry 3 }

ptSGSFGUAMTP3AppServerSI OBJECT-TYPE
    SYNTAX          Integer32 (-2147483648..2147483647)
    MAX-ACCESS      read-only
    STATUS          current
    DESCRIPTION     
            "SFG UA MTP3 App Server Signaling Indicator (optional)."
    ::= { ptSGSFGUAMTP3AppServerEntry 4 }

ptSGSFGUAMTP3AppServerApplicationID OBJECT-TYPE
    SYNTAX          DisplayString (SIZE(0..255))
    MAX-ACCESS      read-only
    STATUS          current
    DESCRIPTION     
            "SFG UA MTP3 App Server Application ID (optional)."
    ::= { ptSGSFGUAMTP3AppServerEntry 5 }

ptSGSFGUAMTP3AppServerServiceHandlerID OBJECT-TYPE
    SYNTAX          Integer32
    MAX-ACCESS      read-only
    STATUS          current
    DESCRIPTION     
            "SFG UA MTP3 App Server Service Handler ID."
    ::= { ptSGSFGUAMTP3AppServerEntry 6 }

ptSGSFGUAMTP3AppServerStatus OBJECT-TYPE
    SYNTAX          INTEGER { down(0), pendingReg(1), up(2) }
    MAX-ACCESS      read-only
    STATUS          current
    DESCRIPTION     
            "SFG UA MTP3 App Server Status (UP/DOWN/PENDING REG)."
    ::= { ptSGSFGUAMTP3AppServerEntry 7 }

ptSGSFGUAMTP3AppServerSFGUAIndex OBJECT-TYPE
    SYNTAX          Integer32 (-2147483648..2147483647)
    MAX-ACCESS      not-accessible
    STATUS          current
    DESCRIPTION     
            "This is the index of the parent type for this object.
             This parent type is SFGUA."
    ::= { ptSGSFGUAMTP3AppServerEntry 242 }

ptSGSFGUAMTP3AppServerSFGUAAppServersIndex OBJECT-TYPE
    SYNTAX          Integer32 (-2147483648..2147483647)
    MAX-ACCESS      not-accessible
    STATUS          current
    DESCRIPTION     
            "This is the index of the parent type for this object.
             This parent type is SFGUAAppServers."
    ::= { ptSGSFGUAMTP3AppServerEntry 243 }

ptSGSFGUAMTP3AppServerParentOID OBJECT-TYPE
    SYNTAX          OBJECT IDENTIFIER
    MAX-ACCESS      read-create
    STATUS          current
    DESCRIPTION     
            "The OID of the parent object for this instance"
    ::= { ptSGSFGUAMTP3AppServerEntry 253 }

ptSGSFGUAMTP3AppServerRowStatus OBJECT-TYPE
    SYNTAX          RowStatus
    MAX-ACCESS      read-create
    STATUS          current
    DESCRIPTION     
            "The row status for the SGSFGUAMTP3AppServer table"
    ::= { ptSGSFGUAMTP3AppServerEntry 254 }

ptSGSFGUAMTP3AppServerIndex OBJECT-TYPE
    SYNTAX          Integer32 (-2147483648..2147483647)
    MAX-ACCESS      not-accessible
    STATUS          current
    DESCRIPTION     
            "The row number for the SGSFGUAMTP3AppServer table"
    ::= { ptSGSFGUAMTP3AppServerEntry 255 }

ptSGSFGUASCCPAppServer OBJECT IDENTIFIER
    ::= { ptSGSFGUAAppServers 263 }

ptSGSFGUASCCPAppServerTable OBJECT-TYPE
    SYNTAX          SEQUENCE OF PtSGSFGUASCCPAppServerEntry
    MAX-ACCESS      not-accessible
    STATUS          current
    DESCRIPTION     
            "No description supplied in the proxy config file."
    ::= { ptSGSFGUASCCPAppServer 1 }

ptSGSFGUASCCPAppServerEntry OBJECT-TYPE
    SYNTAX          PtSGSFGUASCCPAppServerEntry
    MAX-ACCESS      not-accessible
    STATUS          current
    DESCRIPTION     
            "A sequence of SGSFGUASCCPAppServer attributes."
    INDEX           { ptConnGroupIndex, ptSGSFGUASCCPAppServerSFGUAIndex, 
                      ptSGSFGUASCCPAppServerSFGUAAppServersIndex, 
                      ptSGSFGUASCCPAppServerIndex }
    ::= { ptSGSFGUASCCPAppServerTable 1 }

PtSGSFGUASCCPAppServerEntry ::=
    SEQUENCE {
        ptSGSFGUASCCPAppServerRoutingContext    Integer32,
        ptSGSFGUASCCPAppServerNetworkAppearance       Integer32,
        ptSGSFGUASCCPAppServerPC        Integer32,
        ptSGSFGUASCCPAppServerSSN       Integer32,
        ptSGSFGUASCCPAppServerApplicationID   DisplayString,
        ptSGSFGUASCCPAppServerServiceHandlerID      Integer32,
        ptSGSFGUASCCPAppServerStatus    INTEGER,
        ptSGSFGUASCCPAppServerSFGUAIndex Integer32,
        ptSGSFGUASCCPAppServerSFGUAAppServersIndex          Integer32,
        ptSGSFGUASCCPAppServerParentOID OBJECT IDENTIFIER,
        ptSGSFGUASCCPAppServerRowStatus RowStatus,
        ptSGSFGUASCCPAppServerIndex     Integer32
    }

ptSGSFGUASCCPAppServerRoutingContext OBJECT-TYPE
    SYNTAX          Integer32 (1..2147483647)
    MAX-ACCESS      read-only
    STATUS          current
    DESCRIPTION     
            "SFG UA SCCP App Server Routing Context."
    ::= { ptSGSFGUASCCPAppServerEntry 1 }

ptSGSFGUASCCPAppServerNetworkAppearance OBJECT-TYPE
    SYNTAX          Integer32 (-2147483648..2147483647)
    MAX-ACCESS      read-only
    STATUS          current
    DESCRIPTION     
            "SFG UA SCCP App Server Network Appearance."
    ::= { ptSGSFGUASCCPAppServerEntry 2 }

ptSGSFGUASCCPAppServerPC OBJECT-TYPE
    SYNTAX          Integer32 (-2147483648..2147483647)
    MAX-ACCESS      read-only
    STATUS          current
    DESCRIPTION     
            "SFG UA SCCP App Server Point Code (optional)."
    ::= { ptSGSFGUASCCPAppServerEntry 3 }

ptSGSFGUASCCPAppServerSSN OBJECT-TYPE
    SYNTAX          Integer32 (-2147483648..2147483647)
    MAX-ACCESS      read-only
    STATUS          current
    DESCRIPTION     
            "SFG UA SCCP App Server Sub-System Number (optional)."
    ::= { ptSGSFGUASCCPAppServerEntry 4 }

ptSGSFGUASCCPAppServerApplicationID OBJECT-TYPE
    SYNTAX          DisplayString (SIZE(0..255))
    MAX-ACCESS      read-only
    STATUS          current
    DESCRIPTION     
            "SFG UA SCCP App Server Application ID (optional)."
    ::= { ptSGSFGUASCCPAppServerEntry 5 }

ptSGSFGUASCCPAppServerServiceHandlerID OBJECT-TYPE
    SYNTAX          Integer32
    MAX-ACCESS      read-only
    STATUS          current
    DESCRIPTION     
            "SFG UA SCCP App Server Service Handler ID."
    ::= { ptSGSFGUASCCPAppServerEntry 6 }

ptSGSFGUASCCPAppServerStatus OBJECT-TYPE
    SYNTAX          INTEGER { down(0), pendingReg(1), up(2) }
    MAX-ACCESS      read-only
    STATUS          current
    DESCRIPTION     
            "SFG UA SCCP App Server Status (UP/DOWN/PENDING REG)."
    ::= { ptSGSFGUASCCPAppServerEntry 7 }

ptSGSFGUASCCPAppServerSFGUAIndex OBJECT-TYPE
    SYNTAX          Integer32 (-2147483648..2147483647)
    MAX-ACCESS      not-accessible
    STATUS          current
    DESCRIPTION     
            "This is the index of the parent type for this object.
             This parent type is SFGUA."
    ::= { ptSGSFGUASCCPAppServerEntry 242 }

ptSGSFGUASCCPAppServerSFGUAAppServersIndex OBJECT-TYPE
    SYNTAX          Integer32 (-2147483648..2147483647)
    MAX-ACCESS      not-accessible
    STATUS          current
    DESCRIPTION     
            "This is the index of the parent type for this object.
             This parent type is SFGUAAppServers."
    ::= { ptSGSFGUASCCPAppServerEntry 243 }

ptSGSFGUASCCPAppServerParentOID OBJECT-TYPE
    SYNTAX          OBJECT IDENTIFIER
    MAX-ACCESS      read-create
    STATUS          current
    DESCRIPTION     
            "The OID of the parent object for this instance"
    ::= { ptSGSFGUASCCPAppServerEntry 253 }

ptSGSFGUASCCPAppServerRowStatus OBJECT-TYPE
    SYNTAX          RowStatus
    MAX-ACCESS      read-create
    STATUS          current
    DESCRIPTION     
            "The row status for the SGSFGUASCCPAppServer table"
    ::= { ptSGSFGUASCCPAppServerEntry 254 }

ptSGSFGUASCCPAppServerIndex OBJECT-TYPE
    SYNTAX          Integer32 (-2147483648..2147483647)
    MAX-ACCESS      not-accessible
    STATUS          current
    DESCRIPTION     
            "The row number for the SGSFGUASCCPAppServer table"
    ::= { ptSGSFGUASCCPAppServerEntry 255 }

ptConfiguration OBJECT IDENTIFIER
    ::= { ptConnGroup 306 }

ptConfigurationTable OBJECT-TYPE
    SYNTAX          SEQUENCE OF PtConfigurationEntry
    MAX-ACCESS      not-accessible
    STATUS          current
    DESCRIPTION     
            "No description supplied in the proxy config file."
    ::= { ptConfiguration 1 }

ptConfigurationEntry OBJECT-TYPE
    SYNTAX          PtConfigurationEntry
    MAX-ACCESS      not-accessible
    STATUS          current
    DESCRIPTION     
            "A sequence of Configuration attributes."
    INDEX           { ptConnGroupIndex, ptConfigurationIndex }
    ::= { ptConfigurationTable 1 }

PtConfigurationEntry ::=
    SEQUENCE {
        ptConfigurationCLIPort          Integer32,
        ptConfigurationAppletPort       Integer32,
        ptConfigurationGUIPort          Integer32,
        ptConfigurationTL1Port          Integer32,
        ptConfigurationConfigurationFile DisplayString,
        ptConfigurationTrapCommunity    DisplayString,
        ptConfigurationCurrentSequenceNumber    Integer32,
        ptConfigurationSystemName       DisplayString,
        ptConfigurationSingleIntervalStatsFiles       INTEGER,
        ptConfigurationSoftwareVersionInstalled       DisplayString,
        ptConfigurationSingleTrapStream INTEGER,
        ptConfigurationDSCRESTAPI       INTEGER,
        ptConfigurationActiveTraps      INTEGER,
        ptConfigurationParentOID        OBJECT IDENTIFIER,
        ptConfigurationRowStatus        RowStatus,
        ptConfigurationIndex            Integer32
    }

ptConfigurationCLIPort OBJECT-TYPE
    SYNTAX          Integer32 (-32768..32767)
    MAX-ACCESS      read-only
    STATUS          current
    DESCRIPTION     
            "This attribute displays the port used for CLI communication."
    ::= { ptConfigurationEntry 1 }

ptConfigurationAppletPort OBJECT-TYPE
    SYNTAX          Integer32 (-32768..32767)
    MAX-ACCESS      read-only
    STATUS          current
    DESCRIPTION     
            "Obsolete."
    ::= { ptConfigurationEntry 2 }

ptConfigurationGUIPort OBJECT-TYPE
    SYNTAX          Integer32 (-32768..32767)
    MAX-ACCESS      read-only
    STATUS          current
    DESCRIPTION     
            "This attribute displays the port used for the text GUI communication."
    ::= { ptConfigurationEntry 3 }

ptConfigurationTL1Port OBJECT-TYPE
    SYNTAX          Integer32 (-32768..32767)
    MAX-ACCESS      read-only
    STATUS          current
    DESCRIPTION     
            "This attribute displays the port used for TL1 communication."
    ::= { ptConfigurationEntry 4 }

ptConfigurationConfigurationFile OBJECT-TYPE
    SYNTAX          DisplayString (SIZE(0..255))
    MAX-ACCESS      read-only
    STATUS          current
    DESCRIPTION     
            "This attribute displays the path to the configuration File."
    ::= { ptConfigurationEntry 5 }

ptConfigurationTrapCommunity OBJECT-TYPE
    SYNTAX          DisplayString (SIZE(0..255))
    MAX-ACCESS      read-create
    STATUS          current
    DESCRIPTION     
            "This attribute displays the community name that will be sent within SNMP Traps. Maximum length is 64 characters. Only alphanumeric characters are allowed."
    ::= { ptConfigurationEntry 6 }

ptConfigurationCurrentSequenceNumber OBJECT-TYPE
    SYNTAX          Integer32 (-2147483648..2147483647)
    MAX-ACCESS      read-only
    STATUS          current
    DESCRIPTION     
            "Each Trap leaves the system with an associated Trap sequence number. This sequence number can be used by the operators to see if the last Traps received are the last Traps sent.\n\n The Trap sequence number increases by one every time a Trap is generated. On system restart, the Trap sequence number is 0 until a trap gets sent."
    ::= { ptConfigurationEntry 7 }

ptConfigurationSystemName OBJECT-TYPE
    SYNTAX          DisplayString (SIZE(0..255))
    MAX-ACCESS      read-create
    STATUS          current
    DESCRIPTION     
            "This field displays the mean to name the system. The system name is in the top left corner of any application user interface. The default value is Unset."
    ::= { ptConfigurationEntry 8 }

ptConfigurationSingleIntervalStatsFiles OBJECT-TYPE
    SYNTAX          INTEGER { disabled(0), enabled(1) }
    MAX-ACCESS      read-create
    STATUS          current
    DESCRIPTION     
            "This attribute, when ENABLED, results in generation of single interval statistics files. \nThe standard DSC system statistics files contain the object based statistics for the specified interval (5 minutes, 30 minutes, or 1 day) on a daily basis all into the same file. \nThe feature is disabled by default."
    ::= { ptConfigurationEntry 9 }

ptConfigurationSoftwareVersionInstalled OBJECT-TYPE
    SYNTAX          DisplayString (SIZE(0..255))
    MAX-ACCESS      read-create
    STATUS          current
    DESCRIPTION     
            "The Software version number installed on the system to conform to Ribbon format: VMM.mm.dd[Build Type]xxx where MM is major version, mm is minor version, dd is dot version, xxx is build number. [Build Type] is Engineering (A), Release (R), Special (S)."
    ::= { ptConfigurationEntry 10 }

ptConfigurationSingleTrapStream OBJECT-TYPE
    SYNTAX          INTEGER { disabled(0), enabled(1) }
    MAX-ACCESS      read-create
    STATUS          current
    DESCRIPTION     
            "This attribute, when set to ENABLED, results in sending only one stream of traps with the floating IP address as the trap source IP. The setting of the source IP is accomplished by firewall. Two streams of traps, with the source IP set to the IP of their associated Management CPU, are sent when this attribute is set to DISABLED. \nThe feature is disabled by default."
    ::= { ptConfigurationEntry 11 }

ptConfigurationDSCRESTAPI OBJECT-TYPE
    SYNTAX          INTEGER { disabled(0), enabled(1) }
    MAX-ACCESS      read-create
    STATUS          current
    DESCRIPTION     
            "This attribute allows or disallows access to DSC REST API. The feature is DISABLED by default. The REST API is accessed on port 8890."
    ::= { ptConfigurationEntry 12 }

ptConfigurationActiveTraps OBJECT-TYPE
    SYNTAX          INTEGER { disabled(0), enabled(1) }
    MAX-ACCESS      read-create
    STATUS          current
    DESCRIPTION     
            "This attribute, when set to ENABLED, displays the list of current active traps on the DSC system in the associated Active Traps List object under the SNMP application. The Active Traps List object is empty when this attribute is set to DISABLED. \nThe feature is disabled by default."
    ::= { ptConfigurationEntry 13 }

ptConfigurationParentOID OBJECT-TYPE
    SYNTAX          OBJECT IDENTIFIER
    MAX-ACCESS      read-create
    STATUS          current
    DESCRIPTION     
            "The OID of the parent object for this instance"
    ::= { ptConfigurationEntry 253 }

ptConfigurationRowStatus OBJECT-TYPE
    SYNTAX          RowStatus
    MAX-ACCESS      read-create
    STATUS          current
    DESCRIPTION     
            "The row status for the Configuration table"
    ::= { ptConfigurationEntry 254 }

ptConfigurationIndex OBJECT-TYPE
    SYNTAX          Integer32 (-2147483648..2147483647)
    MAX-ACCESS      not-accessible
    STATUS          current
    DESCRIPTION     
            "The row number for the Configuration table"
    ::= { ptConfigurationEntry 255 }

ptSNMPOmitList OBJECT IDENTIFIER
    ::= { ptConfiguration 307 }

ptSNMPOmitListTable OBJECT-TYPE
    SYNTAX          SEQUENCE OF PtSNMPOmitListEntry
    MAX-ACCESS      not-accessible
    STATUS          current
    DESCRIPTION     
            "No description supplied in the proxy config file."
    ::= { ptSNMPOmitList 1 }

ptSNMPOmitListEntry OBJECT-TYPE
    SYNTAX          PtSNMPOmitListEntry
    MAX-ACCESS      not-accessible
    STATUS          current
    DESCRIPTION     
            "A sequence of SNMPOmitList attributes."
    INDEX           { ptConnGroupIndex, ptSNMPOmitListConfigurationIndex, 
                      ptSNMPOmitListIndex }
    ::= { ptSNMPOmitListTable 1 }

PtSNMPOmitListEntry ::=
    SEQUENCE {
        ptSNMPOmitListQuantity          Integer32,
        ptSNMPOmitListConfigurationIndex Integer32,
        ptSNMPOmitListParentOID         OBJECT IDENTIFIER,
        ptSNMPOmitListRowStatus         RowStatus,
        ptSNMPOmitListIndex             Integer32
    }

ptSNMPOmitListQuantity OBJECT-TYPE
    SYNTAX          Integer32 (-2147483648..2147483647)
    MAX-ACCESS      read-only
    STATUS          current
    DESCRIPTION     
            "This feature is currently disabled."
    ::= { ptSNMPOmitListEntry 1 }

ptSNMPOmitListConfigurationIndex OBJECT-TYPE
    SYNTAX          Integer32 (-2147483648..2147483647)
    MAX-ACCESS      not-accessible
    STATUS          current
    DESCRIPTION     
            "This is the index of the parent type for this object.
             This parent type is Configuration."
    ::= { ptSNMPOmitListEntry 242 }

ptSNMPOmitListParentOID OBJECT-TYPE
    SYNTAX          OBJECT IDENTIFIER
    MAX-ACCESS      read-create
    STATUS          current
    DESCRIPTION     
            "The OID of the parent object for this instance"
    ::= { ptSNMPOmitListEntry 253 }

ptSNMPOmitListRowStatus OBJECT-TYPE
    SYNTAX          RowStatus
    MAX-ACCESS      read-create
    STATUS          current
    DESCRIPTION     
            "The row status for the SNMPOmitList table"
    ::= { ptSNMPOmitListEntry 254 }

ptSNMPOmitListIndex OBJECT-TYPE
    SYNTAX          Integer32 (-2147483648..2147483647)
    MAX-ACCESS      not-accessible
    STATUS          current
    DESCRIPTION     
            "The row number for the SNMPOmitList table"
    ::= { ptSNMPOmitListEntry 255 }

ptSNMPOmit OBJECT IDENTIFIER
    ::= { ptSNMPOmitList 315 }

ptSNMPOmitTable OBJECT-TYPE
    SYNTAX          SEQUENCE OF PtSNMPOmitEntry
    MAX-ACCESS      not-accessible
    STATUS          current
    DESCRIPTION     
            "No description supplied in the proxy config file."
    ::= { ptSNMPOmit 1 }

ptSNMPOmitEntry OBJECT-TYPE
    SYNTAX          PtSNMPOmitEntry
    MAX-ACCESS      not-accessible
    STATUS          current
    DESCRIPTION     
            "A sequence of SNMPOmit attributes."
    INDEX           { ptConnGroupIndex, ptSNMPOmitConfigurationIndex, 
                      ptSNMPOmitSNMPOmitListIndex, ptSNMPOmitIndex }
    ::= { ptSNMPOmitTable 1 }

PtSNMPOmitEntry ::=
    SEQUENCE {
        ptSNMPOmitOmit                  Integer32,
        ptSNMPOmitConfigurationIndex    Integer32,
        ptSNMPOmitSNMPOmitListIndex     Integer32,
        ptSNMPOmitParentOID             OBJECT IDENTIFIER,
        ptSNMPOmitRowStatus             RowStatus,
        ptSNMPOmitIndex                 Integer32
    }

ptSNMPOmitOmit OBJECT-TYPE
    SYNTAX          Integer32 (0..2147483647)
    MAX-ACCESS      read-only
    STATUS          current
    DESCRIPTION     
            "This attribute displays the SNMP OID to Omit."
    ::= { ptSNMPOmitEntry 1 }

ptSNMPOmitConfigurationIndex OBJECT-TYPE
    SYNTAX          Integer32 (-2147483648..2147483647)
    MAX-ACCESS      not-accessible
    STATUS          current
    DESCRIPTION     
            "This is the index of the parent type for this object.
             This parent type is Configuration."
    ::= { ptSNMPOmitEntry 242 }

ptSNMPOmitSNMPOmitListIndex OBJECT-TYPE
    SYNTAX          Integer32 (-2147483648..2147483647)
    MAX-ACCESS      not-accessible
    STATUS          current
    DESCRIPTION     
            "This is the index of the parent type for this object.
             This parent type is SNMPOmitList."
    ::= { ptSNMPOmitEntry 243 }

ptSNMPOmitParentOID OBJECT-TYPE
    SYNTAX          OBJECT IDENTIFIER
    MAX-ACCESS      read-create
    STATUS          current
    DESCRIPTION     
            "The OID of the parent object for this instance"
    ::= { ptSNMPOmitEntry 253 }

ptSNMPOmitRowStatus OBJECT-TYPE
    SYNTAX          RowStatus
    MAX-ACCESS      read-create
    STATUS          current
    DESCRIPTION     
            "The row status for the SNMPOmit table"
    ::= { ptSNMPOmitEntry 254 }

ptSNMPOmitIndex OBJECT-TYPE
    SYNTAX          Integer32 (-2147483648..2147483647)
    MAX-ACCESS      not-accessible
    STATUS          current
    DESCRIPTION     
            "The row number for the SNMPOmit table"
    ::= { ptSNMPOmitEntry 255 }

ptTrapHostList OBJECT IDENTIFIER
    ::= { ptConfiguration 308 }

ptTrapHostListTable OBJECT-TYPE
    SYNTAX          SEQUENCE OF PtTrapHostListEntry
    MAX-ACCESS      not-accessible
    STATUS          current
    DESCRIPTION     
            "No description supplied in the proxy config file."
    ::= { ptTrapHostList 1 }

ptTrapHostListEntry OBJECT-TYPE
    SYNTAX          PtTrapHostListEntry
    MAX-ACCESS      not-accessible
    STATUS          current
    DESCRIPTION     
            "A sequence of TrapHostList attributes."
    INDEX           { ptConnGroupIndex, ptTrapHostListConfigurationIndex, 
                      ptTrapHostListIndex }
    ::= { ptTrapHostListTable 1 }

PtTrapHostListEntry ::=
    SEQUENCE {
        ptTrapHostListQuantity          Integer32,
        ptTrapHostListConfigurationIndex Integer32,
        ptTrapHostListParentOID         OBJECT IDENTIFIER,
        ptTrapHostListRowStatus         RowStatus,
        ptTrapHostListIndex             Integer32
    }

ptTrapHostListQuantity OBJECT-TYPE
    SYNTAX          Integer32 (-2147483648..2147483647)
    MAX-ACCESS      read-only
    STATUS          current
    DESCRIPTION     
            "This attribute displays the number of Trap hosts in the list.\n\nNOTE: A maximum of 4 Trap hosts can be configured."
    ::= { ptTrapHostListEntry 1 }

ptTrapHostListConfigurationIndex OBJECT-TYPE
    SYNTAX          Integer32 (-2147483648..2147483647)
    MAX-ACCESS      not-accessible
    STATUS          current
    DESCRIPTION     
            "This is the index of the parent type for this object.
             This parent type is Configuration."
    ::= { ptTrapHostListEntry 242 }

ptTrapHostListParentOID OBJECT-TYPE
    SYNTAX          OBJECT IDENTIFIER
    MAX-ACCESS      read-create
    STATUS          current
    DESCRIPTION     
            "The OID of the parent object for this instance"
    ::= { ptTrapHostListEntry 253 }

ptTrapHostListRowStatus OBJECT-TYPE
    SYNTAX          RowStatus
    MAX-ACCESS      read-create
    STATUS          current
    DESCRIPTION     
            "The row status for the TrapHostList table"
    ::= { ptTrapHostListEntry 254 }

ptTrapHostListIndex OBJECT-TYPE
    SYNTAX          Integer32 (-2147483648..2147483647)
    MAX-ACCESS      not-accessible
    STATUS          current
    DESCRIPTION     
            "The row number for the TrapHostList table"
    ::= { ptTrapHostListEntry 255 }

ptTrapHost OBJECT IDENTIFIER
    ::= { ptTrapHostList 316 }

ptTrapHostTable OBJECT-TYPE
    SYNTAX          SEQUENCE OF PtTrapHostEntry
    MAX-ACCESS      not-accessible
    STATUS          current
    DESCRIPTION     
            "No description supplied in the proxy config file."
    ::= { ptTrapHost 1 }

ptTrapHostEntry OBJECT-TYPE
    SYNTAX          PtTrapHostEntry
    MAX-ACCESS      not-accessible
    STATUS          current
    DESCRIPTION     
            "A sequence of TrapHost attributes."
    INDEX           { ptConnGroupIndex, ptTrapHostConfigurationIndex, 
                      ptTrapHostTrapHostListIndex, ptTrapHostIndex }
    ::= { ptTrapHostTable 1 }

PtTrapHostEntry ::=
    SEQUENCE {
        ptTrapHostTrapHost              DisplayString,
        ptTrapHostConfigurationIndex    Integer32,
        ptTrapHostTrapHostListIndex     Integer32,
        ptTrapHostParentOID             OBJECT IDENTIFIER,
        ptTrapHostRowStatus             RowStatus,
        ptTrapHostIndex                 Integer32
    }

ptTrapHostTrapHost OBJECT-TYPE
    SYNTAX          DisplayString (SIZE(0..255))
    MAX-ACCESS      read-only
    STATUS          current
    DESCRIPTION     
            "This attribute displays the IPv4/IPv6 Address or the Hostname/FQDN of a system ready to receive Traps. The trap host needs to run some Trap receiver application in order to receive the Traps."
    ::= { ptTrapHostEntry 1 }

ptTrapHostConfigurationIndex OBJECT-TYPE
    SYNTAX          Integer32 (-2147483648..2147483647)
    MAX-ACCESS      not-accessible
    STATUS          current
    DESCRIPTION     
            "This is the index of the parent type for this object.
             This parent type is Configuration."
    ::= { ptTrapHostEntry 242 }

ptTrapHostTrapHostListIndex OBJECT-TYPE
    SYNTAX          Integer32 (-2147483648..2147483647)
    MAX-ACCESS      not-accessible
    STATUS          current
    DESCRIPTION     
            "This is the index of the parent type for this object.
             This parent type is TrapHostList."
    ::= { ptTrapHostEntry 243 }

ptTrapHostParentOID OBJECT-TYPE
    SYNTAX          OBJECT IDENTIFIER
    MAX-ACCESS      read-create
    STATUS          current
    DESCRIPTION     
            "The OID of the parent object for this instance"
    ::= { ptTrapHostEntry 253 }

ptTrapHostRowStatus OBJECT-TYPE
    SYNTAX          RowStatus
    MAX-ACCESS      read-create
    STATUS          current
    DESCRIPTION     
            "The row status for the TrapHost table"
    ::= { ptTrapHostEntry 254 }

ptTrapHostIndex OBJECT-TYPE
    SYNTAX          Integer32 (-2147483648..2147483647)
    MAX-ACCESS      not-accessible
    STATUS          current
    DESCRIPTION     
            "The row number for the TrapHost table"
    ::= { ptTrapHostEntry 255 }

ptDefinitionFileList OBJECT IDENTIFIER
    ::= { ptConfiguration 309 }

ptDefinitionFileListTable OBJECT-TYPE
    SYNTAX          SEQUENCE OF PtDefinitionFileListEntry
    MAX-ACCESS      not-accessible
    STATUS          current
    DESCRIPTION     
            "No description supplied in the proxy config file."
    ::= { ptDefinitionFileList 1 }

ptDefinitionFileListEntry OBJECT-TYPE
    SYNTAX          PtDefinitionFileListEntry
    MAX-ACCESS      not-accessible
    STATUS          current
    DESCRIPTION     
            "A sequence of DefinitionFileList attributes."
    INDEX           { ptConnGroupIndex, 
                      ptDefinitionFileListConfigurationIndex, 
                      ptDefinitionFileListIndex }
    ::= { ptDefinitionFileListTable 1 }

PtDefinitionFileListEntry ::=
    SEQUENCE {
        ptDefinitionFileListQuantity    Integer32,
        ptDefinitionFileListConfigurationIndex      Integer32,
        ptDefinitionFileListParentOID   OBJECT IDENTIFIER,
        ptDefinitionFileListRowStatus   RowStatus,
        ptDefinitionFileListIndex       Integer32
    }

ptDefinitionFileListQuantity OBJECT-TYPE
    SYNTAX          Integer32 (-2147483648..2147483647)
    MAX-ACCESS      read-only
    STATUS          current
    DESCRIPTION     
            "This attribute displays the number of definition file in the list."
    ::= { ptDefinitionFileListEntry 1 }

ptDefinitionFileListConfigurationIndex OBJECT-TYPE
    SYNTAX          Integer32 (-2147483648..2147483647)
    MAX-ACCESS      not-accessible
    STATUS          current
    DESCRIPTION     
            "This is the index of the parent type for this object.
             This parent type is Configuration."
    ::= { ptDefinitionFileListEntry 242 }

ptDefinitionFileListParentOID OBJECT-TYPE
    SYNTAX          OBJECT IDENTIFIER
    MAX-ACCESS      read-create
    STATUS          current
    DESCRIPTION     
            "The OID of the parent object for this instance"
    ::= { ptDefinitionFileListEntry 253 }

ptDefinitionFileListRowStatus OBJECT-TYPE
    SYNTAX          RowStatus
    MAX-ACCESS      read-create
    STATUS          current
    DESCRIPTION     
            "The row status for the DefinitionFileList table"
    ::= { ptDefinitionFileListEntry 254 }

ptDefinitionFileListIndex OBJECT-TYPE
    SYNTAX          Integer32 (-2147483648..2147483647)
    MAX-ACCESS      not-accessible
    STATUS          current
    DESCRIPTION     
            "The row number for the DefinitionFileList table"
    ::= { ptDefinitionFileListEntry 255 }

ptDefinitionFile OBJECT IDENTIFIER
    ::= { ptDefinitionFileList 317 }

ptDefinitionFileTable OBJECT-TYPE
    SYNTAX          SEQUENCE OF PtDefinitionFileEntry
    MAX-ACCESS      not-accessible
    STATUS          current
    DESCRIPTION     
            "No description supplied in the proxy config file."
    ::= { ptDefinitionFile 1 }

ptDefinitionFileEntry OBJECT-TYPE
    SYNTAX          PtDefinitionFileEntry
    MAX-ACCESS      not-accessible
    STATUS          current
    DESCRIPTION     
            "A sequence of DefinitionFile attributes."
    INDEX           { ptConnGroupIndex, 
                      ptDefinitionFileConfigurationIndex, 
                      ptDefinitionFileDefinitionFileListIndex, 
                      ptDefinitionFileIndex }
    ::= { ptDefinitionFileTable 1 }

PtDefinitionFileEntry ::=
    SEQUENCE {
        ptDefinitionFileDefinitionFile  DisplayString,
        ptDefinitionFileConfigurationIndex  Integer32,
        ptDefinitionFileDefinitionFileListIndex       Integer32,
        ptDefinitionFileParentOID       OBJECT IDENTIFIER,
        ptDefinitionFileRowStatus       RowStatus,
        ptDefinitionFileIndex           Integer32
    }

ptDefinitionFileDefinitionFile OBJECT-TYPE
    SYNTAX          DisplayString (SIZE(0..255))
    MAX-ACCESS      read-only
    STATUS          current
    DESCRIPTION     
            "This attribute displays the path of a definition File. Definition files are contain the definition of all user interface Objects."
    ::= { ptDefinitionFileEntry 1 }

ptDefinitionFileConfigurationIndex OBJECT-TYPE
    SYNTAX          Integer32 (-2147483648..2147483647)
    MAX-ACCESS      not-accessible
    STATUS          current
    DESCRIPTION     
            "This is the index of the parent type for this object.
             This parent type is Configuration."
    ::= { ptDefinitionFileEntry 242 }

ptDefinitionFileDefinitionFileListIndex OBJECT-TYPE
    SYNTAX          Integer32 (-2147483648..2147483647)
    MAX-ACCESS      not-accessible
    STATUS          current
    DESCRIPTION     
            "This is the index of the parent type for this object.
             This parent type is DefinitionFileList."
    ::= { ptDefinitionFileEntry 243 }

ptDefinitionFileParentOID OBJECT-TYPE
    SYNTAX          OBJECT IDENTIFIER
    MAX-ACCESS      read-create
    STATUS          current
    DESCRIPTION     
            "The OID of the parent object for this instance"
    ::= { ptDefinitionFileEntry 253 }

ptDefinitionFileRowStatus OBJECT-TYPE
    SYNTAX          RowStatus
    MAX-ACCESS      read-create
    STATUS          current
    DESCRIPTION     
            "The row status for the DefinitionFile table"
    ::= { ptDefinitionFileEntry 254 }

ptDefinitionFileIndex OBJECT-TYPE
    SYNTAX          Integer32 (-2147483648..2147483647)
    MAX-ACCESS      not-accessible
    STATUS          current
    DESCRIPTION     
            "The row number for the DefinitionFile table"
    ::= { ptDefinitionFileEntry 255 }

ptAgentHostList OBJECT IDENTIFIER
    ::= { ptConfiguration 310 }

ptAgentHostListTable OBJECT-TYPE
    SYNTAX          SEQUENCE OF PtAgentHostListEntry
    MAX-ACCESS      not-accessible
    STATUS          current
    DESCRIPTION     
            "No description supplied in the proxy config file."
    ::= { ptAgentHostList 1 }

ptAgentHostListEntry OBJECT-TYPE
    SYNTAX          PtAgentHostListEntry
    MAX-ACCESS      not-accessible
    STATUS          current
    DESCRIPTION     
            "A sequence of AgentHostList attributes."
    INDEX           { ptConnGroupIndex, 
                      ptAgentHostListConfigurationIndex, 
                      ptAgentHostListIndex }
    ::= { ptAgentHostListTable 1 }

PtAgentHostListEntry ::=
    SEQUENCE {
        ptAgentHostListQuantity         Integer32,
        ptAgentHostListConfigurationIndex Integer32,
        ptAgentHostListParentOID        OBJECT IDENTIFIER,
        ptAgentHostListRowStatus        RowStatus,
        ptAgentHostListIndex            Integer32
    }

ptAgentHostListQuantity OBJECT-TYPE
    SYNTAX          Integer32 (-2147483648..2147483647)
    MAX-ACCESS      read-only
    STATUS          current
    DESCRIPTION     
            "This attribute displays the number of agent host in the list."
    ::= { ptAgentHostListEntry 1 }

ptAgentHostListConfigurationIndex OBJECT-TYPE
    SYNTAX          Integer32 (-2147483648..2147483647)
    MAX-ACCESS      not-accessible
    STATUS          current
    DESCRIPTION     
            "This is the index of the parent type for this object.
             This parent type is Configuration."
    ::= { ptAgentHostListEntry 242 }

ptAgentHostListParentOID OBJECT-TYPE
    SYNTAX          OBJECT IDENTIFIER
    MAX-ACCESS      read-create
    STATUS          current
    DESCRIPTION     
            "The OID of the parent object for this instance"
    ::= { ptAgentHostListEntry 253 }

ptAgentHostListRowStatus OBJECT-TYPE
    SYNTAX          RowStatus
    MAX-ACCESS      read-create
    STATUS          current
    DESCRIPTION     
            "The row status for the AgentHostList table"
    ::= { ptAgentHostListEntry 254 }

ptAgentHostListIndex OBJECT-TYPE
    SYNTAX          Integer32 (-2147483648..2147483647)
    MAX-ACCESS      not-accessible
    STATUS          current
    DESCRIPTION     
            "The row number for the AgentHostList table"
    ::= { ptAgentHostListEntry 255 }

ptAgentHost OBJECT IDENTIFIER
    ::= { ptAgentHostList 318 }

ptAgentHostTable OBJECT-TYPE
    SYNTAX          SEQUENCE OF PtAgentHostEntry
    MAX-ACCESS      not-accessible
    STATUS          current
    DESCRIPTION     
            "No description supplied in the proxy config file."
    ::= { ptAgentHost 1 }

ptAgentHostEntry OBJECT-TYPE
    SYNTAX          PtAgentHostEntry
    MAX-ACCESS      not-accessible
    STATUS          current
    DESCRIPTION     
            "A sequence of AgentHost attributes."
    INDEX           { ptConnGroupIndex, ptAgentHostConfigurationIndex, 
                      ptAgentHostAgentHostListIndex, ptAgentHostIndex }
    ::= { ptAgentHostTable 1 }

PtAgentHostEntry ::=
    SEQUENCE {
        ptAgentHostAgentHost            DisplayString,
        ptAgentHostPort                 Integer32,
        ptAgentHostSNMPUniqueNumber     Integer32,
        ptAgentHostConfigurationIndex   Integer32,
        ptAgentHostAgentHostListIndex   Integer32,
        ptAgentHostParentOID            OBJECT IDENTIFIER,
        ptAgentHostRowStatus            RowStatus,
        ptAgentHostIndex                Integer32
    }

ptAgentHostAgentHost OBJECT-TYPE
    SYNTAX          DisplayString (SIZE(0..255))
    MAX-ACCESS      read-only
    STATUS          current
    DESCRIPTION     
            "This attribute displays an agent host. An agent host is comma separated list of hosts which run an application that can interface with the pxbr."
    ::= { ptAgentHostEntry 1 }

ptAgentHostPort OBJECT-TYPE
    SYNTAX          Integer32 (-2147483648..2147483647)
    MAX-ACCESS      read-only
    STATUS          current
    DESCRIPTION     
            "This attribute displays on which port communication with the agent host will occur."
    ::= { ptAgentHostEntry 2 }

ptAgentHostSNMPUniqueNumber OBJECT-TYPE
    SYNTAX          Integer32 (-2147483648..2147483647)
    MAX-ACCESS      read-only
    STATUS          current
    DESCRIPTION     
            "This attribute specifies the SNMP unique instance number. This allows SNMP to query 2 distinct copies of an application without collision."
    ::= { ptAgentHostEntry 3 }

ptAgentHostConfigurationIndex OBJECT-TYPE
    SYNTAX          Integer32 (-2147483648..2147483647)
    MAX-ACCESS      not-accessible
    STATUS          current
    DESCRIPTION     
            "This is the index of the parent type for this object.
             This parent type is Configuration."
    ::= { ptAgentHostEntry 242 }

ptAgentHostAgentHostListIndex OBJECT-TYPE
    SYNTAX          Integer32 (-2147483648..2147483647)
    MAX-ACCESS      not-accessible
    STATUS          current
    DESCRIPTION     
            "This is the index of the parent type for this object.
             This parent type is AgentHostList."
    ::= { ptAgentHostEntry 243 }

ptAgentHostParentOID OBJECT-TYPE
    SYNTAX          OBJECT IDENTIFIER
    MAX-ACCESS      read-create
    STATUS          current
    DESCRIPTION     
            "The OID of the parent object for this instance"
    ::= { ptAgentHostEntry 253 }

ptAgentHostRowStatus OBJECT-TYPE
    SYNTAX          RowStatus
    MAX-ACCESS      read-create
    STATUS          current
    DESCRIPTION     
            "The row status for the AgentHost table"
    ::= { ptAgentHostEntry 254 }

ptAgentHostIndex OBJECT-TYPE
    SYNTAX          Integer32 (-2147483648..2147483647)
    MAX-ACCESS      not-accessible
    STATUS          current
    DESCRIPTION     
            "The row number for the AgentHost table"
    ::= { ptAgentHostEntry 255 }

ptTrapLog OBJECT IDENTIFIER
    ::= { ptConfiguration 312 }

ptTrapLogTable OBJECT-TYPE
    SYNTAX          SEQUENCE OF PtTrapLogEntry
    MAX-ACCESS      not-accessible
    STATUS          current
    DESCRIPTION     
            "No description supplied in the proxy config file."
    ::= { ptTrapLog 1 }

ptTrapLogEntry OBJECT-TYPE
    SYNTAX          PtTrapLogEntry
    MAX-ACCESS      not-accessible
    STATUS          current
    DESCRIPTION     
            "A sequence of TrapLog attributes."
    INDEX           { ptConnGroupIndex, ptTrapLogConfigurationIndex, 
                      ptTrapLogIndex }
    ::= { ptTrapLogTable 1 }

PtTrapLogEntry ::=
    SEQUENCE {
        ptTrapLogQuantity               Integer32,
        ptTrapLogMaximumNumberOfTraps   Integer32,
        ptTrapLogConfigurationIndex     Integer32,
        ptTrapLogParentOID              OBJECT IDENTIFIER,
        ptTrapLogRowStatus              RowStatus,
        ptTrapLogIndex                  Integer32
    }

ptTrapLogQuantity OBJECT-TYPE
    SYNTAX          Integer32 (-2147483648..2147483647)
    MAX-ACCESS      read-only
    STATUS          current
    DESCRIPTION     
            "This attribute displays the current number of traps in the list."
    ::= { ptTrapLogEntry 1 }

ptTrapLogMaximumNumberOfTraps OBJECT-TYPE
    SYNTAX          Integer32 (0..2048)
    MAX-ACCESS      read-create
    STATUS          current
    DESCRIPTION     
            "This attribute displays the maximum number of traps that are kept in memory. In order to preserve memory, this value may not exceed 2048. Increasing this number will also increase the amount of memory taken. The default value is 1000."
    ::= { ptTrapLogEntry 2 }

ptTrapLogConfigurationIndex OBJECT-TYPE
    SYNTAX          Integer32 (-2147483648..2147483647)
    MAX-ACCESS      not-accessible
    STATUS          current
    DESCRIPTION     
            "This is the index of the parent type for this object.
             This parent type is Configuration."
    ::= { ptTrapLogEntry 242 }

ptTrapLogParentOID OBJECT-TYPE
    SYNTAX          OBJECT IDENTIFIER
    MAX-ACCESS      read-create
    STATUS          current
    DESCRIPTION     
            "The OID of the parent object for this instance"
    ::= { ptTrapLogEntry 253 }

ptTrapLogRowStatus OBJECT-TYPE
    SYNTAX          RowStatus
    MAX-ACCESS      read-create
    STATUS          current
    DESCRIPTION     
            "The row status for the TrapLog table"
    ::= { ptTrapLogEntry 254 }

ptTrapLogIndex OBJECT-TYPE
    SYNTAX          Integer32 (-2147483648..2147483647)
    MAX-ACCESS      not-accessible
    STATUS          current
    DESCRIPTION     
            "The row number for the TrapLog table"
    ::= { ptTrapLogEntry 255 }

ptTrapEvent OBJECT IDENTIFIER
    ::= { ptTrapLog 313 }

ptTrapEventTable OBJECT-TYPE
    SYNTAX          SEQUENCE OF PtTrapEventEntry
    MAX-ACCESS      not-accessible
    STATUS          current
    DESCRIPTION     
            "No description supplied in the proxy config file."
    ::= { ptTrapEvent 1 }

ptTrapEventEntry OBJECT-TYPE
    SYNTAX          PtTrapEventEntry
    MAX-ACCESS      not-accessible
    STATUS          current
    DESCRIPTION     
            "A sequence of TrapEvent attributes."
    INDEX           { ptConnGroupIndex, ptTrapEventConfigurationIndex, 
                      ptTrapEventTrapLogIndex, ptTrapEventIndex }
    ::= { ptTrapEventTable 1 }

PtTrapEventEntry ::=
    SEQUENCE {
        ptTrapEventTrapName             DisplayString,
        ptTrapEventSequenceNumber       Integer32,
        ptTrapEventDateAndTime          DisplayString,
        ptTrapEventTrapType             INTEGER,
        ptTrapEventSeverity             INTEGER,
        ptTrapEventProblemCause         INTEGER,
        ptTrapEventClearType            INTEGER,
        ptTrapEventItemType             DisplayString,
        ptTrapEventVariableName1        DisplayString,
        ptTrapEventVariableValue1       DisplayString,
        ptTrapEventVariableName2        DisplayString,
        ptTrapEventVariableValue2       DisplayString,
        ptTrapEventVariableName3        DisplayString,
        ptTrapEventVariableValue3       DisplayString,
        ptTrapEventVariableName4        DisplayString,
        ptTrapEventVariableValue4       DisplayString,
        ptTrapEventVariableName5        DisplayString,
        ptTrapEventVariableValue5       DisplayString,
        ptTrapEventVariableName6        DisplayString,
        ptTrapEventVariableValue6       DisplayString,
        ptTrapEventVariableName7        DisplayString,
        ptTrapEventVariableValue7       DisplayString,
        ptTrapEventVariableName8        DisplayString,
        ptTrapEventVariableValue8       DisplayString,
        ptTrapEventVariableName9        DisplayString,
        ptTrapEventVariableValue9       DisplayString,
        ptTrapEventVariableName10       DisplayString,
        ptTrapEventVariableValue10      DisplayString,
        ptTrapEventItemOID              DisplayString,
        ptTrapEventConfigurationIndex   Integer32,
        ptTrapEventTrapLogIndex         Integer32,
        ptTrapEventParentOID            OBJECT IDENTIFIER,
        ptTrapEventRowStatus            RowStatus,
        ptTrapEventIndex                Integer32
    }

ptTrapEventTrapName OBJECT-TYPE
    SYNTAX          DisplayString (SIZE(0..255))
    MAX-ACCESS      read-only
    STATUS          current
    DESCRIPTION     
            "The name of the trap issued. For more information concerning possible traps names, please look at the provided mib files."
    ::= { ptTrapEventEntry 1 }

ptTrapEventSequenceNumber OBJECT-TYPE
    SYNTAX          Integer32 (-2147483648..2147483647)
    MAX-ACCESS      read-only
    STATUS          current
    DESCRIPTION     
            "The sequence number of the trap\n This number increased by one for each trap sent by the system."
    ::= { ptTrapEventEntry 2 }

ptTrapEventDateAndTime OBJECT-TYPE
    SYNTAX          DisplayString (SIZE(0..255))
    MAX-ACCESS      read-only
    STATUS          current
    DESCRIPTION     
            "Date and time value of the occurrence of the trap."
    ::= { ptTrapEventEntry 3 }

ptTrapEventTrapType OBJECT-TYPE
    SYNTAX          INTEGER { undefined(0), communicationAlarm(2), 
                        environmentAlarm(3), equipmentAlarm(4), 
                        processingAlarm(10), qualityOfServiceAlarm(11) }
    MAX-ACCESS      read-only
    STATUS          current
    DESCRIPTION     
            "The type of the trap, follows Ref. X.733 : \n\nCommunication Alarm: An alarm of this type is principally associated with the procedures and/or processes required to convey information from one point to another. \n\nQuality of Service Alarm: An alarm of this type is principally associated with a degradation in the quality of a service.\n\nProcessing Error Alarm: An alarm of this type is principally associated with a software or processing fault.\n\nEquipment Alarm: An alarm of this type is principally associated with equipment fault.\n\nEnvironmental Alarm: An alarm of this type is principally associated with a condition relating to an enclosure in which the equipment resides."
    ::= { ptTrapEventEntry 4 }

ptTrapEventSeverity OBJECT-TYPE
    SYNTAX          INTEGER { indetermined(0), critical(1), major(2), 
                        minor(3), warning(4), cleared(5) }
    MAX-ACCESS      read-only
    STATUS          current
    DESCRIPTION     
            "Severity is used in the reporting of traps. When a trap is issued it will have an associated severity.\n\n Possible Severity are: indeterminate, critical, major, minor, warning, cleared."
    ::= { ptTrapEventEntry 5 }

ptTrapEventProblemCause OBJECT-TYPE
    SYNTAX          INTEGER { undefined(0), 
                        applicationSubsystemFailure(2), 
                        callEstablishmentError(4), 
                        communicationsProtocolError(5), 
                        communicationsSubsystemError(6), 
                        configurationOrCustomizationError(7), 
                        congestion(8), corruptData(9), 
                        cpuCyclesLimitExceeded(10), 
                        datasetOrModemError(11), degradedSignal(12), 
                        dteDceInterfaceError(13), enclosureDoorOpen(14), 
                        equipmentMalfunction(15), fileError(17), 
                        fireDetected(18), floodDetected(19), 
                        framingError(20), inputOutputDeviceError(23), 
                        inputDeviceError(24), lanError(25), 
                        localNodeTransmissionError(27), lossOfFrame(28), 
                        lossOfSignal(29), multiplexerProblem(31), 
                        outOfMemory(32), outputDeviceError(33), 
                        performanceDegraded(34), powerProblem(35), 
                        processorProblem(37), queueSizeExceeded(39), 
                        receiveFailure(40), 
                        remoteNodeTransmissionError(42), 
                        resourceAtOrNearCapacity(43), 
                        responseTimeExcessive(44), 
                        retransmissionRateExcessive(45), 
                        softwareError(46), 
                        softwareProgramAbnormallyTerminated(47), 
                        softwareProgramError(48), 
                        storageCapacityProblem(49), thresholdCrossed(51), 
                        timingProblem(52), transmitFailure(54), 
                        underlyingResourceUnavailable(56), 
                        versionMismatch(57) }
    MAX-ACCESS      read-only
    STATUS          current
    DESCRIPTION     
            "The probable cause of the trap, follows Ref. X.733. After we identify the GSN alarms, we will categorize them according to the five types above, find their probable causes, and map the causes, as close as we can, to the X.733 list."
    ::= { ptTrapEventEntry 6 }

ptTrapEventClearType OBJECT-TYPE
    SYNTAX          INTEGER { fmic(1), oic(2), undefined(3) }
    MAX-ACCESS      read-only
    STATUS          current
    DESCRIPTION     
            "The Clear type of the trap, which is either FMIC or OIC, where FMIC means that the trap will be cleared by another clear trap, and OIC means that the trap needs to be cleared by the operator."
    ::= { ptTrapEventEntry 7 }

ptTrapEventItemType OBJECT-TYPE
    SYNTAX          DisplayString (SIZE(0..255))
    MAX-ACCESS      read-only
    STATUS          current
    DESCRIPTION     
            "This attribute gives the name of the item type from which the variable names and values are taken.\n\n The variable names and values should clarify which item (if there are many of the same type) issued the trap and may give more information as to why the trap has been issued."
    ::= { ptTrapEventEntry 8 }

ptTrapEventVariableName1 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 9 }

ptTrapEventVariableValue1 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 10 }

ptTrapEventVariableName2 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 11 }

ptTrapEventVariableValue2 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 12 }

ptTrapEventVariableName3 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 13 }

ptTrapEventVariableValue3 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 14 }

ptTrapEventVariableName4 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 15 }

ptTrapEventVariableValue4 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 16 }

ptTrapEventVariableName5 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 17 }

ptTrapEventVariableValue5 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 18 }

ptTrapEventVariableName6 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 19 }

ptTrapEventVariableValue6 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 20 }

ptTrapEventVariableName7 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 21 }

ptTrapEventVariableValue7 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 22 }

ptTrapEventVariableName8 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 23 }

ptTrapEventVariableValue8 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 24 }

ptTrapEventVariableName9 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 25 }

ptTrapEventVariableValue9 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 26 }

ptTrapEventVariableName10 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptTrapEventEntry 27 }

ptTrapEventVariableValue10 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptTrapEventEntry 28 }

ptTrapEventItemOID OBJECT-TYPE
    SYNTAX          DisplayString (SIZE(0..255))
    MAX-ACCESS      read-only
    STATUS          current
    DESCRIPTION     
            "This attribute gives the Object Identifier (OID) of the item that produced the trap.\n\n"
    ::= { ptTrapEventEntry 29 }

ptTrapEventConfigurationIndex OBJECT-TYPE
    SYNTAX          Integer32 (-2147483648..2147483647)
    MAX-ACCESS      not-accessible
    STATUS          current
    DESCRIPTION     
            "This is the index of the parent type for this object.
             This parent type is Configuration."
    ::= { ptTrapEventEntry 242 }

ptTrapEventTrapLogIndex OBJECT-TYPE
    SYNTAX          Integer32 (-2147483648..2147483647)
    MAX-ACCESS      not-accessible
    STATUS          current
    DESCRIPTION     
            "This is the index of the parent type for this object.
             This parent type is TrapLog."
    ::= { ptTrapEventEntry 243 }

ptTrapEventParentOID OBJECT-TYPE
    SYNTAX          OBJECT IDENTIFIER
    MAX-ACCESS      read-create
    STATUS          current
    DESCRIPTION     
            "The OID of the parent object for this instance"
    ::= { ptTrapEventEntry 253 }

ptTrapEventRowStatus OBJECT-TYPE
    SYNTAX          RowStatus
    MAX-ACCESS      read-create
    STATUS          current
    DESCRIPTION     
            "The row status for the TrapEvent table"
    ::= { ptTrapEventEntry 254 }

ptTrapEventIndex OBJECT-TYPE
    SYNTAX          Integer32 (-2147483648..2147483647)
    MAX-ACCESS      not-accessible
    STATUS          current
    DESCRIPTION     
            "The row number for the TrapEvent table"
    ::= { ptTrapEventEntry 255 }

ptEventTypeList OBJECT IDENTIFIER
    ::= { ptConfiguration 319 }

ptEventTypeListTable OBJECT-TYPE
    SYNTAX          SEQUENCE OF PtEventTypeListEntry
    MAX-ACCESS      not-accessible
    STATUS          current
    DESCRIPTION     
            "No description supplied in the proxy config file."
    ::= { ptEventTypeList 1 }

ptEventTypeListEntry OBJECT-TYPE
    SYNTAX          PtEventTypeListEntry
    MAX-ACCESS      not-accessible
    STATUS          current
    DESCRIPTION     
            "A sequence of EventTypeList attributes."
    INDEX           { ptConnGroupIndex, 
                      ptEventTypeListConfigurationIndex, 
                      ptEventTypeListIndex }
    ::= { ptEventTypeListTable 1 }

PtEventTypeListEntry ::=
    SEQUENCE {
        ptEventTypeListQuantity         Integer32,
        ptEventTypeListConfigurationIndex Integer32,
        ptEventTypeListParentOID        OBJECT IDENTIFIER,
        ptEventTypeListRowStatus        RowStatus,
        ptEventTypeListIndex            Integer32
    }

ptEventTypeListQuantity OBJECT-TYPE
    SYNTAX          Integer32 (-2147483648..2147483647)
    MAX-ACCESS      read-only
    STATUS          current
    DESCRIPTION     
            "This attribute displays the number of entries in the event config list."
    ::= { ptEventTypeListEntry 1 }

ptEventTypeListConfigurationIndex OBJECT-TYPE
    SYNTAX          Integer32 (-2147483648..2147483647)
    MAX-ACCESS      not-accessible
    STATUS          current
    DESCRIPTION     
            "This is the index of the parent type for this object.
             This parent type is Configuration."
    ::= { ptEventTypeListEntry 242 }

ptEventTypeListParentOID OBJECT-TYPE
    SYNTAX          OBJECT IDENTIFIER
    MAX-ACCESS      read-create
    STATUS          current
    DESCRIPTION     
            "The OID of the parent object for this instance"
    ::= { ptEventTypeListEntry 253 }

ptEventTypeListRowStatus OBJECT-TYPE
    SYNTAX          RowStatus
    MAX-ACCESS      read-create
    STATUS          current
    DESCRIPTION     
            "The row status for the EventTypeList table"
    ::= { ptEventTypeListEntry 254 }

ptEventTypeListIndex OBJECT-TYPE
    SYNTAX          Integer32 (-2147483648..2147483647)
    MAX-ACCESS      not-accessible
    STATUS          current
    DESCRIPTION     
            "The row number for the EventTypeList table"
    ::= { ptEventTypeListEntry 255 }

ptEventNotificationSetup OBJECT IDENTIFIER
    ::= { ptEventTypeList 320 }

ptEventNotificationSetupTable OBJECT-TYPE
    SYNTAX          SEQUENCE OF PtEventNotificationSetupEntry
    MAX-ACCESS      not-accessible
    STATUS          current
    DESCRIPTION     
            "No description supplied in the proxy config file."
    ::= { ptEventNotificationSetup 1 }

ptEventNotificationSetupEntry OBJECT-TYPE
    SYNTAX          PtEventNotificationSetupEntry
    MAX-ACCESS      not-accessible
    STATUS          current
    DESCRIPTION     
            "A sequence of EventNotificationSetup attributes."
    INDEX           { ptConnGroupIndex, 
                      ptEventNotificationSetupConfigurationIndex, 
                      ptEventNotificationSetupEventTypeListIndex, 
                      ptEventNotificationSetupIndex }
    ::= { ptEventNotificationSetupTable 1 }

PtEventNotificationSetupEntry ::=
    SEQUENCE {
        ptEventNotificationSetupEventNumber   Integer32,
        ptEventNotificationSetupEventName DisplayString,
        ptEventNotificationSetupSNMPTrap INTEGER,
        ptEventNotificationSetupDashboard INTEGER,
        ptEventNotificationSetupConfigurationIndex          Integer32,
        ptEventNotificationSetupEventTypeListIndex          Integer32,
        ptEventNotificationSetupParentOID OBJECT IDENTIFIER,
        ptEventNotificationSetupRowStatus RowStatus,
        ptEventNotificationSetupIndex   Integer32
    }

ptEventNotificationSetupEventNumber OBJECT-TYPE
    SYNTAX          Integer32 (-2147483648..2147483647)
    MAX-ACCESS      read-only
    STATUS          current
    DESCRIPTION     
            "This attribute displays the event number."
    ::= { ptEventNotificationSetupEntry 1 }

ptEventNotificationSetupEventName OBJECT-TYPE
    SYNTAX          DisplayString (SIZE(0..255))
    MAX-ACCESS      read-only
    STATUS          current
    DESCRIPTION     
            "This attribute displays the event name."
    ::= { ptEventNotificationSetupEntry 2 }

ptEventNotificationSetupSNMPTrap OBJECT-TYPE
    SYNTAX          INTEGER { disabled(0), enabled(1), 
                        disabledPermanently(2) }
    MAX-ACCESS      read-create
    STATUS          current
    DESCRIPTION     
            "This attribute specifies whether the event is sent to an SNMP trap host. \nAll events can be ENABLED for transmission to an SNMP trap host."
    ::= { ptEventNotificationSetupEntry 3 }

ptEventNotificationSetupDashboard OBJECT-TYPE
    SYNTAX          INTEGER { disabled(0), enabled(1), 
                        disabledPermanently(2) }
    MAX-ACCESS      read-create
    STATUS          current
    DESCRIPTION     
            "This attribute specifies whether the event is displayed in the Alarm Dashboard in the Web UI. \nEnabling or disabling this attribute has no effect for clearing events and events listed as DISABLED_PERMANENTLY because these events are never displayed in the Web UI."
    ::= { ptEventNotificationSetupEntry 4 }

ptEventNotificationSetupConfigurationIndex OBJECT-TYPE
    SYNTAX          Integer32 (-2147483648..2147483647)
    MAX-ACCESS      not-accessible
    STATUS          current
    DESCRIPTION     
            "This is the index of the parent type for this object.
             This parent type is Configuration."
    ::= { ptEventNotificationSetupEntry 242 }

ptEventNotificationSetupEventTypeListIndex OBJECT-TYPE
    SYNTAX          Integer32 (-2147483648..2147483647)
    MAX-ACCESS      not-accessible
    STATUS          current
    DESCRIPTION     
            "This is the index of the parent type for this object.
             This parent type is EventTypeList."
    ::= { ptEventNotificationSetupEntry 243 }

ptEventNotificationSetupParentOID OBJECT-TYPE
    SYNTAX          OBJECT IDENTIFIER
    MAX-ACCESS      read-create
    STATUS          current
    DESCRIPTION     
            "The OID of the parent object for this instance"
    ::= { ptEventNotificationSetupEntry 253 }

ptEventNotificationSetupRowStatus OBJECT-TYPE
    SYNTAX          RowStatus
    MAX-ACCESS      read-create
    STATUS          current
    DESCRIPTION     
            "The row status for the EventNotificationSetup table"
    ::= { ptEventNotificationSetupEntry 254 }

ptEventNotificationSetupIndex OBJECT-TYPE
    SYNTAX          Integer32 (-2147483648..2147483647)
    MAX-ACCESS      not-accessible
    STATUS          current
    DESCRIPTION     
            "The row number for the EventNotificationSetup table"
    ::= { ptEventNotificationSetupEntry 255 }

ptSP2KEventList OBJECT IDENTIFIER
    ::= { ptConfiguration 321 }

ptSP2KEventListTable OBJECT-TYPE
    SYNTAX          SEQUENCE OF PtSP2KEventListEntry
    MAX-ACCESS      not-accessible
    STATUS          current
    DESCRIPTION     
            "No description supplied in the proxy config file."
    ::= { ptSP2KEventList 1 }

ptSP2KEventListEntry OBJECT-TYPE
    SYNTAX          PtSP2KEventListEntry
    MAX-ACCESS      not-accessible
    STATUS          current
    DESCRIPTION     
            "A sequence of SP2KEventList attributes."
    INDEX           { ptConnGroupIndex, 
                      ptSP2KEventListConfigurationIndex, 
                      ptSP2KEventListIndex }
    ::= { ptSP2KEventListTable 1 }

PtSP2KEventListEntry ::=
    SEQUENCE {
        ptSP2KEventListQuantity         Integer32,
        ptSP2KEventListConfigurationIndex Integer32,
        ptSP2KEventListParentOID        OBJECT IDENTIFIER,
        ptSP2KEventListRowStatus        RowStatus,
        ptSP2KEventListIndex            Integer32
    }

ptSP2KEventListQuantity OBJECT-TYPE
    SYNTAX          Integer32 (-2147483648..2147483647)
    MAX-ACCESS      read-only
    STATUS          current
    DESCRIPTION     
            "This attribute displays the number of events in the SP2K list."
    ::= { ptSP2KEventListEntry 1 }

ptSP2KEventListConfigurationIndex OBJECT-TYPE
    SYNTAX          Integer32 (-2147483648..2147483647)
    MAX-ACCESS      not-accessible
    STATUS          current
    DESCRIPTION     
            "This is the index of the parent type for this object.
             This parent type is Configuration."
    ::= { ptSP2KEventListEntry 242 }

ptSP2KEventListParentOID OBJECT-TYPE
    SYNTAX          OBJECT IDENTIFIER
    MAX-ACCESS      read-create
    STATUS          current
    DESCRIPTION     
            "The OID of the parent object for this instance"
    ::= { ptSP2KEventListEntry 253 }

ptSP2KEventListRowStatus OBJECT-TYPE
    SYNTAX          RowStatus
    MAX-ACCESS      read-create
    STATUS          current
    DESCRIPTION     
            "The row status for the SP2KEventList table"
    ::= { ptSP2KEventListEntry 254 }

ptSP2KEventListIndex OBJECT-TYPE
    SYNTAX          Integer32 (-2147483648..2147483647)
    MAX-ACCESS      not-accessible
    STATUS          current
    DESCRIPTION     
            "The row number for the SP2KEventList table"
    ::= { ptSP2KEventListEntry 255 }

ptSP2KEvent OBJECT IDENTIFIER
    ::= { ptSP2KEventList 322 }

ptSP2KEventTable OBJECT-TYPE
    SYNTAX          SEQUENCE OF PtSP2KEventEntry
    MAX-ACCESS      not-accessible
    STATUS          current
    DESCRIPTION     
            "No description supplied in the proxy config file."
    ::= { ptSP2KEvent 1 }

ptSP2KEventEntry OBJECT-TYPE
    SYNTAX          PtSP2KEventEntry
    MAX-ACCESS      not-accessible
    STATUS          current
    DESCRIPTION     
            "A sequence of SP2KEvent attributes."
    INDEX           { ptConnGroupIndex, ptSP2KEventConfigurationIndex, 
                      ptSP2KEventSP2KEventListIndex, ptSP2KEventIndex }
    ::= { ptSP2KEventTable 1 }

PtSP2KEventEntry ::=
    SEQUENCE {
        ptSP2KEventSeverity             INTEGER,
        ptSP2KEventSequenceNumber       Integer32,
        ptSP2KEventDateAndTime          DisplayString,
        ptSP2KEventTrapType             INTEGER,
        ptSP2KEventProblemCause         INTEGER,
        ptSP2KEventClearType            INTEGER,
        ptSP2KEventCorrelationID        DisplayString,
        ptSP2KEventTrapNameAndID        DisplayString,
        ptSP2KEventComponentID          DisplayString,
        ptSP2KEventSpecificProblem      DisplayString,
        ptSP2KEventHWEntityLocation     DisplayString,
        ptSP2KEventDescription          DisplayString,
        ptSP2KEventConfigurationIndex   Integer32,
        ptSP2KEventSP2KEventListIndex   Integer32,
        ptSP2KEventParentOID            OBJECT IDENTIFIER,
        ptSP2KEventRowStatus            RowStatus,
        ptSP2KEventIndex                Integer32
    }

ptSP2KEventSeverity OBJECT-TYPE
    SYNTAX          INTEGER { indetermined(0), critical(1), major(2), 
                        minor(3), warning(4), cleared(5) }
    MAX-ACCESS      read-only
    STATUS          current
    DESCRIPTION     
            "Severity is used in the reporting of traps. When a trap is issued it will have an associated severity.\n\n Possible Severity are: critical, major, minor, warning, cleared."
    ::= { ptSP2KEventEntry 1 }

ptSP2KEventSequenceNumber OBJECT-TYPE
    SYNTAX          Integer32 (-2147483648..2147483647)
    MAX-ACCESS      read-only
    STATUS          current
    DESCRIPTION     
            "The sequence number of the trap. This number increased by one for each trap sent by the system."
    ::= { ptSP2KEventEntry 2 }

ptSP2KEventDateAndTime OBJECT-TYPE
    SYNTAX          DisplayString (SIZE(0..255))
    MAX-ACCESS      read-only
    STATUS          current
    DESCRIPTION     
            "Date and time value of the occurrence of the trap."
    ::= { ptSP2KEventEntry 3 }

ptSP2KEventTrapType OBJECT-TYPE
    SYNTAX          INTEGER { undefined(0), communicationAlarm(2), 
                        environmentAlarm(3), equipmentAlarm(4), 
                        processingAlarm(10), qualityOfServiceAlarm(11) }
    MAX-ACCESS      read-only
    STATUS          current
    DESCRIPTION     
            "The type of the trap, follows Ref. X.733 : \n\nCommunication Alarm: An alarm of this type is principally associated with the procedures and/or processes required to convey information from one point to another.\n\nQuality of Service Alarm: An alarm of this type is principally associated with a degradation in the quality of a service.\n\nProcessing Error Alarm: An alarm of this type is principally associated with a software or processing fault.\n\nEquipment Alarm: An alarm of this type is principally associated with equipment fault.\n\nEnvironmental Alarm: An alarm of this type is principally associated with a condition relating to an enclosure in which the equipment resides."
    ::= { ptSP2KEventEntry 4 }

ptSP2KEventProblemCause OBJECT-TYPE
    SYNTAX          INTEGER { undefined(0), 
                        applicationSubsystemFailure(2), 
                        callEstablishmentError(4), 
                        communicationsProtocolError(5), 
                        communicationsSubsystemError(6), 
                        configurationOrCustomizationError(7), 
                        congestion(8), corruptData(9), 
                        cpuCyclesLimitExceeded(10), 
                        datasetOrModemError(11), degradedSignal(12), 
                        dteDceInterfaceError(13), enclosureDoorOpen(14), 
                        equipmentMalfunction(15), fileError(17), 
                        fireDetected(18), floodDetected(19), 
                        framingError(20), inputOutputDeviceError(23), 
                        inputDeviceError(24), lanError(25), 
                        localNodeTransmissionError(27), lossOfFrame(28), 
                        lossOfSignal(29), multiplexerProblem(31), 
                        outOfMemory(32), outputDeviceError(33), 
                        performanceDegraded(34), powerProblem(35), 
                        processorProblem(37), queueSizeExceeded(39), 
                        receiveFailure(40), 
                        remoteNodeTransmissionError(42), 
                        resourceAtOrNearCapacity(43), 
                        responseTimeExcessive(44), 
                        retransmissionRateExcessive(45), 
                        softwareError(46), 
                        softwareProgramAbnormallyTerminated(47), 
                        softwareProgramError(48), 
                        storageCapacityProblem(49), thresholdCrossed(51), 
                        timingProblem(52), transmitFailure(54), 
                        underlyingResourceUnavailable(56), 
                        versionMismatch(57) }
    MAX-ACCESS      read-only
    STATUS          current
    DESCRIPTION     
            "The probable cause of the trap, follows Ref. X.733. After we identify the GSN alarms, we will categorize them according to the five types above, find their probable causes, and map the causes, as close as we can, to the X.733 list."
    ::= { ptSP2KEventEntry 5 }

ptSP2KEventClearType OBJECT-TYPE
    SYNTAX          INTEGER { fmic(1), oic(2), undefined(3) }
    MAX-ACCESS      read-only
    STATUS          current
    DESCRIPTION     
            "The Clear type of the trap, which is either FMIC or OIC, where FMIC means that the trap will be cleared by another clear trap, and OIC means that the trap needs to be cleared by the operator."
    ::= { ptSP2KEventEntry 6 }

ptSP2KEventCorrelationID OBJECT-TYPE
    SYNTAX          DisplayString (SIZE(0..255))
    MAX-ACCESS      read-only
    STATUS          current
    DESCRIPTION     
            "This attribute displays the correlation ID for the trap. \n\n It is used to correlate between the active alarm and its clearing event."
    ::= { ptSP2KEventEntry 7 }

ptSP2KEventTrapNameAndID OBJECT-TYPE
    SYNTAX          DisplayString (SIZE(0..255))
    MAX-ACCESS      read-only
    STATUS          current
    DESCRIPTION     
            "This attribute displays the internal Name and ID for the trap as shown in the UI dashboard. \n\n It is used to correlate between the SP2K severity-based trap and the internal trap definition in the dashboard."
    ::= { ptSP2KEventEntry 8 }

ptSP2KEventComponentID OBJECT-TYPE
    SYNTAX          DisplayString (SIZE(0..255))
    MAX-ACCESS      read-only
    STATUS          current
    DESCRIPTION     
            "This attribute gives the name and the OID of the item type from which the variable names and values are taken.\n\n The variable names and values (listed in the specificProblem field) should clarify which item (if there are many of the same type) issued the trap and may give more information as to why the trap has been issued."
    ::= { ptSP2KEventEntry 9 }

ptSP2KEventSpecificProblem OBJECT-TYPE
    SYNTAX          DisplayString (SIZE(0..255))
    MAX-ACCESS      read-only
    STATUS          current
    DESCRIPTION     
            "This attribute lists the names and the values of all variables inserted in the trap up to the maximum length of 255 characters. Along with the component ID attribute, this gives either a way to know which item issued the trap or may give more information as to why the trap has been issued.\n\n "
    ::= { ptSP2KEventEntry 10 }

ptSP2KEventHWEntityLocation OBJECT-TYPE
    SYNTAX          DisplayString (SIZE(0..255))
    MAX-ACCESS      read-only
    STATUS          current
    DESCRIPTION     
            "This attribute provides the Frame/Shelf/Slot/Sub-Slot information. This info helps locate the management card issuing SP2K traps."
    ::= { ptSP2KEventEntry 11 }

ptSP2KEventDescription OBJECT-TYPE
    SYNTAX          DisplayString (SIZE(0..255))
    MAX-ACCESS      read-only
    STATUS          current
    DESCRIPTION     
            "This attribute provides a textual description of the condition reported in the trap."
    ::= { ptSP2KEventEntry 12 }

ptSP2KEventConfigurationIndex OBJECT-TYPE
    SYNTAX          Integer32 (-2147483648..2147483647)
    MAX-ACCESS      not-accessible
    STATUS          current
    DESCRIPTION     
            "This is the index of the parent type for this object.
             This parent type is Configuration."
    ::= { ptSP2KEventEntry 242 }

ptSP2KEventSP2KEventListIndex OBJECT-TYPE
    SYNTAX          Integer32 (-2147483648..2147483647)
    MAX-ACCESS      not-accessible
    STATUS          current
    DESCRIPTION     
            "This is the index of the parent type for this object.
             This parent type is SP2KEventList."
    ::= { ptSP2KEventEntry 243 }

ptSP2KEventParentOID OBJECT-TYPE
    SYNTAX          OBJECT IDENTIFIER
    MAX-ACCESS      read-create
    STATUS          current
    DESCRIPTION     
            "The OID of the parent object for this instance"
    ::= { ptSP2KEventEntry 253 }

ptSP2KEventRowStatus OBJECT-TYPE
    SYNTAX          RowStatus
    MAX-ACCESS      read-create
    STATUS          current
    DESCRIPTION     
            "The row status for the SP2KEvent table"
    ::= { ptSP2KEventEntry 254 }

ptSP2KEventIndex OBJECT-TYPE
    SYNTAX          Integer32 (-2147483648..2147483647)
    MAX-ACCESS      not-accessible
    STATUS          current
    DESCRIPTION     
            "The row number for the SP2KEvent table"
    ::= { ptSP2KEventEntry 255 }

ptActiveTrapList OBJECT IDENTIFIER
    ::= { ptConfiguration 323 }

ptActiveTrapListTable OBJECT-TYPE
    SYNTAX          SEQUENCE OF PtActiveTrapListEntry
    MAX-ACCESS      not-accessible
    STATUS          current
    DESCRIPTION     
            "No description supplied in the proxy config file."
    ::= { ptActiveTrapList 1 }

ptActiveTrapListEntry OBJECT-TYPE
    SYNTAX          PtActiveTrapListEntry
    MAX-ACCESS      not-accessible
    STATUS          current
    DESCRIPTION     
            "A sequence of ActiveTrapList attributes."
    INDEX           { ptConnGroupIndex, 
                      ptActiveTrapListConfigurationIndex, 
                      ptActiveTrapListIndex }
    ::= { ptActiveTrapListTable 1 }

PtActiveTrapListEntry ::=
    SEQUENCE {
        ptActiveTrapListQuantity        Integer32,
        ptActiveTrapListConfigurationIndex  Integer32,
        ptActiveTrapListParentOID       OBJECT IDENTIFIER,
        ptActiveTrapListRowStatus       RowStatus,
        ptActiveTrapListIndex           Integer32
    }

ptActiveTrapListQuantity OBJECT-TYPE
    SYNTAX          Integer32 (-2147483648..2147483647)
    MAX-ACCESS      read-only
    STATUS          current
    DESCRIPTION     
            "This attribute displays the current number of outstanding events in the system."
    ::= { ptActiveTrapListEntry 1 }

ptActiveTrapListConfigurationIndex OBJECT-TYPE
    SYNTAX          Integer32 (-2147483648..2147483647)
    MAX-ACCESS      not-accessible
    STATUS          current
    DESCRIPTION     
            "This is the index of the parent type for this object.
             This parent type is Configuration."
    ::= { ptActiveTrapListEntry 242 }

ptActiveTrapListParentOID OBJECT-TYPE
    SYNTAX          OBJECT IDENTIFIER
    MAX-ACCESS      read-create
    STATUS          current
    DESCRIPTION     
            "The OID of the parent object for this instance"
    ::= { ptActiveTrapListEntry 253 }

ptActiveTrapListRowStatus OBJECT-TYPE
    SYNTAX          RowStatus
    MAX-ACCESS      read-create
    STATUS          current
    DESCRIPTION     
            "The row status for the ActiveTrapList table"
    ::= { ptActiveTrapListEntry 254 }

ptActiveTrapListIndex OBJECT-TYPE
    SYNTAX          Integer32 (-2147483648..2147483647)
    MAX-ACCESS      not-accessible
    STATUS          current
    DESCRIPTION     
            "The row number for the ActiveTrapList table"
    ::= { ptActiveTrapListEntry 255 }

ptActiveTrap OBJECT IDENTIFIER
    ::= { ptActiveTrapList 324 }

ptActiveTrapTable OBJECT-TYPE
    SYNTAX          SEQUENCE OF PtActiveTrapEntry
    MAX-ACCESS      not-accessible
    STATUS          current
    DESCRIPTION     
            "No description supplied in the proxy config file."
    ::= { ptActiveTrap 1 }

ptActiveTrapEntry OBJECT-TYPE
    SYNTAX          PtActiveTrapEntry
    MAX-ACCESS      not-accessible
    STATUS          current
    DESCRIPTION     
            "A sequence of ActiveTrap attributes."
    INDEX           { ptConnGroupIndex, ptActiveTrapConfigurationIndex, 
                      ptActiveTrapActiveTrapListIndex, ptActiveTrapIndex }
    ::= { ptActiveTrapTable 1 }

PtActiveTrapEntry ::=
    SEQUENCE {
        ptActiveTrapTrapName            DisplayString,
        ptActiveTrapSequenceNumber      Integer32,
        ptActiveTrapDateAndTime         DisplayString,
        ptActiveTrapTrapType            INTEGER,
        ptActiveTrapSeverity            INTEGER,
        ptActiveTrapProblemCause        INTEGER,
        ptActiveTrapClearType           INTEGER,
        ptActiveTrapItemType            DisplayString,
        ptActiveTrapVariableName1       DisplayString,
        ptActiveTrapVariableValue1      DisplayString,
        ptActiveTrapOid1                DisplayString,
        ptActiveTrapOidType1            DisplayString,
        ptActiveTrapVariableName2       DisplayString,
        ptActiveTrapVariableValue2      DisplayString,
        ptActiveTrapOid2                DisplayString,
        ptActiveTrapOidType2            DisplayString,
        ptActiveTrapVariableName3       DisplayString,
        ptActiveTrapVariableValue3      DisplayString,
        ptActiveTrapOid3                DisplayString,
        ptActiveTrapOidType3            DisplayString,
        ptActiveTrapVariableName4       DisplayString,
        ptActiveTrapVariableValue4      DisplayString,
        ptActiveTrapOid4                DisplayString,
        ptActiveTrapOidType4            DisplayString,
        ptActiveTrapVariableName5       DisplayString,
        ptActiveTrapVariableValue5      DisplayString,
        ptActiveTrapOid5                DisplayString,
        ptActiveTrapOidType5            DisplayString,
        ptActiveTrapVariableName6       DisplayString,
        ptActiveTrapVariableValue6      DisplayString,
        ptActiveTrapOid6                DisplayString,
        ptActiveTrapOidType6            DisplayString,
        ptActiveTrapVariableName7       DisplayString,
        ptActiveTrapVariableValue7      DisplayString,
        ptActiveTrapOid7                DisplayString,
        ptActiveTrapOidType7            DisplayString,
        ptActiveTrapVariableName8       DisplayString,
        ptActiveTrapVariableValue8      DisplayString,
        ptActiveTrapOid8                DisplayString,
        ptActiveTrapOidType8            DisplayString,
        ptActiveTrapVariableName9       DisplayString,
        ptActiveTrapVariableValue9      DisplayString,
        ptActiveTrapOid9                DisplayString,
        ptActiveTrapOidType9            DisplayString,
        ptActiveTrapVariableName10      DisplayString,
        ptActiveTrapVariableValue10     DisplayString,
        ptActiveTrapOid10               DisplayString,
        ptActiveTrapOidType10           DisplayString,
        ptActiveTrapItemOID             DisplayString,
        ptActiveTrapConfigurationIndex  Integer32,
        ptActiveTrapActiveTrapListIndex Integer32,
        ptActiveTrapParentOID           OBJECT IDENTIFIER,
        ptActiveTrapRowStatus           RowStatus,
        ptActiveTrapIndex               Integer32
    }

ptActiveTrapTrapName OBJECT-TYPE
    SYNTAX          DisplayString (SIZE(0..255))
    MAX-ACCESS      read-only
    STATUS          current
    DESCRIPTION     
            "The name of the trap issued. For more information concerning possible traps names, please look at the provided mib files."
    ::= { ptActiveTrapEntry 1 }

ptActiveTrapSequenceNumber OBJECT-TYPE
    SYNTAX          Integer32 (-2147483648..2147483647)
    MAX-ACCESS      read-only
    STATUS          current
    DESCRIPTION     
            "The sequence number of the trap\n This number increased by one for each trap sent by the system."
    ::= { ptActiveTrapEntry 2 }

ptActiveTrapDateAndTime OBJECT-TYPE
    SYNTAX          DisplayString (SIZE(0..255))
    MAX-ACCESS      read-only
    STATUS          current
    DESCRIPTION     
            "Date and time value of the occurrence of the trap."
    ::= { ptActiveTrapEntry 3 }

ptActiveTrapTrapType OBJECT-TYPE
    SYNTAX          INTEGER { undefined(0), communicationAlarm(2), 
                        environmentAlarm(3), equipmentAlarm(4), 
                        processingAlarm(10), qualityOfServiceAlarm(11) }
    MAX-ACCESS      read-only
    STATUS          current
    DESCRIPTION     
            "The type of the trap, follows Ref. X.733 : \n\nCommunication Alarm: An alarm of this type is principally associated with the procedures and/or processes required to convey information from one point to another. \n\nQuality of Service Alarm: An alarm of this type is principally associated with a degradation in the quality of a service.\n\nProcessing Error Alarm: An alarm of this type is principally associated with a software or processing fault.\n\nEquipment Alarm: An alarm of this type is principally associated with equipment fault.\n\nEnvironmental Alarm: An alarm of this type is principally associated with a condition relating to an enclosure in which the equipment resides."
    ::= { ptActiveTrapEntry 4 }

ptActiveTrapSeverity OBJECT-TYPE
    SYNTAX          INTEGER { indetermined(0), critical(1), major(2), 
                        minor(3), warning(4), cleared(5) }
    MAX-ACCESS      read-only
    STATUS          current
    DESCRIPTION     
            "Severity is used in the reporting of traps. When a trap is issued it will have an associated severity.\n\n Possible Severity are: indeterminate, critical, major, minor, warning, cleared."
    ::= { ptActiveTrapEntry 5 }

ptActiveTrapProblemCause OBJECT-TYPE
    SYNTAX          INTEGER { undefined(0), 
                        applicationSubsystemFailure(2), 
                        callEstablishmentError(4), 
                        communicationsProtocolError(5), 
                        communicationsSubsystemError(6), 
                        configurationOrCustomizationError(7), 
                        congestion(8), corruptData(9), 
                        cpuCyclesLimitExceeded(10), 
                        datasetOrModemError(11), degradedSignal(12), 
                        dteDceInterfaceError(13), enclosureDoorOpen(14), 
                        equipmentMalfunction(15), fileError(17), 
                        fireDetected(18), floodDetected(19), 
                        framingError(20), inputOutputDeviceError(23), 
                        inputDeviceError(24), lanError(25), 
                        localNodeTransmissionError(27), lossOfFrame(28), 
                        lossOfSignal(29), multiplexerProblem(31), 
                        outOfMemory(32), outputDeviceError(33), 
                        performanceDegraded(34), powerProblem(35), 
                        processorProblem(37), queueSizeExceeded(39), 
                        receiveFailure(40), 
                        remoteNodeTransmissionError(42), 
                        resourceAtOrNearCapacity(43), 
                        responseTimeExcessive(44), 
                        retransmissionRateExcessive(45), 
                        softwareError(46), 
                        softwareProgramAbnormallyTerminated(47), 
                        softwareProgramError(48), 
                        storageCapacityProblem(49), thresholdCrossed(51), 
                        timingProblem(52), transmitFailure(54), 
                        underlyingResourceUnavailable(56), 
                        versionMismatch(57) }
    MAX-ACCESS      read-only
    STATUS          current
    DESCRIPTION     
            "The probable cause of the trap, follows Ref. X.733. After we identify the GSN alarms, we will categorize them according to the five types above, find their probable causes, and map the causes, as close as we can, to the X.733 list."
    ::= { ptActiveTrapEntry 6 }

ptActiveTrapClearType OBJECT-TYPE
    SYNTAX          INTEGER { fmic(1), oic(2), undefined(3) }
    MAX-ACCESS      read-only
    STATUS          current
    DESCRIPTION     
            "The Clear type of the trap, which is either FMIC or OIC, where FMIC means that the trap will be cleared by another clear trap, and OIC means that the trap needs to be cleared by the operator."
    ::= { ptActiveTrapEntry 7 }

ptActiveTrapItemType OBJECT-TYPE
    SYNTAX          DisplayString (SIZE(0..255))
    MAX-ACCESS      read-only
    STATUS          current
    DESCRIPTION     
            "This attribute gives the name of the item type from which the variable names and values are taken.\n\n The variable names and values should clarify which item (if there are many of the same type) issued the trap and may give more information as to why the trap has been issued."
    ::= { ptActiveTrapEntry 8 }

ptActiveTrapVariableName1 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 9 }

ptActiveTrapVariableValue1 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 10 }

ptActiveTrapOid1 OBJECT-TYPE
    SYNTAX          DisplayString (SIZE(0..255))
    MAX-ACCESS      read-only
    STATUS          current
    DESCRIPTION     
            "This attribute is varbind oid"
    ::= { ptActiveTrapEntry 11 }

ptActiveTrapOidType1 OBJECT-TYPE
    SYNTAX          DisplayString (SIZE(0..255))
    MAX-ACCESS      read-only
    STATUS          current
    DESCRIPTION     
            "This attribute is varbind type"
    ::= { ptActiveTrapEntry 12 }

ptActiveTrapVariableName2 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 13 }

ptActiveTrapVariableValue2 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 14 }

ptActiveTrapOid2 OBJECT-TYPE
    SYNTAX          DisplayString (SIZE(0..255))
    MAX-ACCESS      read-only
    STATUS          current
    DESCRIPTION     
            "This attribute is varbind oid"
    ::= { ptActiveTrapEntry 15 }

ptActiveTrapOidType2 OBJECT-TYPE
    SYNTAX          DisplayString (SIZE(0..255))
    MAX-ACCESS      read-only
    STATUS          current
    DESCRIPTION     
            "This attribute is varbind type"
    ::= { ptActiveTrapEntry 16 }

ptActiveTrapVariableName3 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 17 }

ptActiveTrapVariableValue3 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 18 }

ptActiveTrapOid3 OBJECT-TYPE
    SYNTAX          DisplayString (SIZE(0..255))
    MAX-ACCESS      read-only
    STATUS          current
    DESCRIPTION     
            "This attribute is varbind oid"
    ::= { ptActiveTrapEntry 19 }

ptActiveTrapOidType3 OBJECT-TYPE
    SYNTAX          DisplayString (SIZE(0..255))
    MAX-ACCESS      read-only
    STATUS          current
    DESCRIPTION     
            "This attribute is varbind type"
    ::= { ptActiveTrapEntry 20 }

ptActiveTrapVariableName4 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 21 }

ptActiveTrapVariableValue4 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 22 }

ptActiveTrapOid4 OBJECT-TYPE
    SYNTAX          DisplayString (SIZE(0..255))
    MAX-ACCESS      read-only
    STATUS          current
    DESCRIPTION     
            "This attribute is varbind oid"
    ::= { ptActiveTrapEntry 23 }

ptActiveTrapOidType4 OBJECT-TYPE
    SYNTAX          DisplayString (SIZE(0..255))
    MAX-ACCESS      read-only
    STATUS          current
    DESCRIPTION     
            "This attribute is varbind type"
    ::= { ptActiveTrapEntry 24 }

ptActiveTrapVariableName5 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 25 }

ptActiveTrapVariableValue5 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 26 }

ptActiveTrapOid5 OBJECT-TYPE
    SYNTAX          DisplayString (SIZE(0..255))
    MAX-ACCESS      read-only
    STATUS          current
    DESCRIPTION     
            "This attribute is varbind oid"
    ::= { ptActiveTrapEntry 27 }

ptActiveTrapOidType5 OBJECT-TYPE
    SYNTAX          DisplayString (SIZE(0..255))
    MAX-ACCESS      read-only
    STATUS          current
    DESCRIPTION     
            "This attribute is varbind type"
    ::= { ptActiveTrapEntry 28 }

ptActiveTrapVariableName6 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 29 }

ptActiveTrapVariableValue6 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 30 }

ptActiveTrapOid6 OBJECT-TYPE
    SYNTAX          DisplayString (SIZE(0..255))
    MAX-ACCESS      read-only
    STATUS          current
    DESCRIPTION     
            "This attribute is varbind oid"
    ::= { ptActiveTrapEntry 31 }

ptActiveTrapOidType6 OBJECT-TYPE
    SYNTAX          DisplayString (SIZE(0..255))
    MAX-ACCESS      read-only
    STATUS          current
    DESCRIPTION     
            "This attribute is varbind type"
    ::= { ptActiveTrapEntry 32 }

ptActiveTrapVariableName7 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 33 }

ptActiveTrapVariableValue7 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 34 }

ptActiveTrapOid7 OBJECT-TYPE
    SYNTAX          DisplayString (SIZE(0..255))
    MAX-ACCESS      read-only
    STATUS          current
    DESCRIPTION     
            "This attribute is varbind oid"
    ::= { ptActiveTrapEntry 35 }

ptActiveTrapOidType7 OBJECT-TYPE
    SYNTAX          DisplayString (SIZE(0..255))
    MAX-ACCESS      read-only
    STATUS          current
    DESCRIPTION     
            "This attribute is varbind type"
    ::= { ptActiveTrapEntry 36 }

ptActiveTrapVariableName8 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 37 }

ptActiveTrapVariableValue8 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 38 }

ptActiveTrapOid8 OBJECT-TYPE
    SYNTAX          DisplayString (SIZE(0..255))
    MAX-ACCESS      read-only
    STATUS          current
    DESCRIPTION     
            "This attribute is varbind oid"
    ::= { ptActiveTrapEntry 39 }

ptActiveTrapOidType8 OBJECT-TYPE
    SYNTAX          DisplayString (SIZE(0..255))
    MAX-ACCESS      read-only
    STATUS          current
    DESCRIPTION     
            "This attribute is varbind type"
    ::= { ptActiveTrapEntry 40 }

ptActiveTrapVariableName9 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 41 }

ptActiveTrapVariableValue9 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 42 }

ptActiveTrapOid9 OBJECT-TYPE
    SYNTAX          DisplayString (SIZE(0..255))
    MAX-ACCESS      read-only
    STATUS          current
    DESCRIPTION     
            "This attribute is varbind oid"
    ::= { ptActiveTrapEntry 43 }

ptActiveTrapOidType9 OBJECT-TYPE
    SYNTAX          DisplayString (SIZE(0..255))
    MAX-ACCESS      read-only
    STATUS          current
    DESCRIPTION     
            "This attribute is varbind type"
    ::= { ptActiveTrapEntry 44 }

ptActiveTrapVariableName10 OBJECT-TYPE
    SYNTAX          DisplayString (SIZE(0..255))
    MAX-ACCESS      read-only
    STATUS          current
    DESCRIPTION     
            "This attribute gives the name of a variable that was inserted in the trap. Associated with its variable value, this gives either a way to know which item issued the trap or may give more information as to why the trap has been issued.\n\n A maximum of 10 variables might have been included in a trap."
    ::= { ptActiveTrapEntry 45 }

ptActiveTrapVariableValue10 OBJECT-TYPE
    SYNTAX          DisplayString (SIZE(0..255))
    MAX-ACCESS      read-only
    STATUS          current
    DESCRIPTION     
            "This attribute gives the value of a variable that was inserted in the trap. Associated with its variable name, this gives either a way to know which item issued the trap or may give more information as to why the trap has been issued."
    ::= { ptActiveTrapEntry 46 }

ptActiveTrapOid10 OBJECT-TYPE
    SYNTAX          DisplayString (SIZE(0..255))
    MAX-ACCESS      read-only
    STATUS          current
    DESCRIPTION     
            "This attribute is varbind oid"
    ::= { ptActiveTrapEntry 47 }

ptActiveTrapOidType10 OBJECT-TYPE
    SYNTAX          DisplayString (SIZE(0..255))
    MAX-ACCESS      read-only
    STATUS          current
    DESCRIPTION     
            "This attribute is varbind type"
    ::= { ptActiveTrapEntry 48 }

ptActiveTrapItemOID OBJECT-TYPE
    SYNTAX          DisplayString (SIZE(0..255))
    MAX-ACCESS      read-only
    STATUS          current
    DESCRIPTION     
            "This attribute gives the Object Identifier (OID) of the item that produced the trap.\n\n"
    ::= { ptActiveTrapEntry 49 }

ptActiveTrapConfigurationIndex OBJECT-TYPE
    SYNTAX          Integer32 (-2147483648..2147483647)
    MAX-ACCESS      not-accessible
    STATUS          current
    DESCRIPTION     
            "This is the index of the parent type for this object.
             This parent type is Configuration."
    ::= { ptActiveTrapEntry 242 }

ptActiveTrapActiveTrapListIndex OBJECT-TYPE
    SYNTAX          Integer32 (-2147483648..2147483647)
    MAX-ACCESS      not-accessible
    STATUS          current
    DESCRIPTION     
            "This is the index of the parent type for this object.
             This parent type is ActiveTrapList."
    ::= { ptActiveTrapEntry 243 }

ptActiveTrapParentOID OBJECT-TYPE
    SYNTAX          OBJECT IDENTIFIER
    MAX-ACCESS      read-create
    STATUS          current
    DESCRIPTION     
            "The OID of the parent object for this instance"
    ::= { ptActiveTrapEntry 253 }

ptActiveTrapRowStatus OBJECT-TYPE
    SYNTAX          RowStatus
    MAX-ACCESS      read-create
    STATUS          current
    DESCRIPTION     
            "The row status for the ActiveTrap table"
    ::= { ptActiveTrapEntry 254 }

ptActiveTrapIndex OBJECT-TYPE
    SYNTAX          Integer32 (-2147483648..2147483647)
    MAX-ACCESS      not-accessible
    STATUS          current
    DESCRIPTION     
            "The row number for the ActiveTrap table"
    ::= { ptActiveTrapEntry 255 }

ptPCEPCE OBJECT IDENTIFIER
    ::= { ptConnGroup 451 }

ptPCEPCETable OBJECT-TYPE
    SYNTAX          SEQUENCE OF PtPCEPCEEntry
    MAX-ACCESS      not-accessible
    STATUS          current
    DESCRIPTION     
            "No description supplied in the proxy config file."
    ::= { ptPCEPCE 1 }

ptPCEPCEEntry OBJECT-TYPE
    SYNTAX          PtPCEPCEEntry
    MAX-ACCESS      not-accessible
    STATUS          current
    DESCRIPTION     
            "A sequence of PCEPCE attributes."
    INDEX           { ptConnGroupIndex, ptPCEPCEIndex }
    ::= { ptPCEPCETable 1 }

PtPCEPCEEntry ::=
    SEQUENCE {
        ptPCEPCEParentOID               OBJECT IDENTIFIER,
        ptPCEPCERowStatus               RowStatus,
        ptPCEPCEIndex                   Integer32
    }

ptPCEPCEParentOID OBJECT-TYPE
    SYNTAX          OBJECT IDENTIFIER
    MAX-ACCESS      read-create
    STATUS          current
    DESCRIPTION     
            "The OID of the parent object for this instance"
    ::= { ptPCEPCEEntry 253 }

ptPCEPCERowStatus OBJECT-TYPE
    SYNTAX          RowStatus
    MAX-ACCESS      read-create
    STATUS          current
    DESCRIPTION     
            "The row status for the PCEPCE table"
    ::= { ptPCEPCEEntry 254 }

ptPCEPCEIndex OBJECT-TYPE
    SYNTAX          Integer32 (-2147483648..2147483647)
    MAX-ACCESS      not-accessible
    STATUS          current
    DESCRIPTION     
            "The row number for the PCEPCE table"
    ::= { ptPCEPCEEntry 255 }

ptPCEPCEConfiguration OBJECT IDENTIFIER
    ::= { ptConnGroup 452 }

ptPCEPCEConfigurationTable OBJECT-TYPE
    SYNTAX          SEQUENCE OF PtPCEPCEConfigurationEntry
    MAX-ACCESS      not-accessible
    STATUS          current
    DESCRIPTION     
            "No description supplied in the proxy config file."
    ::= { ptPCEPCEConfiguration 1 }

ptPCEPCEConfigurationEntry OBJECT-TYPE
    SYNTAX          PtPCEPCEConfigurationEntry
    MAX-ACCESS      not-accessible
    STATUS          current
    DESCRIPTION     
            "A sequence of PCEPCEConfiguration attributes."
    INDEX           { ptConnGroupIndex, ptPCEPCEConfigurationIndex }
    ::= { ptPCEPCEConfigurationTable 1 }

PtPCEPCEConfigurationEntry ::=
    SEQUENCE {
        ptPCEPCEConfigurationName       DisplayString,
        ptPCEPCEConfigurationSS7Variant INTEGER,
        ptPCEPCEConfigurationSupportedTraffic     INTEGER,
        ptPCEPCEConfigurationMonoMode   INTEGER,
        ptPCEPCEConfigurationConfigurationType      INTEGER,
        ptPCEPCEConfigurationPCETraffic INTEGER,
        ptPCEPCEConfigurationUnavailablePeerIDs       DisplayString,
        ptPCEPCEConfigurationISUPManagement   INTEGER,
        ptPCEPCEConfigurationCGBGeneration  INTEGER,
        ptPCEPCEConfigurationUCICSupport INTEGER,
        ptPCEPCEConfigurationPrivatePCAuditing      INTEGER,
        ptPCEPCEConfigurationPublicPCAuditing     INTEGER,
        ptPCEPCEConfigurationTransactionTimeout       INTEGER,
        ptPCEPCEConfigurationVariant    INTEGER,
        ptPCEPCEConfigurationDefaultPrivateOPC      Integer32,
        ptPCEPCEConfigurationBroadcastToPrivate       INTEGER,
        ptPCEPCEConfigurationISUPLearning INTEGER,
        ptPCEPCEConfigurationISUPLearningDigits       INTEGER,
        ptPCEPCEConfigurationISUPLearningQueryTimeout             INTEGER,
        ptPCEPCEConfigurationErrors     INTEGER,
        ptPCEPCEConfigurationSetupManagement    INTEGER,
        ptPCEPCEConfigurationExecutionTrace   INTEGER,
        ptPCEPCEConfigurationLayerCommunication       INTEGER,
        ptPCEPCEConfigurationPeerManagement   INTEGER,
        ptPCEPCEConfigurationSS7Messages INTEGER,
        ptPCEPCEConfigurationMaxPublicNodes   Integer32,
        ptPCEPCEConfigurationMaxPrivateNodes    Integer32,
        ptPCEPCEConfigurationMaxPublicGateways      Integer32,
        ptPCEPCEConfigurationMaxGTTTunnelGateways         Integer32,
        ptPCEPCEConfigurationMaxTrunkMappings     Integer32,
        ptPCEPCEConfigurationMaxISUPLearningExceptions              Integer32,
        ptPCEPCEConfigurationTransactionIDMapping         INTEGER,
        ptPCEPCEConfigurationIS41BillingIDRouting         INTEGER,
        ptPCEPCEConfigurationMaxIS41BillingIDMappings             Integer32,
        ptPCEPCEConfigurationIS41Conversion   INTEGER,
        ptPCEPCEConfigurationLDLDebugLevel  Integer32,
        ptPCEPCEConfigurationLDLSCTPDebugLevel      Integer32,
        ptPCEPCEConfigurationMaxReportingPerInterval            Integer32,
        ptPCEPCEConfigurationReportingInterval      INTEGER,
        ptPCEPCEConfigurationForwardedPublicQueries           INTEGER,
        ptPCEPCEConfigurationFileManagement   INTEGER,
        ptPCEPCEConfigurationDatabaseManagement       INTEGER,
        ptPCEPCEConfigurationSCCPTCAPMapping    INTEGER,
        ptPCEPCEConfigurationNonMemberRoutesetSupport             INTEGER,
        ptPCEPCEConfigurationActions    INTEGER,
        ptPCEPCEConfigurationParentOID  OBJECT IDENTIFIER,
        ptPCEPCEConfigurationRowStatus  RowStatus,
        ptPCEPCEConfigurationIndex      Integer32
    }

ptPCEPCEConfigurationName OBJECT-TYPE
    SYNTAX          DisplayString (SIZE(0..255))
    MAX-ACCESS      read-only
    STATUS          current
    DESCRIPTION     
            "Name of the CPU currently 'Active', or in control of the User provisioned data. \nThe active peer is identified by the LDL peer ID as found in the PCE LDL file (default pce_ldl.conf). \nAll CPUs will be handling PCE traffic in a load sharing manner. However the Active CPU will be in control of the User Provisioned data. The CPU designated as active can change transparently to the user. This attribute maybe consulted during software upgrades."
    ::= { ptPCEPCEConfigurationEntry 1 }

ptPCEPCEConfigurationSS7Variant OBJECT-TYPE
    SYNTAX          INTEGER { undefined(255), ansi(1), itu(2) }
    MAX-ACCESS      read-create
    STATUS          current
    DESCRIPTION     
            "This attribute sets the SS7 variant (ANSI/ITU). The variant listed here must be set to agree with the variant set at the MTP3. Applies to all PCE defined NAs. \nThis attribute does NOT indicate the TCAP variant, which will be determined on a message by message basis, so that ANSI networks can use ANSI and ITU TCAP messages at the same time as per their IN, AIN and GSM requirements."
    ::= { ptPCEPCEConfigurationEntry 2 }

ptPCEPCEConfigurationSupportedTraffic OBJECT-TYPE
    SYNTAX          INTEGER { isup(0), tcap(1), tcapIsup(2) }
    MAX-ACCESS      read-create
    STATUS          current
    DESCRIPTION     
            "This attribute indicates the levels of traffic to be supported by this system. The valid options are: (ISUP/TCAP/TCAP_ISUP)."
    ::= { ptPCEPCEConfigurationEntry 4 }

ptPCEPCEConfigurationMonoMode OBJECT-TYPE
    SYNTAX          INTEGER { disabled(0), enabled(1) }
    MAX-ACCESS      read-create
    STATUS          current
    DESCRIPTION     
            "Mono Mode is enabled during certain maintenance activities, usually as directed by Sonus Networks Customer Support. The Mono Mode feature indicates to the PCE software that the other PCE CPU(s) are still functioning, but are not in communication with this CPU. In such a situation, we do not want this PCE to send out Circuit Group Block (CGB) ISUP messages when a private switch is unavailable, because that switch may be available to the other PCE CPUs. \nThe default value for this attribute is DISABLED."
    ::= { ptPCEPCEConfigurationEntry 5 }

ptPCEPCEConfigurationConfigurationType OBJECT-TYPE
    SYNTAX          INTEGER { basic(0), enhanced(1) }
    MAX-ACCESS      read-only
    STATUS          current
    DESCRIPTION     
            "PCE Configuration Type (BASIC/ENHANCED) is based on your licensed capabilities. BASIC PCE is the most common form of PCE and divides the SS7 network into 1 Public and 1 Private network. The ENHANCED PCE is used to migrate trunks from one switch to another, where both switches have the same Point Code. ENHANCED PCE divides the SS7 network into 1 Public and 2 Private networks."
    ::= { ptPCEPCEConfigurationEntry 6 }

ptPCEPCEConfigurationPCETraffic OBJECT-TYPE
    SYNTAX          INTEGER { inactive(0), active(1), pceUnlicensed(2), 
                        enhancedUnlicensed(3) }
    MAX-ACCESS      read-only
    STATUS          current
    DESCRIPTION     
            "PCE Traffic (INACTIVE/ACTIVE/PCE_UNLICENSED); This attribute will indicate the state of the PCE traffic. The state can be changed between INACTIVE and ACTIVE, by using the action buttons on this screen. \nPCE requires you to intentionally deactivate traffic before changing some traffic impacting settings such as Variant. This is done as an extra check to confirm the change."
    ::= { ptPCEPCEConfigurationEntry 7 }

ptPCEPCEConfigurationUnavailablePeerIDs OBJECT-TYPE
    SYNTAX          DisplayString (SIZE(0..255))
    MAX-ACCESS      read-only
    STATUS          current
    DESCRIPTION     
            "Should one or more CPUs lose communication with this CPU, then those CPUs will be listed here. The most common cause of communication problems are IP network related."
    ::= { ptPCEPCEConfigurationEntry 8 }

ptPCEPCEConfigurationISUPManagement OBJECT-TYPE
    SYNTAX          INTEGER { disabled(0), enabled(1) }
    MAX-ACCESS      read-create
    STATUS          current
    DESCRIPTION     
            "Enable of disable the ISUP Management feature. \nIf ISUP Management is disabled, public network messages for unreachable private network destinations are discarded. \nIf ISUP Management is enabled, public network messages for unreachable private network destinations are processed (see PCE User Guide)."
    ::= { ptPCEPCEConfigurationEntry 9 }

ptPCEPCEConfigurationCGBGeneration OBJECT-TYPE
    SYNTAX          INTEGER { disabled(0), enabled(1) }
    MAX-ACCESS      read-create
    STATUS          current
    DESCRIPTION     
            "Enable or disable the CGB Generation feature. \nThe CGB Generation feature only takes effect if the ISUP Management feature is also enabled."
    ::= { ptPCEPCEConfigurationEntry 10 }

ptPCEPCEConfigurationUCICSupport OBJECT-TYPE
    SYNTAX          INTEGER { disabled(0), enabled(1) }
    MAX-ACCESS      read-create
    STATUS          current
    DESCRIPTION     
            "Enable or disable the Public Network UCIC Support."
    ::= { ptPCEPCEConfigurationEntry 11 }

ptPCEPCEConfigurationPrivatePCAuditing OBJECT-TYPE
    SYNTAX          INTEGER { disabled(0) }
    MAX-ACCESS      read-create
    STATUS          current
    DESCRIPTION     
            "Interval at which the Private PC Audits are sent (in seconds); \nThis must be enabled if a private network MTP3 has cluster, network, or default Routesets. \nA point code audit will be automatically cleared on the receipt of a corresponding MTP-RESUME (MTP3 TFA) or MTP-LOCAL-STATUS Unavailable (all linksets unavailable). \nA value of zero seconds will turn off the feature. \nThe default value is 30 seconds."
    ::= { ptPCEPCEConfigurationEntry 12 }

ptPCEPCEConfigurationPublicPCAuditing OBJECT-TYPE
    SYNTAX          INTEGER { disabled(0) }
    MAX-ACCESS      read-create
    STATUS          current
    DESCRIPTION     
            "Interval at which the Public PC Audits are sent (in seconds); \nThis must be enabled if the public network MTP3 has cluster, network, or default Routesets. \nA point code audit will be automatically cleared on the receipt of a corresponding MTP-RESUME (MTP3 TFA) or MTP-LOCAL-STATUS Unavailable (all linksets unavailable). \nA value of zero seconds will turn off the feature. \nThe default value is 30 seconds."
    ::= { ptPCEPCEConfigurationEntry 13 }

ptPCEPCEConfigurationTransactionTimeout OBJECT-TYPE
    SYNTAX          INTEGER { disabled(0) }
    MAX-ACCESS      read-create
    STATUS          current
    DESCRIPTION     
            "Interval at which the TCAP mapping records are cleared (in seconds). \nThe completion of a transaction will clear the corresponding record automatically but an unfinished transaction must be cleared after their lifespan expires."
    ::= { ptPCEPCEConfigurationEntry 15 }

ptPCEPCEConfigurationVariant OBJECT-TYPE
    SYNTAX          INTEGER { autoDetect(0), ansi(1), itu(2) }
    MAX-ACCESS      read-create
    STATUS          current
    DESCRIPTION     
            "TCAP Variant (AUTO DETECT/ANSI/ITU). \nThe TCAP Variant can be determined on a per message basis based on the TCAP message type. If the TCAP Variant is not set to AUTO DETECT and a message is not supported in the given TCAP Variant, the message is discarded."
    ::= { ptPCEPCEConfigurationEntry 16 }

ptPCEPCEConfigurationDefaultPrivateOPC OBJECT-TYPE
    SYNTAX          Integer32 (-2147483648..2147483647)
    MAX-ACCESS      read-create
    STATUS          current
    DESCRIPTION     
            "TCAP Default Private OPC. \nFor public TCAP traffic to a private network where a Public Node is not defined, set the message OPC and SCCP CLG, if present, to the TCAP Default Private OPC. \nTo remove this feature set the value to '-1', which will remove the PC value from the attribute."
    ::= { ptPCEPCEConfigurationEntry 17 }

ptPCEPCEConfigurationBroadcastToPrivate OBJECT-TYPE
    SYNTAX          INTEGER { disabled(0), random(1), all(2) }
    MAX-ACCESS      read-create
    STATUS          current
    DESCRIPTION     
            "Broadcast public initiated TCAP query to one or all Private Nodes. \nIf set to ALL, the public initiated TCAP query in forwarded to all Private Nodes. If set to RANDOM, the public initiated TCAP query will be sent to a randomly chosen Private Node. \nIf disabled and GTT routing has failed, the message will be discarded"
    ::= { ptPCEPCEConfigurationEntry 18 }

ptPCEPCEConfigurationISUPLearning OBJECT-TYPE
    SYNTAX          INTEGER { disabled(0) }
    MAX-ACCESS      read-create
    STATUS          current
    DESCRIPTION     
            "Interval at which the TCAP ISUP Learning records are cleared (in seconds). \nSet to 0 (DISABLED) to disable the TCAP ISUP Learning feature."
    ::= { ptPCEPCEConfigurationEntry 19 }

ptPCEPCEConfigurationISUPLearningDigits OBJECT-TYPE
    SYNTAX          INTEGER { called(0), originalElseCalled(1), 
                        originalAndCalled(2), calledAndCalling(3), 
                        originalElseCalledAndCalling(4), all(5) }
    MAX-ACCESS      read-create
    STATUS          current
    DESCRIPTION     
            "ISUP IAM digit parameters which are used for TCAP ISUP Learning. \nSet to CALLED for Called Party Number parameter. \nSet to ORIGINAL ELSE CALLED for Original Called Number if present else Called Party Number parameter. \nSet to ORIGINAL AND CALLED for the Original Called Number if present and the Called Party Number parameter(s). \nSet to CALLED AND CALLING for Called and Calling Party Number parameters. \nSet to ORIGINAL ELSE CALLED AND CALLING for the Original Called Number if present else the Called Party Number, and the Calling Party Number. \nSet to ALL for Called, Calling and Original Called (if present) Party Number parameters."
    ::= { ptPCEPCEConfigurationEntry 20 }

ptPCEPCEConfigurationISUPLearningQueryTimeout OBJECT-TYPE
    SYNTAX          INTEGER { noneBroadcast(0) }
    MAX-ACCESS      read-create
    STATUS          current
    DESCRIPTION     
            "TCAP ISUP Learning query timeout for a Public TCAP query (in milliseconds). \nBy default, the timeout is set to NONE (BROADCAST) where each IAM immediately broadcasts its learned information to all peers. For heavy ISUP traffic with minimal TCAP queries, the query-and-response implementation is recommended with a 1000 milliseconds delay."
    ::= { ptPCEPCEConfigurationEntry 21 }

ptPCEPCEConfigurationErrors OBJECT-TYPE
    SYNTAX          INTEGER { notLogged(0), logged(1) }
    MAX-ACCESS      read-create
    STATUS          current
    DESCRIPTION     
            "If this flag is set to LOGGED, then error situation that require attention will be noted in the Debug Log file. The Syslog file may also contain error situation information that the operator should be aware off. \nIt is strongly recommended that the Error Debug Flag be set to LOGGED for all systems."
    ::= { ptPCEPCEConfigurationEntry 22 }

ptPCEPCEConfigurationSetupManagement OBJECT-TYPE
    SYNTAX          INTEGER { notLogged(0), logged(1) }
    MAX-ACCESS      read-create
    STATUS          current
    DESCRIPTION     
            "If this flag is set to LOGGED, then information concerning the internal procedures that occur during process startup will be presented in the Debug Log file. \nIt is recommended that the Setup Management Debug Flag be set to LOGGED for all systems. The amount of data produced by this flag is not large, because it is referenced only at startup and in some recovery situations."
    ::= { ptPCEPCEConfigurationEntry 23 }

ptPCEPCEConfigurationExecutionTrace OBJECT-TYPE
    SYNTAX          INTEGER { notLogged(0), logged(1) }
    MAX-ACCESS      read-create
    STATUS          current
    DESCRIPTION     
            "If the Execution Trace debug flag is set to LOGGED, then information concerning the internal processing of the PCE process will be sent to the Debug Log file. This information is intended for Sonus Networks Customer Support staff and may not be legible by most customers. \n The recommended setting of this flag is NOT_LOGGED, so that the system resources are not unduly taken up in the production of log messages."
    ::= { ptPCEPCEConfigurationEntry 24 }

ptPCEPCEConfigurationLayerCommunication OBJECT-TYPE
    SYNTAX          INTEGER { notLogged(0), logged(1) }
    MAX-ACCESS      read-create
    STATUS          current
    DESCRIPTION     
            "If the Layer Communication debug flag is set to LOGGED, then information concerning the internal connections of the PCE process to the MTP3, SCCP and GTT will be sent to the Debug Log file. This information is intended for Sonus Networks Customer Support staff and may not be legible by many customers. \n The recommended setting of this flag is NOT_LOGGED, so that the system resources are not unduly taken up in the production of log messages."
    ::= { ptPCEPCEConfigurationEntry 25 }

ptPCEPCEConfigurationPeerManagement OBJECT-TYPE
    SYNTAX          INTEGER { notLogged(0), logged(1) }
    MAX-ACCESS      read-create
    STATUS          current
    DESCRIPTION     
            "If the Peer Management debug flag is set to LOGGED, then information concerning the internal connections of the PCE process its peers on other CPUs will be sent to the Debug Log file. This information is intended for Sonus Networks Customer Support staff and may not be legible by many customers. \n The recommended setting of this flag is NOT_LOGGED, so that the system resources are not unduly taken up in the production of log messages."
    ::= { ptPCEPCEConfigurationEntry 26 }

ptPCEPCEConfigurationSS7Messages OBJECT-TYPE
    SYNTAX          INTEGER { notLogged(0), logged(1) }
    MAX-ACCESS      read-create
    STATUS          current
    DESCRIPTION     
            "If the SS7 Messages debug flag is set to LOGGED, then the contents of the SS7 messages will be presented in the Debug Log file. This information is very useful when first learning how the PCE works and how to provision it. However it can produce very large volumes of data and tax a busy system. \n The recommended setting of this flag is NOT_LOGGED, so that the system resources are not unduly taken up in the production of log messages."
    ::= { ptPCEPCEConfigurationEntry 27 }

ptPCEPCEConfigurationMaxPublicNodes OBJECT-TYPE
    SYNTAX          Integer32 (-2147483648..2147483647)
    MAX-ACCESS      read-only
    STATUS          current
    DESCRIPTION     
            "Maximum number of Public Nodes."
    ::= { ptPCEPCEConfigurationEntry 28 }

ptPCEPCEConfigurationMaxPrivateNodes OBJECT-TYPE
    SYNTAX          Integer32 (-2147483648..2147483647)
    MAX-ACCESS      read-only
    STATUS          current
    DESCRIPTION     
            "Maximum number of Private Nodes."
    ::= { ptPCEPCEConfigurationEntry 29 }

ptPCEPCEConfigurationMaxPublicGateways OBJECT-TYPE
    SYNTAX          Integer32 (-2147483648..2147483647)
    MAX-ACCESS      read-only
    STATUS          current
    DESCRIPTION     
            "Maximum number of Public Gateways."
    ::= { ptPCEPCEConfigurationEntry 30 }

ptPCEPCEConfigurationMaxGTTTunnelGateways OBJECT-TYPE
    SYNTAX          Integer32 (-2147483648..2147483647)
    MAX-ACCESS      read-only
    STATUS          current
    DESCRIPTION     
            "Maximum number of GTT Tunnel Gateways."
    ::= { ptPCEPCEConfigurationEntry 31 }

ptPCEPCEConfigurationMaxTrunkMappings OBJECT-TYPE
    SYNTAX          Integer32 (-2147483648..2147483647)
    MAX-ACCESS      read-only
    STATUS          current
    DESCRIPTION     
            "Maximum number of Trunk Mappings."
    ::= { ptPCEPCEConfigurationEntry 32 }

ptPCEPCEConfigurationMaxISUPLearningExceptions OBJECT-TYPE
    SYNTAX          Integer32 (-2147483648..2147483647)
    MAX-ACCESS      read-only
    STATUS          current
    DESCRIPTION     
            "Maximum number of ISUP Learning Exceptions."
    ::= { ptPCEPCEConfigurationEntry 33 }

ptPCEPCEConfigurationTransactionIDMapping OBJECT-TYPE
    SYNTAX          INTEGER { disabled(0), enabled(1) }
    MAX-ACCESS      read-create
    STATUS          current
    DESCRIPTION     
            "Enable or disable TCAP Transaction ID Mapping. \nBy default, transaction ID mapping is enabled. \nThe transaction ID mapping can only be disabled when the Public Gateways are a one-to-one mapping with the Private Nodes. The Private Node TCAP Public Gateway Name and the Public Gateway TCAP Private Node Name attributes must be set to enable one-to-one mapping."
    ::= { ptPCEPCEConfigurationEntry 34 }

ptPCEPCEConfigurationIS41BillingIDRouting OBJECT-TYPE
    SYNTAX          INTEGER { disabled(0), enabled(1) }
    MAX-ACCESS      read-create
    STATUS          current
    DESCRIPTION     
            "Enable or disable ANSI TCAP IS-41 Billing ID Routing. \nDisabled by default. \nCan only be enabled if TCAP Variant is set to ANSI or AUTO DETECT. \nIf enabled, the IS41 Conversion attribute will automatically be enabled to properly decode the necessary IS-41 parameters."
    ::= { ptPCEPCEConfigurationEntry 35 }

ptPCEPCEConfigurationMaxIS41BillingIDMappings OBJECT-TYPE
    SYNTAX          Integer32 (-2147483648..2147483647)
    MAX-ACCESS      read-only
    STATUS          current
    DESCRIPTION     
            "Maximum number of IS41 Billing ID Mappings."
    ::= { ptPCEPCEConfigurationEntry 36 }

ptPCEPCEConfigurationIS41Conversion OBJECT-TYPE
    SYNTAX          INTEGER { disabled(0), enabled(1) }
    MAX-ACCESS      read-create
    STATUS          current
    DESCRIPTION     
            "Enable or disable ANSI TCAP IS-41 Conversion. \nIS-41 has two point code based parameters the PC-SSN and the SMS-Address with NP 13. These point codes if present need to be converted similar to the Routing Label and SCCP CLD/CLG point codes to maintain network integrity. Only enable if payload is IS-41. \nThis attribute is forced to enabled if the IS41 Billing ID Routing attribute is enabled."
    ::= { ptPCEPCEConfigurationEntry 37 }

ptPCEPCEConfigurationLDLDebugLevel OBJECT-TYPE
    SYNTAX          Integer32 (-2147483648..2147483647)
    MAX-ACCESS      read-create
    STATUS          current
    DESCRIPTION     
            "LDL debug level for inter-peer logging. 0..255. \n The recommended setting of the attribute is 0, so that the system resources are not unduly taken up in the production of log messages."
    ::= { ptPCEPCEConfigurationEntry 38 }

ptPCEPCEConfigurationLDLSCTPDebugLevel OBJECT-TYPE
    SYNTAX          Integer32 (-2147483648..2147483647)
    MAX-ACCESS      read-create
    STATUS          current
    DESCRIPTION     
            "LDL SCTP debug level for inter-peer logging. 0..255. \n The recommended setting of the attribute is 0, so that the system resources are not unduly taken up in the production of log messages."
    ::= { ptPCEPCEConfigurationEntry 39 }

ptPCEPCEConfigurationMaxReportingPerInterval OBJECT-TYPE
    SYNTAX          Integer32 (0..99)
    MAX-ACCESS      read-create
    STATUS          current
    DESCRIPTION     
            "Maximum number of reported MSUs logged in the given interval. \nThe reported MSUs are MSUs which failed PCE processing and were discarded. A hex dump of the discarded MSU is sent to the debug log. \nMaximum cannot exceed 99. Set to 0 to disable MSU reporting."
    ::= { ptPCEPCEConfigurationEntry 40 }

ptPCEPCEConfigurationReportingInterval OBJECT-TYPE
    SYNTAX          INTEGER { five(300000), ten(600000), fifteen(900000), 
                        twenty(1200000), thirty(1800000) }
    MAX-ACCESS      read-create
    STATUS          current
    DESCRIPTION     
            "MSU Reporting logging interval [5, 10, 15, 20, or 30 minutes]."
    ::= { ptPCEPCEConfigurationEntry 41 }

ptPCEPCEConfigurationForwardedPublicQueries OBJECT-TYPE
    SYNTAX          INTEGER { disabled(0), enabled(1), enabledOpcOnly(2) }
    MAX-ACCESS      read-create
    STATUS          current
    DESCRIPTION     
            "Forwarded Public Queries (DISABLED, ENABLED, ENABLED OPC ONLY). \nThe Forwarded Public Queries feature must be set to ENABLED or ENABLED OPC ONLY if a node in the private network can forward a public query back to the public network without modifying the MSU OPC or the SCCP CLG PA such as an LPN query. This private query needs to be mapped back to the public network as per the originating public query information and new DPC. ENABLED is the value by default, it does trigger forwarding of public queries based on either OPC or SCCP CLG PA; ENABLED OPC ONLY will only trigger forwarding if the MSU OPC belongs to the public network"
    ::= { ptPCEPCEConfigurationEntry 42 }

ptPCEPCEConfigurationFileManagement OBJECT-TYPE
    SYNTAX          INTEGER { notLogged(0), logged(1) }
    MAX-ACCESS      read-create
    STATUS          current
    DESCRIPTION     
            "If the File Management debug flag is set to LOGGED, then information concerning the internal management of the database and configuration files will be presented in the Debug Log file. This information is very useful when first learning how the PCE works and how to provision it. However it can produce very large volumes of data and tax a busy system. \n The recommended setting of this flag is NOT_LOGGED, so that the system resources are not unduly taken up in the production of log messages."
    ::= { ptPCEPCEConfigurationEntry 43 }

ptPCEPCEConfigurationDatabaseManagement OBJECT-TYPE
    SYNTAX          INTEGER { notLogged(0), logged(1) }
    MAX-ACCESS      read-create
    STATUS          current
    DESCRIPTION     
            "If the Database Management debug flag is set to LOGGED, then information concerning the internal management of the database data. This information is very useful when first learning how the PCE works and how to provision it. However it can produce very large volumes of data and tax a busy system. \n The recommended setting of this flag is NOT_LOGGED, so that the system resources are not unduly taken up in the production of log messages."
    ::= { ptPCEPCEConfigurationEntry 44 }

ptPCEPCEConfigurationSCCPTCAPMapping OBJECT-TYPE
    SYNTAX          INTEGER { disabled(0), enabled(1) }
    MAX-ACCESS      read-create
    STATUS          current
    DESCRIPTION     
            "Enable or disable SCCP TCAP Mapping. \nBy default, the SCCP TCAP mapping is enabled. \nThe SCCP TCAP mapping when enabled, will map the SCCP CLG & CLD PCs and the TCAP IS41 PCs if present based on their database mapping if available. When disabled, the above mentioned PCs will be formatted based on the OPC and DPC in the originating query information."
    ::= { ptPCEPCEConfigurationEntry 45 }

ptPCEPCEConfigurationNonMemberRoutesetSupport OBJECT-TYPE
    SYNTAX          INTEGER { disabled(0), enabled(1) }
    MAX-ACCESS      read-create
    STATUS          current
    DESCRIPTION     
            "PCE Non-Member Routeset Support (DISABLED/ENABLED) \nEnable the PCE Non-Member Routeset Support if one or more of the Private Nodes have cluster, network, or default routesets used to reach nodes in the public network which are not defined as Public Nodes in PCE. PCE will register the reserved Application ID (DSC_DEFAULT_RS) with SCCP on the private NAs to route SS7 messages up to PCE when MTP3 has no available routeset and registered PC-SI for that DPC. If PCE is unable to process the Application ID routed MSU, the MSU will follow standard PCE error handling. \nThe Private Nodes with non-member routesets cannot initiate traffic to unknown public nodes, they may only respond to received queries. If private initiated traffic to a specific destination is required, a Public Node must be defined. \nIn this configuration, any missing Public Node mapping during PCE processing will be ignored and the PC in question will remain unchanged. \nBy default, this attribute is set to DISABLED."
    ::= { ptPCEPCEConfigurationEntry 46 }

ptPCEPCEConfigurationActions OBJECT-TYPE
    SYNTAX          INTEGER { activateTraffic(1), deactivateTraffic(2), 
                        resetPeers(3), restoreDebugDefaults(4) }
    MAX-ACCESS      read-create
    STATUS          current
    DESCRIPTION     
            "The OID of all possible actions for this instance"
    ::= { ptPCEPCEConfigurationEntry 252 }

ptPCEPCEConfigurationParentOID OBJECT-TYPE
    SYNTAX          OBJECT IDENTIFIER
    MAX-ACCESS      read-create
    STATUS          current
    DESCRIPTION     
            "The OID of the parent object for this instance"
    ::= { ptPCEPCEConfigurationEntry 253 }

ptPCEPCEConfigurationRowStatus OBJECT-TYPE
    SYNTAX          RowStatus
    MAX-ACCESS      read-create
    STATUS          current
    DESCRIPTION     
            "The row status for the PCEPCEConfiguration table"
    ::= { ptPCEPCEConfigurationEntry 254 }

ptPCEPCEConfigurationIndex OBJECT-TYPE
    SYNTAX          Integer32 (-2147483648..2147483647)
    MAX-ACCESS      not-accessible
    STATUS          current
    DESCRIPTION     
            "The row number for the PCEPCEConfiguration table"
    ::= { ptPCEPCEConfigurationEntry 255 }

ptPCEPCEStatistics OBJECT IDENTIFIER
    ::= { ptConnGroup 453 }

ptPCEPCEStatisticsTable OBJECT-TYPE
    SYNTAX          SEQUENCE OF PtPCEPCEStatisticsEntry
    MAX-ACCESS      not-accessible
    STATUS          current
    DESCRIPTION     
            "No description supplied in the proxy config file."
    ::= { ptPCEPCEStatistics 1 }

ptPCEPCEStatisticsEntry OBJECT-TYPE
    SYNTAX          PtPCEPCEStatisticsEntry
    MAX-ACCESS      not-accessible
    STATUS          current
    DESCRIPTION     
            "A sequence of PCEPCEStatistics attributes."
    INDEX           { ptConnGroupIndex, ptPCEPCEStatisticsIndex }
    ::= { ptPCEPCEStatisticsTable 1 }

PtPCEPCEStatisticsEntry ::=
    SEQUENCE {
        ptPCEPCEStatisticsRefreshDate   DisplayString,
        ptPCEPCEStatisticsResetDate     DisplayString,
        ptPCEPCEStatisticsActions       INTEGER,
        ptPCEPCEStatisticsParentOID     OBJECT IDENTIFIER,
        ptPCEPCEStatisticsRowStatus     RowStatus,
        ptPCEPCEStatisticsIndex         Integer32
    }

ptPCEPCEStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptPCEPCEStatisticsEntry 1 }

ptPCEPCEStatisticsResetDate OBJECT-TYPE
    SYNTAX          DisplayString (SIZE(0..255))
    MAX-ACCESS      read-only
    STATUS          current
    DESCRIPTION     
            "Date/Time from which the above counts were last started or reset. \nUse the Reset All Stats action to reset the counts to zero."
    ::= { ptPCEPCEStatisticsEntry 2 }

ptPCEPCEStatisticsActions OBJECT-TYPE
    SYNTAX          INTEGER { refreshAllStats(1), resetAllStats(2) }
    MAX-ACCESS      read-create
    STATUS          current
    DESCRIPTION     
            "The OID of all possible actions for this instance"
    ::= { ptPCEPCEStatisticsEntry 252 }

ptPCEPCEStatisticsParentOID OBJECT-TYPE
    SYNTAX          OBJECT IDENTIFIER
    MAX-ACCESS      read-create
    STATUS          current
    DESCRIPTION     
            "The OID of the parent object for this instance"
    ::= { ptPCEPCEStatisticsEntry 253 }

ptPCEPCEStatisticsRowStatus OBJECT-TYPE
    SYNTAX          RowStatus
    MAX-ACCESS      read-create
    STATUS          current
    DESCRIPTION     
            "The row status for the PCEPCEStatistics table"
    ::= { ptPCEPCEStatisticsEntry 254 }

ptPCEPCEStatisticsIndex OBJECT-TYPE
    SYNTAX          Integer32 (-2147483648..2147483647)
    MAX-ACCESS      not-accessible
    STATUS          current
    DESCRIPTION     
            "The row number for the PCEPCEStatistics table"
    ::= { ptPCEPCEStatisticsEntry 255 }

ptPCEPCEISUPStatistics OBJECT IDENTIFIER
    ::= { ptPCEPCEStatistics 454 }

ptPCEPCEISUPStatisticsTable OBJECT-TYPE
    SYNTAX          SEQUENCE OF PtPCEPCEISUPStatisticsEntry
    MAX-ACCESS      not-accessible
    STATUS          current
    DESCRIPTION     
            "No description supplied in the proxy config file."
    ::= { ptPCEPCEISUPStatistics 1 }

ptPCEPCEISUPStatisticsEntry OBJECT-TYPE
    SYNTAX          PtPCEPCEISUPStatisticsEntry
    MAX-ACCESS      not-accessible
    STATUS          current
    DESCRIPTION     
            "A sequence of PCEPCEISUPStatistics attributes."
    INDEX           { ptConnGroupIndex, 
                      ptPCEPCEISUPStatisticsPCEStatisticsIndex, 
                      ptPCEPCEISUPStatisticsIndex }
    ::= { ptPCEPCEISUPStatisticsTable 1 }

PtPCEPCEISUPStatisticsEntry ::=
    SEQUENCE {
        ptPCEPCEISUPStatisticsPublicReceived    Integer32,
        ptPCEPCEISUPStatisticsPublicDiscarded     Integer32,
        ptPCEPCEISUPStatisticsPublicSent Integer32,
        ptPCEPCEISUPStatisticsPublicGenerated     Integer32,
        ptPCEPCEISUPStatisticsPublicPeerRecv    Integer32,
        ptPCEPCEISUPStatisticsPublicPeerSent    Integer32,
        ptPCEPCEISUPStatisticsPrivateReceived     Integer32,
        ptPCEPCEISUPStatisticsPrivateDiscarded      Integer32,
        ptPCEPCEISUPStatisticsPrivateSent Integer32,
        ptPCEPCEISUPStatisticsRefreshDate DisplayString,
        ptPCEPCEISUPStatisticsResetDate DisplayString,
        ptPCEPCEISUPStatisticsPCEStatisticsIndex        Integer32,
        ptPCEPCEISUPStatisticsActions   INTEGER,
        ptPCEPCEISUPStatisticsParentOID OBJECT IDENTIFIER,
        ptPCEPCEISUPStatisticsRowStatus RowStatus,
        ptPCEPCEISUPStatisticsIndex     Integer32
    }

ptPCEPCEISUPStatisticsPublicReceived OBJECT-TYPE
    SYNTAX          Integer32 (-2147483648..2147483647)
    MAX-ACCESS      read-only
    STATUS          current
    DESCRIPTION     
            "Number of received Public ISUP messages."
    ::= { ptPCEPCEISUPStatisticsEntry 1 }

ptPCEPCEISUPStatisticsPublicDiscarded OBJECT-TYPE
    SYNTAX          Integer32 (-2147483648..2147483647)
    MAX-ACCESS      read-only
    STATUS          current
    DESCRIPTION     
            "Number of discarded Public ISUP messages."
    ::= { ptPCEPCEISUPStatisticsEntry 2 }

ptPCEPCEISUPStatisticsPublicSent OBJECT-TYPE
    SYNTAX          Integer32 (-2147483648..2147483647)
    MAX-ACCESS      read-only
    STATUS          current
    DESCRIPTION     
            "Number of sent Public ISUP messages."
    ::= { ptPCEPCEISUPStatisticsEntry 3 }

ptPCEPCEISUPStatisticsPublicGenerated OBJECT-TYPE
    SYNTAX          Integer32 (-2147483648..2147483647)
    MAX-ACCESS      read-only
    STATUS          current
    DESCRIPTION     
            "Number of generated Public ISUP messages."
    ::= { ptPCEPCEISUPStatisticsEntry 4 }

ptPCEPCEISUPStatisticsPublicPeerRecv OBJECT-TYPE
    SYNTAX          Integer32 (-2147483648..2147483647)
    MAX-ACCESS      read-only
    STATUS          current
    DESCRIPTION     
            "Number of Public ISUP messages received from peer."
    ::= { ptPCEPCEISUPStatisticsEntry 5 }

ptPCEPCEISUPStatisticsPublicPeerSent OBJECT-TYPE
    SYNTAX          Integer32 (-2147483648..2147483647)
    MAX-ACCESS      read-only
    STATUS          current
    DESCRIPTION     
            "Number of Public ISUP messages sent from peer."
    ::= { ptPCEPCEISUPStatisticsEntry 6 }

ptPCEPCEISUPStatisticsPrivateReceived OBJECT-TYPE
    SYNTAX          Integer32 (-2147483648..2147483647)
    MAX-ACCESS      read-only
    STATUS          current
    DESCRIPTION     
            "Number of received Private ISUP messages."
    ::= { ptPCEPCEISUPStatisticsEntry 7 }

ptPCEPCEISUPStatisticsPrivateDiscarded OBJECT-TYPE
    SYNTAX          Integer32 (-2147483648..2147483647)
    MAX-ACCESS      read-only
    STATUS          current
    DESCRIPTION     
            "Number of discarded Private ISUP messages."
    ::= { ptPCEPCEISUPStatisticsEntry 8 }

ptPCEPCEISUPStatisticsPrivateSent OBJECT-TYPE
    SYNTAX          Integer32 (-2147483648..2147483647)
    MAX-ACCESS      read-only
    STATUS          current
    DESCRIPTION     
            "Number of sent Private ISUP messages."
    ::= { ptPCEPCEISUPStatisticsEntry 9 }

ptPCEPCEISUPStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptPCEPCEISUPStatisticsEntry 10 }

ptPCEPCEISUPStatisticsResetDate OBJECT-TYPE
    SYNTAX          DisplayString (SIZE(0..255))
    MAX-ACCESS      read-only
    STATUS          current
    DESCRIPTION     
            "Date/Time from which the above counts were last started or reset. \nUse the Reset All Stats action to reset the counts to zero."
    ::= { ptPCEPCEISUPStatisticsEntry 11 }

ptPCEPCEISUPStatisticsPCEStatisticsIndex OBJECT-TYPE
    SYNTAX          Integer32 (-2147483648..2147483647)
    MAX-ACCESS      not-accessible
    STATUS          current
    DESCRIPTION     
            "This is the index of the parent type for this object.
             This parent type is PCEStatistics."
    ::= { ptPCEPCEISUPStatisticsEntry 242 }

ptPCEPCEISUPStatisticsActions OBJECT-TYPE
    SYNTAX          INTEGER { refreshAllStats(1), resetAllStats(2) }
    MAX-ACCESS      read-create
    STATUS          current
    DESCRIPTION     
            "The OID of all possible actions for this instance"
    ::= { ptPCEPCEISUPStatisticsEntry 252 }

ptPCEPCEISUPStatisticsParentOID OBJECT-TYPE
    SYNTAX          OBJECT IDENTIFIER
    MAX-ACCESS      read-create
    STATUS          current
    DESCRIPTION     
            "The OID of the parent object for this instance"
    ::= { ptPCEPCEISUPStatisticsEntry 253 }

ptPCEPCEISUPStatisticsRowStatus OBJECT-TYPE
    SYNTAX          RowStatus
    MAX-ACCESS      read-create
    STATUS          current
    DESCRIPTION     
            "The row status for the PCEPCEISUPStatistics table"
    ::= { ptPCEPCEISUPStatisticsEntry 254 }

ptPCEPCEISUPStatisticsIndex OBJECT-TYPE
    SYNTAX          Integer32 (-2147483648..2147483647)
    MAX-ACCESS      not-accessible
    STATUS          current
    DESCRIPTION     
            "The row number for the PCEPCEISUPStatistics table"
    ::= { ptPCEPCEISUPStatisticsEntry 255 }

ptPCEPeerISUPStatistics OBJECT IDENTIFIER
    ::= { ptPCEPCEISUPStatistics 455 }

ptPCEPeerISUPStatisticsTable OBJECT-TYPE
    SYNTAX          SEQUENCE OF PtPCEPeerISUPStatisticsEntry
    MAX-ACCESS      not-accessible
    STATUS          current
    DESCRIPTION     
            "No description supplied in the proxy config file."
    ::= { ptPCEPeerISUPStatistics 1 }

ptPCEPeerISUPStatisticsEntry OBJECT-TYPE
    SYNTAX          PtPCEPeerISUPStatisticsEntry
    MAX-ACCESS      not-accessible
    STATUS          current
    DESCRIPTION     
            "A sequence of PCEPeerISUPStatistics attributes."
    INDEX           { ptConnGroupIndex, 
                      ptPCEPeerISUPStatisticsPCEStatisticsIndex, 
                      ptPCEPeerISUPStatisticsPCEISUPStatisticsIndex, 
                      ptPCEPeerISUPStatisticsIndex }
    ::= { ptPCEPeerISUPStatisticsTable 1 }

PtPCEPeerISUPStatisticsEntry ::=
    SEQUENCE {
        ptPCEPeerISUPStatisticsPeerID   Integer32,
        ptPCEPeerISUPStatisticsPublicReceived     Integer32,
        ptPCEPeerISUPStatisticsPublicDiscarded      Integer32,
        ptPCEPeerISUPStatisticsPublicSent Integer32,
        ptPCEPeerISUPStatisticsPublicGenerated      Integer32,
        ptPCEPeerISUPStatisticsPublicPeerRecv     Integer32,
        ptPCEPeerISUPStatisticsPublicPeerSent     Integer32,
        ptPCEPeerISUPStatisticsPrivateReceived      Integer32,
        ptPCEPeerISUPStatisticsPrivateDiscarded       Integer32,
        ptPCEPeerISUPStatisticsPrivateSent  Integer32,
        ptPCEPeerISUPStatisticsRefreshDate  DisplayString,
        ptPCEPeerISUPStatisticsResetDate DisplayString,
        ptPCEPeerISUPStatisticsPCEStatisticsIndex         Integer32,
        ptPCEPeerISUPStatisticsPCEISUPStatisticsIndex             Integer32,
        ptPCEPeerISUPStatisticsActions  INTEGER,
        ptPCEPeerISUPStatisticsParentOID OBJECT IDENTIFIER,
        ptPCEPeerISUPStatisticsRowStatus RowStatus,
        ptPCEPeerISUPStatisticsIndex    Integer32
    }

ptPCEPeerISUPStatisticsPeerID OBJECT-TYPE
    SYNTAX          Integer32 (-2147483648..2147483647)
    MAX-ACCESS      read-only
    STATUS          current
    DESCRIPTION     
            "PCE LDL Peer Identifier."
    ::= { ptPCEPeerISUPStatisticsEntry 1 }

ptPCEPeerISUPStatisticsPublicReceived OBJECT-TYPE
    SYNTAX          Integer32 (-2147483648..2147483647)
    MAX-ACCESS      read-only
    STATUS          current
    DESCRIPTION     
            "Number of received Public ISUP messages on this peer."
    ::= { ptPCEPeerISUPStatisticsEntry 2 }

ptPCEPeerISUPStatisticsPublicDiscarded OBJECT-TYPE
    SYNTAX          Integer32 (-2147483648..2147483647)
    MAX-ACCESS      read-only
    STATUS          current
    DESCRIPTION     
            "Number of discarded Public ISUP messages on this peer."
    ::= { ptPCEPeerISUPStatisticsEntry 3 }

ptPCEPeerISUPStatisticsPublicSent OBJECT-TYPE
    SYNTAX          Integer32 (-2147483648..2147483647)
    MAX-ACCESS      read-only
    STATUS          current
    DESCRIPTION     
            "Number of sent Public ISUP messages on this peer."
    ::= { ptPCEPeerISUPStatisticsEntry 4 }

ptPCEPeerISUPStatisticsPublicGenerated OBJECT-TYPE
    SYNTAX          Integer32 (-2147483648..2147483647)
    MAX-ACCESS      read-only
    STATUS          current
    DESCRIPTION     
            "Number of generated Public ISUP messages on this peer."
    ::= { ptPCEPeerISUPStatisticsEntry 5 }

ptPCEPeerISUPStatisticsPublicPeerRecv OBJECT-TYPE
    SYNTAX          Integer32 (-2147483648..2147483647)
    MAX-ACCESS      read-only
    STATUS          current
    DESCRIPTION     
            "Number of Public ISUP messages received from peer on this peer."
    ::= { ptPCEPeerISUPStatisticsEntry 6 }

ptPCEPeerISUPStatisticsPublicPeerSent OBJECT-TYPE
    SYNTAX          Integer32 (-2147483648..2147483647)
    MAX-ACCESS      read-only
    STATUS          current
    DESCRIPTION     
            "Number of Public ISUP messages sent from peer on this peer."
    ::= { ptPCEPeerISUPStatisticsEntry 7 }

ptPCEPeerISUPStatisticsPrivateReceived OBJECT-TYPE
    SYNTAX          Integer32 (-2147483648..2147483647)
    MAX-ACCESS      read-only
    STATUS          current
    DESCRIPTION     
            "Number of received Private ISUP messages on this peer."
    ::= { ptPCEPeerISUPStatisticsEntry 8 }

ptPCEPeerISUPStatisticsPrivateDiscarded OBJECT-TYPE
    SYNTAX          Integer32 (-2147483648..2147483647)
    MAX-ACCESS      read-only
    STATUS          current
    DESCRIPTION     
            "Number of discarded Private ISUP messages on this peer."
    ::= { ptPCEPeerISUPStatisticsEntry 9 }

ptPCEPeerISUPStatisticsPrivateSent OBJECT-TYPE
    SYNTAX          Integer32 (-2147483648..2147483647)
    MAX-ACCESS      read-only
    STATUS          current
    DESCRIPTION     
            "Number of sent Private ISUP messages on this peer."
    ::= { ptPCEPeerISUPStatisticsEntry 10 }

ptPCEPeerISUPStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptPCEPeerISUPStatisticsEntry 11 }

ptPCEPeerISUPStatisticsResetDate OBJECT-TYPE
    SYNTAX          DisplayString (SIZE(0..255))
    MAX-ACCESS      read-only
    STATUS          current
    DESCRIPTION     
            "Date/Time from which the above counts were last started or reset. \nUse the Reset All Stats action to reset the counts to zero."
    ::= { ptPCEPeerISUPStatisticsEntry 12 }

ptPCEPeerISUPStatisticsPCEStatisticsIndex OBJECT-TYPE
    SYNTAX          Integer32 (-2147483648..2147483647)
    MAX-ACCESS      not-accessible
    STATUS          current
    DESCRIPTION     
            "This is the index of the parent type for this object.
             This parent type is PCEStatistics."
    ::= { ptPCEPeerISUPStatisticsEntry 242 }

ptPCEPeerISUPStatisticsPCEISUPStatisticsIndex OBJECT-TYPE
    SYNTAX          Integer32 (-2147483648..2147483647)
    MAX-ACCESS      not-accessible
    STATUS          current
    DESCRIPTION     
            "This is the index of the parent type for this object.
             This parent type is PCEISUPStatistics."
    ::= { ptPCEPeerISUPStatisticsEntry 243 }

ptPCEPeerISUPStatisticsActions OBJECT-TYPE
    SYNTAX          INTEGER { refreshAllStats(1), resetAllStats(2) }
    MAX-ACCESS      read-create
    STATUS          current
    DESCRIPTION     
            "The OID of all possible actions for this instance"
    ::= { ptPCEPeerISUPStatisticsEntry 252 }

ptPCEPeerISUPStatisticsParentOID OBJECT-TYPE
    SYNTAX          OBJECT IDENTIFIER
    MAX-ACCESS      read-create
    STATUS          current
    DESCRIPTION     
            "The OID of the parent object for this instance"
    ::= { ptPCEPeerISUPStatisticsEntry 253 }

ptPCEPeerISUPStatisticsRowStatus OBJECT-TYPE
    SYNTAX          RowStatus
    MAX-ACCESS      read-create
    STATUS          current
    DESCRIPTION     
            "The row status for the PCEPeerISUPStatistics table"
    ::= { ptPCEPeerISUPStatisticsEntry 254 }

ptPCEPeerISUPStatisticsIndex OBJECT-TYPE
    SYNTAX          Integer32 (-2147483648..2147483647)
    MAX-ACCESS      not-accessible
    STATUS          current
    DESCRIPTION     
            "The row number for the PCEPeerISUPStatistics table"
    ::= { ptPCEPeerISUPStatisticsEntry 255 }

ptPCEPCETCAPStatistics OBJECT IDENTIFIER
    ::= { ptPCEPCEStatistics 456 }

ptPCEPCETCAPStatisticsTable OBJECT-TYPE
    SYNTAX          SEQUENCE OF PtPCEPCETCAPStatisticsEntry
    MAX-ACCESS      not-accessible
    STATUS          current
    DESCRIPTION     
            "No description supplied in the proxy config file."
    ::= { ptPCEPCETCAPStatistics 1 }

ptPCEPCETCAPStatisticsEntry OBJECT-TYPE
    SYNTAX          PtPCEPCETCAPStatisticsEntry
    MAX-ACCESS      not-accessible
    STATUS          current
    DESCRIPTION     
            "A sequence of PCEPCETCAPStatistics attributes."
    INDEX           { ptConnGroupIndex, 
                      ptPCEPCETCAPStatisticsPCEStatisticsIndex, 
                      ptPCEPCETCAPStatisticsIndex }
    ::= { ptPCEPCETCAPStatisticsTable 1 }

PtPCEPCETCAPStatisticsEntry ::=
    SEQUENCE {
        ptPCEPCETCAPStatisticsPublicReceived    Integer32,
        ptPCEPCETCAPStatisticsPublicTunnelRecv      Integer32,
        ptPCEPCETCAPStatisticsPublicDiscarded     Integer32,
        ptPCEPCETCAPStatisticsPublicSent Integer32,
        ptPCEPCETCAPStatisticsPublicGenerated     Integer32,
        ptPCEPCETCAPStatisticsPublicPeerRecv    Integer32,
        ptPCEPCETCAPStatisticsPublicPeerSent    Integer32,
        ptPCEPCETCAPStatisticsPrivateReceived     Integer32,
        ptPCEPCETCAPStatisticsPrivateTunnelRecv       Integer32,
        ptPCEPCETCAPStatisticsPrivateDiscarded      Integer32,
        ptPCEPCETCAPStatisticsPrivateSent Integer32,
        ptPCEPCETCAPStatisticsPrivateGenerated      Integer32,
        ptPCEPCETCAPStatisticsRefreshDate DisplayString,
        ptPCEPCETCAPStatisticsResetDate DisplayString,
        ptPCEPCETCAPStatisticsPrivatePeerRecv     Integer32,
        ptPCEPCETCAPStatisticsPrivatePeerSent     Integer32,
        ptPCEPCETCAPStatisticsPCEStatisticsIndex        Integer32,
        ptPCEPCETCAPStatisticsActions   INTEGER,
        ptPCEPCETCAPStatisticsParentOID OBJECT IDENTIFIER,
        ptPCEPCETCAPStatisticsRowStatus RowStatus,
        ptPCEPCETCAPStatisticsIndex     Integer32
    }

ptPCEPCETCAPStatisticsPublicReceived OBJECT-TYPE
    SYNTAX          Integer32 (-2147483648..2147483647)
    MAX-ACCESS      read-only
    STATUS          current
    DESCRIPTION     
            "Number of received Public TCAP messages."
    ::= { ptPCEPCETCAPStatisticsEntry 1 }

ptPCEPCETCAPStatisticsPublicTunnelRecv OBJECT-TYPE
    SYNTAX          Integer32 (-2147483648..2147483647)
    MAX-ACCESS      read-only
    STATUS          current
    DESCRIPTION     
            "Number of received Tunnel Public TCAP messages."
    ::= { ptPCEPCETCAPStatisticsEntry 2 }

ptPCEPCETCAPStatisticsPublicDiscarded OBJECT-TYPE
    SYNTAX          Integer32 (-2147483648..2147483647)
    MAX-ACCESS      read-only
    STATUS          current
    DESCRIPTION     
            "Number of discarded Public TCAP messages."
    ::= { ptPCEPCETCAPStatisticsEntry 3 }

ptPCEPCETCAPStatisticsPublicSent OBJECT-TYPE
    SYNTAX          Integer32 (-2147483648..2147483647)
    MAX-ACCESS      read-only
    STATUS          current
    DESCRIPTION     
            "Number of sent Public TCAP messages."
    ::= { ptPCEPCETCAPStatisticsEntry 4 }

ptPCEPCETCAPStatisticsPublicGenerated OBJECT-TYPE
    SYNTAX          Integer32 (-2147483648..2147483647)
    MAX-ACCESS      read-only
    STATUS          current
    DESCRIPTION     
            "Number of generated Public TCAP messages."
    ::= { ptPCEPCETCAPStatisticsEntry 5 }

ptPCEPCETCAPStatisticsPublicPeerRecv OBJECT-TYPE
    SYNTAX          Integer32 (-2147483648..2147483647)
    MAX-ACCESS      read-only
    STATUS          current
    DESCRIPTION     
            "Number of Public TCAP messages received from peer."
    ::= { ptPCEPCETCAPStatisticsEntry 6 }

ptPCEPCETCAPStatisticsPublicPeerSent OBJECT-TYPE
    SYNTAX          Integer32 (-2147483648..2147483647)
    MAX-ACCESS      read-only
    STATUS          current
    DESCRIPTION     
            "Number of Public TCAP messages sent from peer."
    ::= { ptPCEPCETCAPStatisticsEntry 7 }

ptPCEPCETCAPStatisticsPrivateReceived OBJECT-TYPE
    SYNTAX          Integer32 (-2147483648..2147483647)
    MAX-ACCESS      read-only
    STATUS          current
    DESCRIPTION     
            "Number of received Private TCAP messages."
    ::= { ptPCEPCETCAPStatisticsEntry 8 }

ptPCEPCETCAPStatisticsPrivateTunnelRecv OBJECT-TYPE
    SYNTAX          Integer32 (-2147483648..2147483647)
    MAX-ACCESS      read-only
    STATUS          current
    DESCRIPTION     
            "Number of received Tunnel Private TCAP messages."
    ::= { ptPCEPCETCAPStatisticsEntry 9 }

ptPCEPCETCAPStatisticsPrivateDiscarded OBJECT-TYPE
    SYNTAX          Integer32 (-2147483648..2147483647)
    MAX-ACCESS      read-only
    STATUS          current
    DESCRIPTION     
            "Number of discarded Private TCAP messages."
    ::= { ptPCEPCETCAPStatisticsEntry 10 }

ptPCEPCETCAPStatisticsPrivateSent OBJECT-TYPE
    SYNTAX          Integer32 (-2147483648..2147483647)
    MAX-ACCESS      read-only
    STATUS          current
    DESCRIPTION     
            "Number of sent Private TCAP messages."
    ::= { ptPCEPCETCAPStatisticsEntry 11 }

ptPCEPCETCAPStatisticsPrivateGenerated OBJECT-TYPE
    SYNTAX          Integer32 (-2147483648..2147483647)
    MAX-ACCESS      read-only
    STATUS          current
    DESCRIPTION     
            "Number of generated Private TCAP messages."
    ::= { ptPCEPCETCAPStatisticsEntry 12 }

ptPCEPCETCAPStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptPCEPCETCAPStatisticsEntry 13 }

ptPCEPCETCAPStatisticsResetDate OBJECT-TYPE
    SYNTAX          DisplayString (SIZE(0..255))
    MAX-ACCESS      read-only
    STATUS          current
    DESCRIPTION     
            "Date/Time from which the above counts were last started or reset. \nUse the Reset All Stats action to reset the counts to zero."
    ::= { ptPCEPCETCAPStatisticsEntry 14 }

ptPCEPCETCAPStatisticsPrivatePeerRecv OBJECT-TYPE
    SYNTAX          Integer32 (-2147483648..2147483647)
    MAX-ACCESS      read-only
    STATUS          current
    DESCRIPTION     
            "Number of Private TCAP messages received from peer."
    ::= { ptPCEPCETCAPStatisticsEntry 15 }

ptPCEPCETCAPStatisticsPrivatePeerSent OBJECT-TYPE
    SYNTAX          Integer32 (-2147483648..2147483647)
    MAX-ACCESS      read-only
    STATUS          current
    DESCRIPTION     
            "Number of Private TCAP messages sent from peer."
    ::= { ptPCEPCETCAPStatisticsEntry 16 }

ptPCEPCETCAPStatisticsPCEStatisticsIndex OBJECT-TYPE
    SYNTAX          Integer32 (-2147483648..2147483647)
    MAX-ACCESS      not-accessible
    STATUS          current
    DESCRIPTION     
            "This is the index of the parent type for this object.
             This parent type is PCEStatistics."
    ::= { ptPCEPCETCAPStatisticsEntry 242 }

ptPCEPCETCAPStatisticsActions OBJECT-TYPE
    SYNTAX          INTEGER { refreshAllStats(1), resetAllStats(2) }
    MAX-ACCESS      read-create
    STATUS          current
    DESCRIPTION     
            "The OID of all possible actions for this instance"
    ::= { ptPCEPCETCAPStatisticsEntry 252 }

ptPCEPCETCAPStatisticsParentOID OBJECT-TYPE
    SYNTAX          OBJECT IDENTIFIER
    MAX-ACCESS      read-create
    STATUS          current
    DESCRIPTION     
            "The OID of the parent object for this instance"
    ::= { ptPCEPCETCAPStatisticsEntry 253 }

ptPCEPCETCAPStatisticsRowStatus OBJECT-TYPE
    SYNTAX          RowStatus
    MAX-ACCESS      read-create
    STATUS          current
    DESCRIPTION     
            "The row status for the PCEPCETCAPStatistics table"
    ::= { ptPCEPCETCAPStatisticsEntry 254 }

ptPCEPCETCAPStatisticsIndex OBJECT-TYPE
    SYNTAX          Integer32 (-2147483648..2147483647)
    MAX-ACCESS      not-accessible
    STATUS          current
    DESCRIPTION     
            "The row number for the PCEPCETCAPStatistics table"
    ::= { ptPCEPCETCAPStatisticsEntry 255 }

ptPCEPeerTCAPStatistics OBJECT IDENTIFIER
    ::= { ptPCEPCETCAPStatistics 457 }

ptPCEPeerTCAPStatisticsTable OBJECT-TYPE
    SYNTAX          SEQUENCE OF PtPCEPeerTCAPStatisticsEntry
    MAX-ACCESS      not-accessible
    STATUS          current
    DESCRIPTION     
            "No description supplied in the proxy config file."
    ::= { ptPCEPeerTCAPStatistics 1 }

ptPCEPeerTCAPStatisticsEntry OBJECT-TYPE
    SYNTAX          PtPCEPeerTCAPStatisticsEntry
    MAX-ACCESS      not-accessible
    STATUS          current
    DESCRIPTION     
            "A sequence of PCEPeerTCAPStatistics attributes."
    INDEX           { ptConnGroupIndex, 
                      ptPCEPeerTCAPStatisticsPCEStatisticsIndex, 
                      ptPCEPeerTCAPStatisticsPCETCAPStatisticsIndex, 
                      ptPCEPeerTCAPStatisticsIndex }
    ::= { ptPCEPeerTCAPStatisticsTable 1 }

PtPCEPeerTCAPStatisticsEntry ::=
    SEQUENCE {
        ptPCEPeerTCAPStatisticsPeerID   Integer32,
        ptPCEPeerTCAPStatisticsPublicReceived     Integer32,
        ptPCEPeerTCAPStatisticsPublicTunnelRecv       Integer32,
        ptPCEPeerTCAPStatisticsPublicDiscarded      Integer32,
        ptPCEPeerTCAPStatisticsPublicSent Integer32,
        ptPCEPeerTCAPStatisticsPublicGenerated      Integer32,
        ptPCEPeerTCAPStatisticsPublicPeerRecv     Integer32,
        ptPCEPeerTCAPStatisticsPublicPeerSent     Integer32,
        ptPCEPeerTCAPStatisticsPrivateReceived      Integer32,
        ptPCEPeerTCAPStatisticsPrivateTunnelRecv        Integer32,
        ptPCEPeerTCAPStatisticsPrivateDiscarded       Integer32,
        ptPCEPeerTCAPStatisticsPrivateSent  Integer32,
        ptPCEPeerTCAPStatisticsPrivateGenerated       Integer32,
        ptPCEPeerTCAPStatisticsRefreshDate  DisplayString,
        ptPCEPeerTCAPStatisticsResetDate DisplayString,
        ptPCEPeerTCAPStatisticsPrivatePeerRecv      Integer32,
        ptPCEPeerTCAPStatisticsPrivatePeerSent      Integer32,
        ptPCEPeerTCAPStatisticsPCEStatisticsIndex         Integer32,
        ptPCEPeerTCAPStatisticsPCETCAPStatisticsIndex             Integer32,
        ptPCEPeerTCAPStatisticsActions  INTEGER,
        ptPCEPeerTCAPStatisticsParentOID OBJECT IDENTIFIER,
        ptPCEPeerTCAPStatisticsRowStatus RowStatus,
        ptPCEPeerTCAPStatisticsIndex    Integer32
    }

ptPCEPeerTCAPStatisticsPeerID OBJECT-TYPE
    SYNTAX          Integer32 (-2147483648..2147483647)
    MAX-ACCESS      read-only
    STATUS          current
    DESCRIPTION     
            "PCE LDL Peer Identifier."
    ::= { ptPCEPeerTCAPStatisticsEntry 1 }

ptPCEPeerTCAPStatisticsPublicReceived OBJECT-TYPE
    SYNTAX          Integer32 (-2147483648..2147483647)
    MAX-ACCESS      read-only
    STATUS          current
    DESCRIPTION     
            "Number of received Public TCAP messages on this peer."
    ::= { ptPCEPeerTCAPStatisticsEntry 2 }

ptPCEPeerTCAPStatisticsPublicTunnelRecv OBJECT-TYPE
    SYNTAX          Integer32 (-2147483648..2147483647)
    MAX-ACCESS      read-only
    STATUS          current
    DESCRIPTION     
            "Number of received Tunnel Public TCAP messages on this peer."
    ::= { ptPCEPeerTCAPStatisticsEntry 3 }

ptPCEPeerTCAPStatisticsPublicDiscarded OBJECT-TYPE
    SYNTAX          Integer32 (-2147483648..2147483647)
    MAX-ACCESS      read-only
    STATUS          current
    DESCRIPTION     
            "Number of discarded Public TCAP messages on this peer."
    ::= { ptPCEPeerTCAPStatisticsEntry 4 }

ptPCEPeerTCAPStatisticsPublicSent OBJECT-TYPE
    SYNTAX          Integer32 (-2147483648..2147483647)
    MAX-ACCESS      read-only
    STATUS          current
    DESCRIPTION     
            "Number of sent Public TCAP messages on this peer."
    ::= { ptPCEPeerTCAPStatisticsEntry 5 }

ptPCEPeerTCAPStatisticsPublicGenerated OBJECT-TYPE
    SYNTAX          Integer32 (-2147483648..2147483647)
    MAX-ACCESS      read-only
    STATUS          current
    DESCRIPTION     
            "Number of generated Public TCAP messages on this peer."
    ::= { ptPCEPeerTCAPStatisticsEntry 6 }

ptPCEPeerTCAPStatisticsPublicPeerRecv OBJECT-TYPE
    SYNTAX          Integer32 (-2147483648..2147483647)
    MAX-ACCESS      read-only
    STATUS          current
    DESCRIPTION     
            "Number of Public TCAP messages received from peer on this peer."
    ::= { ptPCEPeerTCAPStatisticsEntry 7 }

ptPCEPeerTCAPStatisticsPublicPeerSent OBJECT-TYPE
    SYNTAX          Integer32 (-2147483648..2147483647)
    MAX-ACCESS      read-only
    STATUS          current
    DESCRIPTION     
            "Number of Public TCAP messages sent from peer on this peer."
    ::= { ptPCEPeerTCAPStatisticsEntry 8 }

ptPCEPeerTCAPStatisticsPrivateReceived OBJECT-TYPE
    SYNTAX          Integer32 (-2147483648..2147483647)
    MAX-ACCESS      read-only
    STATUS          current
    DESCRIPTION     
            "Number of received Private TCAP messages on this peer."
    ::= { ptPCEPeerTCAPStatisticsEntry 9 }

ptPCEPeerTCAPStatisticsPrivateTunnelRecv OBJECT-TYPE
    SYNTAX          Integer32 (-2147483648..2147483647)
    MAX-ACCESS      read-only
    STATUS          current
    DESCRIPTION     
            "Number of received Tunnel Private TCAP messages on this peer."
    ::= { ptPCEPeerTCAPStatisticsEntry 10 }

ptPCEPeerTCAPStatisticsPrivateDiscarded OBJECT-TYPE
    SYNTAX          Integer32 (-2147483648..2147483647)
    MAX-ACCESS      read-only
    STATUS          current
    DESCRIPTION     
            "Number of discarded Private TCAP messages on this peer."
    ::= { ptPCEPeerTCAPStatisticsEntry 11 }

ptPCEPeerTCAPStatisticsPrivateSent OBJECT-TYPE
    SYNTAX          Integer32 (-2147483648..2147483647)
    MAX-ACCESS      read-only
    STATUS          current
    DESCRIPTION     
            "Number of sent Private TCAP messages on this peer."
    ::= { ptPCEPeerTCAPStatisticsEntry 12 }

ptPCEPeerTCAPStatisticsPrivateGenerated OBJECT-TYPE
    SYNTAX          Integer32 (-2147483648..2147483647)
    MAX-ACCESS      read-only
    STATUS          current
    DESCRIPTION     
            "Number of generated Private TCAP messages on this peer."
    ::= { ptPCEPeerTCAPStatisticsEntry 13 }

ptPCEPeerTCAPStatisticsRefreshDate OBJECT-TYPE
    SYNTAX          DisplayString (SIZE(0..255))
    MAX-ACCESS      read-only
    STATUS          current
    DESCRIPTION     
            "Date/Time from which the above counts were last updated. \nUse the Refresh All Stats action to update to the latest counts."
    ::= { ptPCEPeerTCAPStatisticsEntry 14 }

ptPCEPeerTCAPStatisticsResetDate OBJECT-TYPE
    SYNTAX          DisplayString (SIZE(0..255))
    MAX-ACCESS      read-only
    STATUS          current
    DESCRIPTION     
            "Date/Time from which the above counts were last started or reset. \nUse the Reset All Stats action to reset the counts to zero."
    ::= { ptPCEPeerTCAPStatisticsEntry 15 }

ptPCEPeerTCAPStatisticsPrivatePeerRecv OBJECT-TYPE
    SYNTAX          Integer32 (-2147483648..2147483647)
    MAX-ACCESS      read-only
    STATUS          current
    DESCRIPTION     
            "Number of Private TCAP messages received from peer on this peer."
    ::= { ptPCEPeerTCAPStatisticsEntry 16 }

ptPCEPeerTCAPStatisticsPrivatePeerSent OBJECT-TYPE
    SYNTAX          Integer32 (-2147483648..2147483647)
    MAX-ACCESS      read-only
    STATUS          current
    DESCRIPTION     
            "Number of Private TCAP messages sent from peer on this peer."
    ::= { ptPCEPeerTCAPStatisticsEntry 17 }

ptPCEPeerTCAPStatisticsPCEStatisticsIndex OBJECT-TYPE
    SYNTAX          Integer32 (-2147483648..2147483647)
    MAX-ACCESS      not-accessible
    STATUS          current
    DESCRIPTION     
            "This is the index of the parent type for this object.
             This parent type is PCEStatistics."
    ::= { ptPCEPeerTCAPStatisticsEntry 242 }

ptPCEPeerTCAPStatisticsPCETCAPStatisticsIndex OBJECT-TYPE
    SYNTAX          Integer32 (-2147483648..2147483647)
    MAX-ACCESS      not-accessible
    STATUS          current
    DESCRIPTION     
            "This is the index of the parent type for this object.
             This parent type is PCETCAPStatistics."
    ::= { ptPCEPeerTCAPStatisticsEntry 243 }

ptPCEPeerTCAPStatisticsActions OBJECT-TYPE
    SYNTAX          INTEGER { refreshAllStats(1), resetAllStats(2) }
    MAX-ACCESS      read-create
    STATUS          current
    DESCRIPTION     
            "The OID of all possible actions for this instance"
    ::= { ptPCEPeerTCAPStatisticsEntry 252 }

ptPCEPeerTCAPStatisticsParentOID OBJECT-TYPE
    SYNTAX          OBJECT IDENTIFIER
    MAX-ACCESS      read-create
    STATUS          current
    DESCRIPTION     
            "The OID of the parent object for this instance"
    ::= { ptPCEPeerTCAPStatisticsEntry 253 }

ptPCEPeerTCAPStatisticsRowStatus OBJECT-TYPE
    SYNTAX          RowStatus
    MAX-ACCESS      read-create
    STATUS          current
    DESCRIPTION     
            "The row status for the PCEPeerTCAPStatistics table"
    ::= { ptPCEPeerTCAPStatisticsEntry 254 }

ptPCEPeerTCAPStatisticsIndex OBJECT-TYPE
    SYNTAX          Integer32 (-2147483648..2147483647)
    MAX-ACCESS      not-accessible
    STATUS          current
    DESCRIPTION     
            "The row number for the PCEPeerTCAPStatistics table"
    ::= { ptPCEPeerTCAPStatisticsEntry 255 }

ptPCEPCENAManager OBJECT IDENTIFIER
    ::= { ptConnGroup 458 }

ptPCEPCENAManagerTable OBJECT-TYPE
    SYNTAX          SEQUENCE OF PtPCEPCENAManagerEntry
    MAX-ACCESS      not-accessible
    STATUS          current
    DESCRIPTION     
            "No description supplied in the proxy config file."
    ::= { ptPCEPCENAManager 1 }

ptPCEPCENAManagerEntry OBJECT-TYPE
    SYNTAX          PtPCEPCENAManagerEntry
    MAX-ACCESS      not-accessible
    STATUS          current
    DESCRIPTION     
            "A sequence of PCEPCENAManager attributes."
    INDEX           { ptConnGroupIndex, ptPCEPCENAManagerIndex }
    ::= { ptPCEPCENAManagerTable 1 }

PtPCEPCENAManagerEntry ::=
    SEQUENCE {
        ptPCEPCENAManagerPCENAs         Integer32,
        ptPCEPCENAManagerRegistrationTimer  INTEGER,
        ptPCEPCENAManagerParentOID      OBJECT IDENTIFIER,
        ptPCEPCENAManagerRowStatus      RowStatus,
        ptPCEPCENAManagerIndex          Integer32
    }

ptPCEPCENAManagerPCENAs OBJECT-TYPE
    SYNTAX          Integer32 (-2147483648..2147483647)
    MAX-ACCESS      read-only
    STATUS          current
    DESCRIPTION     
            "Number of PCE Network Appearances."
    ::= { ptPCEPCENAManagerEntry 1 }

ptPCEPCENAManagerRegistrationTimer OBJECT-TYPE
    SYNTAX          INTEGER { disabled(0) }
    MAX-ACCESS      read-create
    STATUS          current
    DESCRIPTION     
            "Interval between reregistration (in seconds)."
    ::= { ptPCEPCENAManagerEntry 2 }

ptPCEPCENAManagerParentOID OBJECT-TYPE
    SYNTAX          OBJECT IDENTIFIER
    MAX-ACCESS      read-create
    STATUS          current
    DESCRIPTION     
            "The OID of the parent object for this instance"
    ::= { ptPCEPCENAManagerEntry 253 }

ptPCEPCENAManagerRowStatus OBJECT-TYPE
    SYNTAX          RowStatus
    MAX-ACCESS      read-create
    STATUS          current
    DESCRIPTION     
            "The row status for the PCEPCENAManager table"
    ::= { ptPCEPCENAManagerEntry 254 }

ptPCEPCENAManagerIndex OBJECT-TYPE
    SYNTAX          Integer32 (-2147483648..2147483647)
    MAX-ACCESS      not-accessible
    STATUS          current
    DESCRIPTION     
            "The row number for the PCEPCENAManager table"
    ::= { ptPCEPCENAManagerEntry 255 }

ptPCEPCENA OBJECT IDENTIFIER
    ::= { ptPCEPCENAManager 459 }

ptPCEPCENATable OBJECT-TYPE
    SYNTAX          SEQUENCE OF PtPCEPCENAEntry
    MAX-ACCESS      not-accessible
    STATUS          current
    DESCRIPTION     
            "No description supplied in the proxy config file."
    ::= { ptPCEPCENA 1 }

ptPCEPCENAEntry OBJECT-TYPE
    SYNTAX          PtPCEPCENAEntry
    MAX-ACCESS      not-accessible
    STATUS          current
    DESCRIPTION     
            "A sequence of PCEPCENA attributes."
    INDEX           { ptConnGroupIndex, ptPCEPCENAPCENAManagerIndex, 
                      ptPCEPCENAIndex }
    ::= { ptPCEPCENATable 1 }

PtPCEPCENAEntry ::=
    SEQUENCE {
        ptPCEPCENANA                    Integer32,
        ptPCEPCENAType                  INTEGER,
        ptPCEPCENAMTPPort               Integer32,
        ptPCEPCENASCCPGTTPort           Integer32,
        ptPCEPCENAPCEGTTPort            Integer32,
        ptPCEPCENANetworkIndicator      INTEGER,
        ptPCEPCENAPCENAManagerIndex     Integer32,
        ptPCEPCENAParentOID             OBJECT IDENTIFIER,
        ptPCEPCENARowStatus             RowStatus,
        ptPCEPCENAIndex                 Integer32
    }

ptPCEPCENANA OBJECT-TYPE
    SYNTAX          Integer32 (1..99)
    MAX-ACCESS      read-create
    STATUS          current
    DESCRIPTION     
            "At the PCE level Network Appearances (NAs) are usually known as Public, Private-1, and Private-2. However the NA's are known at the MTP3, SCCP, and GTT by their numbers. \nCan only be modified when PCE traffic is deactivated. \nBy default, NA 1 is public while NA 2 and 3 are private."
    ::= { ptPCEPCENAEntry 1 }

ptPCEPCENAType OBJECT-TYPE
    SYNTAX          INTEGER { public(1), private1(2), private2(3) }
    MAX-ACCESS      read-only
    STATUS          current
    DESCRIPTION     
            "Network Appearance Type (PUBLIC/PRIVATE 1/PRIVATE 2)."
    ::= { ptPCEPCENAEntry 2 }

ptPCEPCENAMTPPort OBJECT-TYPE
    SYNTAX          Integer32 (-2147483648..2147483647)
    MAX-ACCESS      read-only
    STATUS          current
    DESCRIPTION     
            "User Port of the MTP3 for the given NA. \nThis is a read-only attribute for informational purposes."
    ::= { ptPCEPCENAEntry 4 }

ptPCEPCENASCCPGTTPort OBJECT-TYPE
    SYNTAX          Integer32 (-2147483648..2147483647)
    MAX-ACCESS      read-only
    STATUS          current
    DESCRIPTION     
            "GTT Port of the SCCP for the given NA. \nThis is a read-only attribute for informational purposes."
    ::= { ptPCEPCENAEntry 5 }

ptPCEPCENAPCEGTTPort OBJECT-TYPE
    SYNTAX          Integer32 (-2147483648..2147483647)
    MAX-ACCESS      read-only
    STATUS          current
    DESCRIPTION     
            "Service Port of the GTT for the given NA. \nPCE connects to SCCP GTT port to intercept traffic. The GTT for the given NA is connected to this port. \nThis is a read-only attribute for informational purposes."
    ::= { ptPCEPCENAEntry 6 }

ptPCEPCENANetworkIndicator OBJECT-TYPE
    SYNTAX          INTEGER { undefined(255), ni00(0), ni01(1), ni10(2), 
                        ni11(3) }
    MAX-ACCESS      read-only
    STATUS          current
    DESCRIPTION     
            "MTP3 NA associated Network Indicator. \nThis is a read-only attribute for informational purposes."
    ::= { ptPCEPCENAEntry 7 }

ptPCEPCENAPCENAManagerIndex OBJECT-TYPE
    SYNTAX          Integer32 (-2147483648..2147483647)
    MAX-ACCESS      not-accessible
    STATUS          current
    DESCRIPTION     
            "This is the index of the parent type for this object.
             This parent type is PCENAManager."
    ::= { ptPCEPCENAEntry 242 }

ptPCEPCENAParentOID OBJECT-TYPE
    SYNTAX          OBJECT IDENTIFIER
    MAX-ACCESS      read-create
    STATUS          current
    DESCRIPTION     
            "The OID of the parent object for this instance"
    ::= { ptPCEPCENAEntry 253 }

ptPCEPCENARowStatus OBJECT-TYPE
    SYNTAX          RowStatus
    MAX-ACCESS      read-create
    STATUS          current
    DESCRIPTION     
            "The row status for the PCEPCENA table"
    ::= { ptPCEPCENAEntry 254 }

ptPCEPCENAIndex OBJECT-TYPE
    SYNTAX          Integer32 (-2147483648..2147483647)
    MAX-ACCESS      not-accessible
    STATUS          current
    DESCRIPTION     
            "The row number for the PCEPCENA table"
    ::= { ptPCEPCENAEntry 255 }

ptPCEPCEDBManager OBJECT IDENTIFIER
    ::= { ptConnGroup 460 }

ptPCEPCEDBManagerTable OBJECT-TYPE
    SYNTAX          SEQUENCE OF PtPCEPCEDBManagerEntry
    MAX-ACCESS      not-accessible
    STATUS          current
    DESCRIPTION     
            "No description supplied in the proxy config file."
    ::= { ptPCEPCEDBManager 1 }

ptPCEPCEDBManagerEntry OBJECT-TYPE
    SYNTAX          PtPCEPCEDBManagerEntry
    MAX-ACCESS      not-accessible
    STATUS          current
    DESCRIPTION     
            "A sequence of PCEPCEDBManager attributes."
    INDEX           { ptConnGroupIndex, ptPCEPCEDBManagerIndex }
    ::= { ptPCEPCEDBManagerTable 1 }

PtPCEPCEDBManagerEntry ::=
    SEQUENCE {
        ptPCEPCEDBManagerActions        INTEGER,
        ptPCEPCEDBManagerParentOID      OBJECT IDENTIFIER,
        ptPCEPCEDBManagerRowStatus      RowStatus,
        ptPCEPCEDBManagerIndex          Integer32
    }

ptPCEPCEDBManagerActions OBJECT-TYPE
    SYNTAX          INTEGER { liveToWorkspace(1), workspaceToLive(2) }
    MAX-ACCESS      read-create
    STATUS          current
    DESCRIPTION     
            "The OID of all possible actions for this instance"
    ::= { ptPCEPCEDBManagerEntry 252 }

ptPCEPCEDBManagerParentOID OBJECT-TYPE
    SYNTAX          OBJECT IDENTIFIER
    MAX-ACCESS      read-create
    STATUS          current
    DESCRIPTION     
            "The OID of the parent object for this instance"
    ::= { ptPCEPCEDBManagerEntry 253 }

ptPCEPCEDBManagerRowStatus OBJECT-TYPE
    SYNTAX          RowStatus
    MAX-ACCESS      read-create
    STATUS          current
    DESCRIPTION     
            "The row status for the PCEPCEDBManager table"
    ::= { ptPCEPCEDBManagerEntry 254 }

ptPCEPCEDBManagerIndex OBJECT-TYPE
    SYNTAX          Integer32 (-2147483648..2147483647)
    MAX-ACCESS      not-accessible
    STATUS          current
    DESCRIPTION     
            "The row number for the PCEPCEDBManager table"
    ::= { ptPCEPCEDBManagerEntry 255 }

ptPCEPCEDBSummary OBJECT IDENTIFIER
    ::= { ptPCEPCEDBManager 461 }

ptPCEPCEDBSummaryTable OBJECT-TYPE
    SYNTAX          SEQUENCE OF PtPCEPCEDBSummaryEntry
    MAX-ACCESS      not-accessible
    STATUS          current
    DESCRIPTION     
            "No description supplied in the proxy config file."
    ::= { ptPCEPCEDBSummary 1 }

ptPCEPCEDBSummaryEntry OBJECT-TYPE
    SYNTAX          PtPCEPCEDBSummaryEntry
    MAX-ACCESS      not-accessible
    STATUS          current
    DESCRIPTION     
            "A sequence of PCEPCEDBSummary attributes."
    INDEX           { ptConnGroupIndex, 
                      ptPCEPCEDBSummaryPCEDBManagerIndex, 
                      ptPCEPCEDBSummaryIndex }
    ::= { ptPCEPCEDBSummaryTable 1 }

PtPCEPCEDBSummaryEntry ::=
    SEQUENCE {
        ptPCEPCEDBSummaryDatabaseType   INTEGER,
        ptPCEPCEDBSummaryLastAction     INTEGER,
        ptPCEPCEDBSummaryLastModified   DisplayString,
        ptPCEPCEDBSummaryErrors         Integer32,
        ptPCEPCEDBSummaryPublicNodes    Integer32,
        ptPCEPCEDBSummaryPrivateNodes   Integer32,
        ptPCEPCEDBSummaryPublicGateways Integer32,
        ptPCEPCEDBSummaryGTTTunnelGateways  Integer32,
        ptPCEPCEDBSummaryTrunkMappings  Integer32,
        ptPCEPCEDBSummaryISUPLearningExceptions       Integer32,
        ptPCEPCEDBSummaryIS41BillingIDMappings      Integer32,
        ptPCEPCEDBSummaryCurrentStatus  DisplayString,
        ptPCEPCEDBSummaryPCEDBManagerIndex  Integer32,
        ptPCEPCEDBSummaryParentOID      OBJECT IDENTIFIER,
        ptPCEPCEDBSummaryRowStatus      RowStatus,
        ptPCEPCEDBSummaryIndex          Integer32
    }

ptPCEPCEDBSummaryDatabaseType OBJECT-TYPE
    SYNTAX          INTEGER { live(1), workspace(2) }
    MAX-ACCESS      read-only
    STATUS          current
    DESCRIPTION     
            "Database Type (LIVE/WORKSPACE)."
    ::= { ptPCEPCEDBSummaryEntry 1 }

ptPCEPCEDBSummaryLastAction OBJECT-TYPE
    SYNTAX          INTEGER { notApplicable(0), manual(1), addRecords(2), 
                        deleteRecords(3), replaceDatabase(4), 
                        exportDatabase(5), loadDatabase(6), 
                        commitLiveFromWorkspace(7), 
                        resetWorkspaceFromLive(8), purgeDatabase(9), 
                        reloadDatabase(10), saveDatabase(11), 
                        addRecordsFailed(12), deleteRecordsFailed(13), 
                        replaceDatabaseFailed(14), 
                        exportDatabaseFailed(15), loadDatabaseFailed(16), 
                        reloadDatabaseFailed(17), 
                        purgeDatabaseFailed(18), saveDatabaseFailed(19), 
                        commitLiveFromWsFailed(20), 
                        resetWsFromLiveFailed(21), databaseUpgrade(22) }
    MAX-ACCESS      read-only
    STATUS          current
    DESCRIPTION     
            "Database Last Action."
    ::= { ptPCEPCEDBSummaryEntry 2 }

ptPCEPCEDBSummaryLastModified OBJECT-TYPE
    SYNTAX          DisplayString (SIZE(0..255))
    MAX-ACCESS      read-only
    STATUS          current
    DESCRIPTION     
            "Date and time of Last Action."
    ::= { ptPCEPCEDBSummaryEntry 3 }

ptPCEPCEDBSummaryErrors OBJECT-TYPE
    SYNTAX          Integer32 (-2147483648..2147483647)
    MAX-ACCESS      read-only
    STATUS          current
    DESCRIPTION     
            "Number of errors during Last Action."
    ::= { ptPCEPCEDBSummaryEntry 4 }

ptPCEPCEDBSummaryPublicNodes OBJECT-TYPE
    SYNTAX          Integer32 (-2147483648..2147483647)
    MAX-ACCESS      read-only
    STATUS          current
    DESCRIPTION     
            "Number of Public Nodes."
    ::= { ptPCEPCEDBSummaryEntry 5 }

ptPCEPCEDBSummaryPrivateNodes OBJECT-TYPE
    SYNTAX          Integer32 (-2147483648..2147483647)
    MAX-ACCESS      read-only
    STATUS          current
    DESCRIPTION     
            "Number of Private Nodes."
    ::= { ptPCEPCEDBSummaryEntry 6 }

ptPCEPCEDBSummaryPublicGateways OBJECT-TYPE
    SYNTAX          Integer32 (-2147483648..2147483647)
    MAX-ACCESS      read-only
    STATUS          current
    DESCRIPTION     
            "Number of Public Gateways."
    ::= { ptPCEPCEDBSummaryEntry 7 }

ptPCEPCEDBSummaryGTTTunnelGateways OBJECT-TYPE
    SYNTAX          Integer32 (-2147483648..2147483647)
    MAX-ACCESS      read-only
    STATUS          current
    DESCRIPTION     
            "Number of GTT Tunnel Gateways."
    ::= { ptPCEPCEDBSummaryEntry 8 }

ptPCEPCEDBSummaryTrunkMappings OBJECT-TYPE
    SYNTAX          Integer32 (-2147483648..2147483647)
    MAX-ACCESS      read-only
    STATUS          current
    DESCRIPTION     
            "Number of Trunk Mappings."
    ::= { ptPCEPCEDBSummaryEntry 9 }

ptPCEPCEDBSummaryISUPLearningExceptions OBJECT-TYPE
    SYNTAX          Integer32 (-2147483648..2147483647)
    MAX-ACCESS      read-only
    STATUS          current
    DESCRIPTION     
            "Number of ISUP Learning Exceptions."
    ::= { ptPCEPCEDBSummaryEntry 10 }

ptPCEPCEDBSummaryIS41BillingIDMappings OBJECT-TYPE
    SYNTAX          Integer32 (-2147483648..2147483647)
    MAX-ACCESS      read-only
    STATUS          current
    DESCRIPTION     
            "Number of IS41 Billing ID Mappings."
    ::= { ptPCEPCEDBSummaryEntry 11 }

ptPCEPCEDBSummaryCurrentStatus OBJECT-TYPE
    SYNTAX          DisplayString (SIZE(0..255))
    MAX-ACCESS      read-only
    STATUS          current
    DESCRIPTION     
            "Current database status."
    ::= { ptPCEPCEDBSummaryEntry 12 }

ptPCEPCEDBSummaryPCEDBManagerIndex OBJECT-TYPE
    SYNTAX          Integer32 (-2147483648..2147483647)
    MAX-ACCESS      not-accessible
    STATUS          current
    DESCRIPTION     
            "This is the index of the parent type for this object.
             This parent type is PCEDBManager."
    ::= { ptPCEPCEDBSummaryEntry 242 }

ptPCEPCEDBSummaryParentOID OBJECT-TYPE
    SYNTAX          OBJECT IDENTIFIER
    MAX-ACCESS      read-create
    STATUS          current
    DESCRIPTION     
            "The OID of the parent object for this instance"
    ::= { ptPCEPCEDBSummaryEntry 253 }

ptPCEPCEDBSummaryRowStatus OBJECT-TYPE
    SYNTAX          RowStatus
    MAX-ACCESS      read-create
    STATUS          current
    DESCRIPTION     
            "The row status for the PCEPCEDBSummary table"
    ::= { ptPCEPCEDBSummaryEntry 254 }

ptPCEPCEDBSummaryIndex OBJECT-TYPE
    SYNTAX          Integer32 (-2147483648..2147483647)
    MAX-ACCESS      not-accessible
    STATUS          current
    DESCRIPTION     
            "The row number for the PCEPCEDBSummary table"
    ::= { ptPCEPCEDBSummaryEntry 255 }

ptPCEPCEDatabase OBJECT IDENTIFIER
    ::= { ptConnGroup 462 }

ptPCEPCEDatabaseTable OBJECT-TYPE
    SYNTAX          SEQUENCE OF PtPCEPCEDatabaseEntry
    MAX-ACCESS      not-accessible
    STATUS          current
    DESCRIPTION     
            "No description supplied in the proxy config file."
    ::= { ptPCEPCEDatabase 1 }

ptPCEPCEDatabaseEntry OBJECT-TYPE
    SYNTAX          PtPCEPCEDatabaseEntry
    MAX-ACCESS      not-accessible
    STATUS          current
    DESCRIPTION     
            "A sequence of PCEPCEDatabase attributes."
    INDEX           { ptConnGroupIndex, ptPCEPCEDatabaseIndex }
    ::= { ptPCEPCEDatabaseTable 1 }

PtPCEPCEDatabaseEntry ::=
    SEQUENCE {
        ptPCEPCEDatabaseType            INTEGER,
        ptPCEPCEDatabaseLastModified    DisplayString,
        ptPCEPCEDatabaseParentOID       OBJECT IDENTIFIER,
        ptPCEPCEDatabaseRowStatus       RowStatus,
        ptPCEPCEDatabaseIndex           Integer32
    }

ptPCEPCEDatabaseType OBJECT-TYPE
    SYNTAX          INTEGER { live(1), workspace(2) }
    MAX-ACCESS      read-only
    STATUS          current
    DESCRIPTION     
            "Database Type (LIVE, WORKSPACE)."
    ::= { ptPCEPCEDatabaseEntry 1 }

ptPCEPCEDatabaseLastModified OBJECT-TYPE
    SYNTAX          DisplayString (SIZE(0..255))
    MAX-ACCESS      read-only
    STATUS          current
    DESCRIPTION     
            "Date/Time of last modification."
    ::= { ptPCEPCEDatabaseEntry 2 }

ptPCEPCEDatabaseParentOID OBJECT-TYPE
    SYNTAX          OBJECT IDENTIFIER
    MAX-ACCESS      read-create
    STATUS          current
    DESCRIPTION     
            "The OID of the parent object for this instance"
    ::= { ptPCEPCEDatabaseEntry 253 }

ptPCEPCEDatabaseRowStatus OBJECT-TYPE
    SYNTAX          RowStatus
    MAX-ACCESS      read-create
    STATUS          current
    DESCRIPTION     
            "The row status for the PCEPCEDatabase table"
    ::= { ptPCEPCEDatabaseEntry 254 }

ptPCEPCEDatabaseIndex OBJECT-TYPE
    SYNTAX          Integer32 (-2147483648..2147483647)
    MAX-ACCESS      not-accessible
    STATUS          current
    DESCRIPTION     
            "The row number for the PCEPCEDatabase table"
    ::= { ptPCEPCEDatabaseEntry 255 }

ptPCEGTTTunnelGateways OBJECT IDENTIFIER
    ::= { ptPCEPCEDatabase 469 }

ptPCEGTTTunnelGatewaysTable OBJECT-TYPE
    SYNTAX          SEQUENCE OF PtPCEGTTTunnelGatewaysEntry
    MAX-ACCESS      not-accessible
    STATUS          current
    DESCRIPTION     
            "No description supplied in the proxy config file."
    ::= { ptPCEGTTTunnelGateways 1 }

ptPCEGTTTunnelGatewaysEntry OBJECT-TYPE
    SYNTAX          PtPCEGTTTunnelGatewaysEntry
    MAX-ACCESS      not-accessible
    STATUS          current
    DESCRIPTION     
            "A sequence of PCEGTTTunnelGateways attributes."
    INDEX           { ptConnGroupIndex, 
                      ptPCEGTTTunnelGatewaysPCEDatabaseIndex, 
                      ptPCEGTTTunnelGatewaysIndex }
    ::= { ptPCEGTTTunnelGatewaysTable 1 }

PtPCEGTTTunnelGatewaysEntry ::=
    SEQUENCE {
        ptPCEGTTTunnelGatewaysGTTTunnelGateways       Integer32,
        ptPCEGTTTunnelGatewaysPCEDatabaseIndex      Integer32,
        ptPCEGTTTunnelGatewaysParentOID OBJECT IDENTIFIER,
        ptPCEGTTTunnelGatewaysRowStatus RowStatus,
        ptPCEGTTTunnelGatewaysIndex     Integer32
    }

ptPCEGTTTunnelGatewaysGTTTunnelGateways OBJECT-TYPE
    SYNTAX          Integer32 (-2147483648..2147483647)
    MAX-ACCESS      read-only
    STATUS          current
    DESCRIPTION     
            "Number of GTT Tunnel Gateways."
    ::= { ptPCEGTTTunnelGatewaysEntry 1 }

ptPCEGTTTunnelGatewaysPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEGTTTunnelGatewaysEntry 242 }

ptPCEGTTTunnelGatewaysParentOID OBJECT-TYPE
    SYNTAX          OBJECT IDENTIFIER
    MAX-ACCESS      read-create
    STATUS          current
    DESCRIPTION     
            "The OID of the parent object for this instance"
    ::= { ptPCEGTTTunnelGatewaysEntry 253 }

ptPCEGTTTunnelGatewaysRowStatus OBJECT-TYPE
    SYNTAX          RowStatus
    MAX-ACCESS      read-create
    STATUS          current
    DESCRIPTION     
            "The row status for the PCEGTTTunnelGateways table"
    ::= { ptPCEGTTTunnelGatewaysEntry 254 }

ptPCEGTTTunnelGatewaysIndex OBJECT-TYPE
    SYNTAX          Integer32 (-2147483648..2147483647)
    MAX-ACCESS      not-accessible
    STATUS          current
    DESCRIPTION     
            "The row number for the PCEGTTTunnelGateways table"
    ::= { ptPCEGTTTunnelGatewaysEntry 255 }

ptPCEGTTTunnelGateway OBJECT IDENTIFIER
    ::= { ptPCEGTTTunnelGateways 470 }

ptPCEGTTTunnelGatewayTable OBJECT-TYPE
    SYNTAX          SEQUENCE OF PtPCEGTTTunnelGatewayEntry
    MAX-ACCESS      not-accessible
    STATUS          current
    DESCRIPTION     
            "No description supplied in the proxy config file."
    ::= { ptPCEGTTTunnelGateway 1 }

ptPCEGTTTunnelGatewayEntry OBJECT-TYPE
    SYNTAX          PtPCEGTTTunnelGatewayEntry
    MAX-ACCESS      not-accessible
    STATUS          current
    DESCRIPTION     
            "A sequence of PCEGTTTunnelGateway attributes."
    INDEX           { ptConnGroupIndex, 
                      ptPCEGTTTunnelGatewayPCEDatabaseIndex, 
                      ptPCEGTTTunnelGatewayGTTTunnelGatewaysIndex, 
                      ptPCEGTTTunnelGatewayIndex }
    ::= { ptPCEGTTTunnelGatewayTable 1 }

PtPCEGTTTunnelGatewayEntry ::=
    SEQUENCE {
        ptPCEGTTTunnelGatewayName       DisplayString,
        ptPCEGTTTunnelGatewayPublicPC   Integer32,
        ptPCEGTTTunnelGatewayPrivatePC  Integer32,
        ptPCEGTTTunnelGatewayStatusSummary  INTEGER,
        ptPCEGTTTunnelGatewayPublicMTPStatus    DisplayString,
        ptPCEGTTTunnelGatewayPublicSCCPStatus     DisplayString,
        ptPCEGTTTunnelGatewayPrivate1MTPStatus      DisplayString,
        ptPCEGTTTunnelGatewayPrivate1SCCPStatus       DisplayString,
        ptPCEGTTTunnelGatewayPrivate2MTPStatus      DisplayString,
        ptPCEGTTTunnelGatewayPrivate2SCCPStatus       DisplayString,
        ptPCEGTTTunnelGatewayPCEDatabaseIndex     Integer32,
        ptPCEGTTTunnelGatewayGTTTunnelGatewaysIndex           Integer32,
        ptPCEGTTTunnelGatewayParentOID  OBJECT IDENTIFIER,
        ptPCEGTTTunnelGatewayRowStatus  RowStatus,
        ptPCEGTTTunnelGatewayIndex      Integer32
    }

ptPCEGTTTunnelGatewayName OBJECT-TYPE
    SYNTAX          DisplayString (SIZE(0..255))
    MAX-ACCESS      read-create
    STATUS          current
    DESCRIPTION     
            "GTT Tunnel Gateway unique name."
    ::= { ptPCEGTTTunnelGatewayEntry 1 }

ptPCEGTTTunnelGatewayPublicPC OBJECT-TYPE
    SYNTAX          Integer32 (-2147483648..2147483647)
    MAX-ACCESS      read-only
    STATUS          current
    DESCRIPTION     
            "This attribute describes a point code that will be used for GTT processing of traffic that is NOT to be processed through PCE. ISUP traffic cannot be processed by GTT. \nThe MTP3 on the public NA must have a corresponding VNode. \nIf traffic goes from the public side to the private side via GTT, the Private PC will be used as the Originating Point Code in the private network."
    ::= { ptPCEGTTTunnelGatewayEntry 2 }

ptPCEGTTTunnelGatewayPrivatePC OBJECT-TYPE
    SYNTAX          Integer32 (-2147483648..2147483647)
    MAX-ACCESS      read-only
    STATUS          current
    DESCRIPTION     
            "This attribute describes a point code that will be used for GTT processing of traffic that is NOT to be processed through PCE. ISUP traffic cannot be processed by GTT. \nThe MTP3 on both private NAs must have a corresponding VNode. The same PC is used in both private networks. \nIf traffic goes from the private side to the public side via GTT, the Private PC will be used as the Originating Point Code."
    ::= { ptPCEGTTTunnelGatewayEntry 3 }

ptPCEGTTTunnelGatewayStatusSummary OBJECT-TYPE
    SYNTAX          INTEGER { error(0), ok(1), notApplicable(2) }
    MAX-ACCESS      read-only
    STATUS          current
    DESCRIPTION     
            "Status Summary [NOT APPLICABLE/OK/ERROR]."
    ::= { ptPCEGTTTunnelGatewayEntry 4 }

ptPCEGTTTunnelGatewayPublicMTPStatus OBJECT-TYPE
    SYNTAX          DisplayString (SIZE(0..255))
    MAX-ACCESS      read-only
    STATUS          current
    DESCRIPTION     
            "This attribute will indicate if any PCE process on any CPU are having difficulties with the connection to the MTP3. \nThe most common cause of problems here is forgetting to create a corresponding VNode in the MTP3 public NA or IP networking errors. \nObsolete as of 16.0.0."
    ::= { ptPCEGTTTunnelGatewayEntry 5 }

ptPCEGTTTunnelGatewayPublicSCCPStatus OBJECT-TYPE
    SYNTAX          DisplayString (SIZE(0..255))
    MAX-ACCESS      read-only
    STATUS          current
    DESCRIPTION     
            "This attribute will indicate if any PCE process on any CPU are having difficulties with the connection to the SCCP. \nThe most common cause of problems here is forgetting to create a corresponding VNode in the MTP3 public NA or IP networking errors."
    ::= { ptPCEGTTTunnelGatewayEntry 6 }

ptPCEGTTTunnelGatewayPrivate1MTPStatus OBJECT-TYPE
    SYNTAX          DisplayString (SIZE(0..255))
    MAX-ACCESS      read-only
    STATUS          current
    DESCRIPTION     
            "This attribute will indicate if any PCE process on any CPU are having difficulties with the connection to the MTP3. \nThe most common cause of problems here is forgetting to create a corresponding VNode in the MTP3 first private NA or IP networking errors. \nObsolete as of 16.0.0."
    ::= { ptPCEGTTTunnelGatewayEntry 7 }

ptPCEGTTTunnelGatewayPrivate1SCCPStatus OBJECT-TYPE
    SYNTAX          DisplayString (SIZE(0..255))
    MAX-ACCESS      read-only
    STATUS          current
    DESCRIPTION     
            "This attribute will indicate if any PCE process on any CPU are having difficulties with the connection to the SCCP. \nThe most common cause of problems here is forgetting to create a corresponding VNode in the MTP3 first private NA or IP networking errors."
    ::= { ptPCEGTTTunnelGatewayEntry 8 }

ptPCEGTTTunnelGatewayPrivate2MTPStatus OBJECT-TYPE
    SYNTAX          DisplayString (SIZE(0..255))
    MAX-ACCESS      read-only
    STATUS          current
    DESCRIPTION     
            "This attribute will indicate if any PCE process on any CPU are having difficulties with the connection to the MTP3. \nThe most common cause of problems here is forgetting to create a corresponding VNode in the MTP3 second private NA or IP networking errors. \nObsolete as of 16.0.0."
    ::= { ptPCEGTTTunnelGatewayEntry 9 }

ptPCEGTTTunnelGatewayPrivate2SCCPStatus OBJECT-TYPE
    SYNTAX          DisplayString (SIZE(0..255))
    MAX-ACCESS      read-only
    STATUS          current
    DESCRIPTION     
            "This attribute will indicate if any PCE process on any CPU are having difficulties with the connection to the SCCP. \nThe most common cause of problems here is forgetting to create a corresponding VNode in the MTP3 second private NA or IP networking errors."
    ::= { ptPCEGTTTunnelGatewayEntry 10 }

ptPCEGTTTunnelGatewayPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEGTTTunnelGatewayEntry 242 }

ptPCEGTTTunnelGatewayGTTTunnelGatewaysIndex OBJECT-TYPE
    SYNTAX          Integer32 (-2147483648..2147483647)
    MAX-ACCESS      not-accessible
    STATUS          current
    DESCRIPTION     
            "This is the index of the parent type for this object.
             This parent type is GTTTunnelGateways."
    ::= { ptPCEGTTTunnelGatewayEntry 243 }

ptPCEGTTTunnelGatewayParentOID OBJECT-TYPE
    SYNTAX          OBJECT IDENTIFIER
    MAX-ACCESS      read-create
    STATUS          current
    DESCRIPTION     
            "The OID of the parent object for this instance"
    ::= { ptPCEGTTTunnelGatewayEntry 253 }

ptPCEGTTTunnelGatewayRowStatus OBJECT-TYPE
    SYNTAX          RowStatus
    MAX-ACCESS      read-create
    STATUS          current
    DESCRIPTION     
            "The row status for the PCEGTTTunnelGateway table"
    ::= { ptPCEGTTTunnelGatewayEntry 254 }

ptPCEGTTTunnelGatewayIndex OBJECT-TYPE
    SYNTAX          Integer32 (-2147483648..2147483647)
    MAX-ACCESS      not-accessible
    STATUS          current
    DESCRIPTION     
            "The row number for the PCEGTTTunnelGateway table"
    ::= { ptPCEGTTTunnelGatewayEntry 255 }

ptPCEISUPLearningExceptions OBJECT IDENTIFIER
    ::= { ptPCEPCEDatabase 693 }

ptPCEISUPLearningExceptionsTable OBJECT-TYPE
    SYNTAX          SEQUENCE OF PtPCEISUPLearningExceptionsEntry
    MAX-ACCESS      not-accessible
    STATUS          current
    DESCRIPTION     
            "No description supplied in the proxy config file."
    ::= { ptPCEISUPLearningExceptions 1 }

ptPCEISUPLearningExceptionsEntry OBJECT-TYPE
    SYNTAX          PtPCEISUPLearningExceptionsEntry
    MAX-ACCESS      not-accessible
    STATUS          current
    DESCRIPTION     
            "A sequence of PCEISUPLearningExceptions attributes."
    INDEX           { ptConnGroupIndex, 
                      ptPCEISUPLearningExceptionsPCEDatabaseIndex, 
                      ptPCEISUPLearningExceptionsIndex }
    ::= { ptPCEISUPLearningExceptionsTable 1 }

PtPCEISUPLearningExceptionsEntry ::=
    SEQUENCE {
        ptPCEISUPLearningExceptionsISUPLearningExceptions                 Integer32,
        ptPCEISUPLearningExceptionsPCEDatabaseIndex           Integer32,
        ptPCEISUPLearningExceptionsParentOID    OBJECT IDENTIFIER,
        ptPCEISUPLearningExceptionsRowStatus    RowStatus,
        ptPCEISUPLearningExceptionsIndex Integer32
    }

ptPCEISUPLearningExceptionsISUPLearningExceptions OBJECT-TYPE
    SYNTAX          Integer32 (-2147483648..2147483647)
    MAX-ACCESS      read-only
    STATUS          current
    DESCRIPTION     
            "Number of TCAP ISUP Learning Exceptions."
    ::= { ptPCEISUPLearningExceptionsEntry 1 }

ptPCEISUPLearningExceptionsPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEISUPLearningExceptionsEntry 242 }

ptPCEISUPLearningExceptionsParentOID OBJECT-TYPE
    SYNTAX          OBJECT IDENTIFIER
    MAX-ACCESS      read-create
    STATUS          current
    DESCRIPTION     
            "The OID of the parent object for this instance"
    ::= { ptPCEISUPLearningExceptionsEntry 253 }

ptPCEISUPLearningExceptionsRowStatus OBJECT-TYPE
    SYNTAX          RowStatus
    MAX-ACCESS      read-create
    STATUS          current
    DESCRIPTION     
            "The row status for the PCEISUPLearningExceptions table"
    ::= { ptPCEISUPLearningExceptionsEntry 254 }

ptPCEISUPLearningExceptionsIndex OBJECT-TYPE
    SYNTAX          Integer32 (-2147483648..2147483647)
    MAX-ACCESS      not-accessible
    STATUS          current
    DESCRIPTION     
            "The row number for the PCEISUPLearningExceptions table"
    ::= { ptPCEISUPLearningExceptionsEntry 255 }

ptPCEISUPLearningException OBJECT IDENTIFIER
    ::= { ptPCEISUPLearningExceptions 694 }

ptPCEISUPLearningExceptionTable OBJECT-TYPE
    SYNTAX          SEQUENCE OF PtPCEISUPLearningExceptionEntry
    MAX-ACCESS      not-accessible
    STATUS          current
    DESCRIPTION     
            "No description supplied in the proxy config file."
    ::= { ptPCEISUPLearningException 1 }

ptPCEISUPLearningExceptionEntry OBJECT-TYPE
    SYNTAX          PtPCEISUPLearningExceptionEntry
    MAX-ACCESS      not-accessible
    STATUS          current
    DESCRIPTION     
            "A sequence of PCEISUPLearningException attributes."
    INDEX           { ptConnGroupIndex, 
                      ptPCEISUPLearningExceptionPCEDatabaseIndex, 
                      ptPCEISUPLearningExceptionISUPLearningExceptionsIndex, 
                      ptPCEISUPLearningExceptionIndex }
    ::= { ptPCEISUPLearningExceptionTable 1 }

PtPCEISUPLearningExceptionEntry ::=
    SEQUENCE {
        ptPCEISUPLearningExceptionPrefixDigits      DisplayString,
        ptPCEISUPLearningExceptionPCEDatabaseIndex          Integer32,
        ptPCEISUPLearningExceptionISUPLearningExceptionsIndex                     Integer32,
        ptPCEISUPLearningExceptionParentOID   OBJECT IDENTIFIER,
        ptPCEISUPLearningExceptionRowStatus   RowStatus,
        ptPCEISUPLearningExceptionIndex Integer32
    }

ptPCEISUPLearningExceptionPrefixDigits OBJECT-TYPE
    SYNTAX          DisplayString (SIZE(0..255))
    MAX-ACCESS      read-only
    STATUS          current
    DESCRIPTION     
            "TCAP ISUP Learning Exception prefix digit(s) (up to 9 digits)."
    ::= { ptPCEISUPLearningExceptionEntry 1 }

ptPCEISUPLearningExceptionPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEISUPLearningExceptionEntry 242 }

ptPCEISUPLearningExceptionISUPLearningExceptionsIndex OBJECT-TYPE
    SYNTAX          Integer32 (-2147483648..2147483647)
    MAX-ACCESS      not-accessible
    STATUS          current
    DESCRIPTION     
            "This is the index of the parent type for this object.
             This parent type is ISUPLearningExceptions."
    ::= { ptPCEISUPLearningExceptionEntry 243 }

ptPCEISUPLearningExceptionParentOID OBJECT-TYPE
    SYNTAX          OBJECT IDENTIFIER
    MAX-ACCESS      read-create
    STATUS          current
    DESCRIPTION     
            "The OID of the parent object for this instance"
    ::= { ptPCEISUPLearningExceptionEntry 253 }

ptPCEISUPLearningExceptionRowStatus OBJECT-TYPE
    SYNTAX          RowStatus
    MAX-ACCESS      read-create
    STATUS          current
    DESCRIPTION     
            "The row status for the PCEISUPLearningException table"
    ::= { ptPCEISUPLearningExceptionEntry 254 }

ptPCEISUPLearningExceptionIndex OBJECT-TYPE
    SYNTAX          Integer32 (-2147483648..2147483647)
    MAX-ACCESS      not-accessible
    STATUS          current
    DESCRIPTION     
            "The row number for the PCEISUPLearningException table"
    ::= { ptPCEISUPLearningExceptionEntry 255 }

ptPCEPCEBatchOperations OBJECT IDENTIFIER
    ::= { ptPCEPCEDatabase 695 }

ptPCEPCEBatchOperationsTable OBJECT-TYPE
    SYNTAX          SEQUENCE OF PtPCEPCEBatchOperationsEntry
    MAX-ACCESS      not-accessible
    STATUS          current
    DESCRIPTION     
            "No description supplied in the proxy config file."
    ::= { ptPCEPCEBatchOperations 1 }

ptPCEPCEBatchOperationsEntry OBJECT-TYPE
    SYNTAX          PtPCEPCEBatchOperationsEntry
    MAX-ACCESS      not-accessible
    STATUS          current
    DESCRIPTION     
            "A sequence of PCEPCEBatchOperations attributes."
    INDEX           { ptConnGroupIndex, 
                      ptPCEPCEBatchOperationsPCEDatabaseIndex, 
                      ptPCEPCEBatchOperationsIndex }
    ::= { ptPCEPCEBatchOperationsTable 1 }

PtPCEPCEBatchOperationsEntry ::=
    SEQUENCE {
        ptPCEPCEBatchOperationsBatchInterval    Integer32,
        ptPCEPCEBatchOperationsCurrentStatus    DisplayString,
        ptPCEPCEBatchOperationsMaxPerInterval     Integer32,
        ptPCEPCEBatchOperationsPCEDatabaseIndex       Integer32,
        ptPCEPCEBatchOperationsActions  INTEGER,
        ptPCEPCEBatchOperationsParentOID OBJECT IDENTIFIER,
        ptPCEPCEBatchOperationsRowStatus RowStatus,
        ptPCEPCEBatchOperationsIndex    Integer32
    }

ptPCEPCEBatchOperationsBatchInterval OBJECT-TYPE
    SYNTAX          Integer32 (1..60000)
    MAX-ACCESS      read-create
    STATUS          current
    DESCRIPTION     
            "Interval at which batch operations process each record (in milliseconds). \nThe valid values are 1 to 60000."
    ::= { ptPCEPCEBatchOperationsEntry 1 }

ptPCEPCEBatchOperationsCurrentStatus OBJECT-TYPE
    SYNTAX          DisplayString (SIZE(0..255))
    MAX-ACCESS      read-only
    STATUS          current
    DESCRIPTION     
            "Current database status"
    ::= { ptPCEPCEBatchOperationsEntry 2 }

ptPCEPCEBatchOperationsMaxPerInterval OBJECT-TYPE
    SYNTAX          Integer32 (1..100)
    MAX-ACCESS      read-create
    STATUS          current
    DESCRIPTION     
            "Maximum number of records processed in each batch operation interval. \nThe valid values are 1 to 100."
    ::= { ptPCEPCEBatchOperationsEntry 3 }

ptPCEPCEBatchOperationsPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEPCEBatchOperationsEntry 242 }

ptPCEPCEBatchOperationsActions OBJECT-TYPE
    SYNTAX          INTEGER { addRecords(1), deleteRecords(2), 
                        replaceDatabase(3), exportDatabase(4), 
                        purgeDatabase(5), fileTransfer(6) }
    MAX-ACCESS      read-create
    STATUS          current
    DESCRIPTION     
            "The OID of all possible actions for this instance"
    ::= { ptPCEPCEBatchOperationsEntry 252 }

ptPCEPCEBatchOperationsParentOID OBJECT-TYPE
    SYNTAX          OBJECT IDENTIFIER
    MAX-ACCESS      read-create
    STATUS          current
    DESCRIPTION     
            "The OID of the parent object for this instance"
    ::= { ptPCEPCEBatchOperationsEntry 253 }

ptPCEPCEBatchOperationsRowStatus OBJECT-TYPE
    SYNTAX          RowStatus
    MAX-ACCESS      read-create
    STATUS          current
    DESCRIPTION     
            "The row status for the PCEPCEBatchOperations table"
    ::= { ptPCEPCEBatchOperationsEntry 254 }

ptPCEPCEBatchOperationsIndex OBJECT-TYPE
    SYNTAX          Integer32 (-2147483648..2147483647)
    MAX-ACCESS      not-accessible
    STATUS          current
    DESCRIPTION     
            "The row number for the PCEPCEBatchOperations table"
    ::= { ptPCEPCEBatchOperationsEntry 255 }

ptPCEPCESearchOperations OBJECT IDENTIFIER
    ::= { ptPCEPCEDatabase 696 }

ptPCEPCESearchOperationsTable OBJECT-TYPE
    SYNTAX          SEQUENCE OF PtPCEPCESearchOperationsEntry
    MAX-ACCESS      not-accessible
    STATUS          current
    DESCRIPTION     
            "No description supplied in the proxy config file."
    ::= { ptPCEPCESearchOperations 1 }

ptPCEPCESearchOperationsEntry OBJECT-TYPE
    SYNTAX          PtPCEPCESearchOperationsEntry
    MAX-ACCESS      not-accessible
    STATUS          current
    DESCRIPTION     
            "A sequence of PCEPCESearchOperations attributes."
    INDEX           { ptConnGroupIndex, 
                      ptPCEPCESearchOperationsPCEDatabaseIndex, 
                      ptPCEPCESearchOperationsIndex }
    ::= { ptPCEPCESearchOperationsTable 1 }

PtPCEPCESearchOperationsEntry ::=
    SEQUENCE {
        ptPCEPCESearchOperationsDigits  DisplayString,
        ptPCEPCESearchOperationsPrivateNodeName       DisplayString,
        ptPCEPCESearchOperationsExpiry  DisplayString,
        ptPCEPCESearchOperationsSearchStatus    INTEGER,
        ptPCEPCESearchOperationsPCEDatabaseIndex        Integer32,
        ptPCEPCESearchOperationsParentOID OBJECT IDENTIFIER,
        ptPCEPCESearchOperationsRowStatus RowStatus,
        ptPCEPCESearchOperationsIndex   Integer32
    }

ptPCEPCESearchOperationsDigits OBJECT-TYPE
    SYNTAX          DisplayString (SIZE(0..255))
    MAX-ACCESS      read-create
    STATUS          current
    DESCRIPTION     
            "ISUP Learned Digits."
    ::= { ptPCEPCESearchOperationsEntry 1 }

ptPCEPCESearchOperationsPrivateNodeName OBJECT-TYPE
    SYNTAX          DisplayString (SIZE(0..255))
    MAX-ACCESS      read-only
    STATUS          current
    DESCRIPTION     
            "ISUP Learned Private Node name for given digits."
    ::= { ptPCEPCESearchOperationsEntry 2 }

ptPCEPCESearchOperationsExpiry OBJECT-TYPE
    SYNTAX          DisplayString (SIZE(0..255))
    MAX-ACCESS      read-only
    STATUS          current
    DESCRIPTION     
            "ISUP Learned expiry for given digits."
    ::= { ptPCEPCESearchOperationsEntry 3 }

ptPCEPCESearchOperationsSearchStatus OBJECT-TYPE
    SYNTAX          INTEGER { found(0), notFound(1), searchPending(2) }
    MAX-ACCESS      read-only
    STATUS          current
    DESCRIPTION     
            "ISUP Learning search status (FOUND, NOT FOUND, SEARCH PENDING)."
    ::= { ptPCEPCESearchOperationsEntry 4 }

ptPCEPCESearchOperationsPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEPCESearchOperationsEntry 242 }

ptPCEPCESearchOperationsParentOID OBJECT-TYPE
    SYNTAX          OBJECT IDENTIFIER
    MAX-ACCESS      read-create
    STATUS          current
    DESCRIPTION     
            "The OID of the parent object for this instance"
    ::= { ptPCEPCESearchOperationsEntry 253 }

ptPCEPCESearchOperationsRowStatus OBJECT-TYPE
    SYNTAX          RowStatus
    MAX-ACCESS      read-create
    STATUS          current
    DESCRIPTION     
            "The row status for the PCEPCESearchOperations table"
    ::= { ptPCEPCESearchOperationsEntry 254 }

ptPCEPCESearchOperationsIndex OBJECT-TYPE
    SYNTAX          Integer32 (-2147483648..2147483647)
    MAX-ACCESS      not-accessible
    STATUS          current
    DESCRIPTION     
            "The row number for the PCEPCESearchOperations table"
    ::= { ptPCEPCESearchOperationsEntry 255 }

ptPCEIS41BillingIDMappings OBJECT IDENTIFIER
    ::= { ptPCEPCEDatabase 697 }

ptPCEIS41BillingIDMappingsTable OBJECT-TYPE
    SYNTAX          SEQUENCE OF PtPCEIS41BillingIDMappingsEntry
    MAX-ACCESS      not-accessible
    STATUS          current
    DESCRIPTION     
            "No description supplied in the proxy config file."
    ::= { ptPCEIS41BillingIDMappings 1 }

ptPCEIS41BillingIDMappingsEntry OBJECT-TYPE
    SYNTAX          PtPCEIS41BillingIDMappingsEntry
    MAX-ACCESS      not-accessible
    STATUS          current
    DESCRIPTION     
            "A sequence of PCEIS41BillingIDMappings attributes."
    INDEX           { ptConnGroupIndex, 
                      ptPCEIS41BillingIDMappingsPCEDatabaseIndex, 
                      ptPCEIS41BillingIDMappingsIndex }
    ::= { ptPCEIS41BillingIDMappingsTable 1 }

PtPCEIS41BillingIDMappingsEntry ::=
    SEQUENCE {
        ptPCEIS41BillingIDMappingsIS41BillingIDMappings               Integer32,
        ptPCEIS41BillingIDMappingsPCEDatabaseIndex          Integer32,
        ptPCEIS41BillingIDMappingsParentOID   OBJECT IDENTIFIER,
        ptPCEIS41BillingIDMappingsRowStatus   RowStatus,
        ptPCEIS41BillingIDMappingsIndex Integer32
    }

ptPCEIS41BillingIDMappingsIS41BillingIDMappings OBJECT-TYPE
    SYNTAX          Integer32 (-2147483648..2147483647)
    MAX-ACCESS      read-only
    STATUS          current
    DESCRIPTION     
            "Number of IS41 Billing ID Mappings."
    ::= { ptPCEIS41BillingIDMappingsEntry 1 }

ptPCEIS41BillingIDMappingsPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEIS41BillingIDMappingsEntry 242 }

ptPCEIS41BillingIDMappingsParentOID OBJECT-TYPE
    SYNTAX          OBJECT IDENTIFIER
    MAX-ACCESS      read-create
    STATUS          current
    DESCRIPTION     
            "The OID of the parent object for this instance"
    ::= { ptPCEIS41BillingIDMappingsEntry 253 }

ptPCEIS41BillingIDMappingsRowStatus OBJECT-TYPE
    SYNTAX          RowStatus
    MAX-ACCESS      read-create
    STATUS          current
    DESCRIPTION     
            "The row status for the PCEIS41BillingIDMappings table"
    ::= { ptPCEIS41BillingIDMappingsEntry 254 }

ptPCEIS41BillingIDMappingsIndex OBJECT-TYPE
    SYNTAX          Integer32 (-2147483648..2147483647)
    MAX-ACCESS      not-accessible
    STATUS          current
    DESCRIPTION     
            "The row number for the PCEIS41BillingIDMappings table"
    ::= { ptPCEIS41BillingIDMappingsEntry 255 }

ptPCEIS41BillingIDMapping OBJECT IDENTIFIER
    ::= { ptPCEIS41BillingIDMappings 698 }

ptPCEIS41BillingIDMappingTable OBJECT-TYPE
    SYNTAX          SEQUENCE OF PtPCEIS41BillingIDMappingEntry
    MAX-ACCESS      not-accessible
    STATUS          current
    DESCRIPTION     
            "No description supplied in the proxy config file."
    ::= { ptPCEIS41BillingIDMapping 1 }

ptPCEIS41BillingIDMappingEntry OBJECT-TYPE
    SYNTAX          PtPCEIS41BillingIDMappingEntry
    MAX-ACCESS      not-accessible
    STATUS          current
    DESCRIPTION     
            "A sequence of PCEIS41BillingIDMapping attributes."
    INDEX           { ptConnGroupIndex, 
                      ptPCEIS41BillingIDMappingPCEDatabaseIndex, 
                      ptPCEIS41BillingIDMappingIS41BillingIDMappingsIndex, 
                      ptPCEIS41BillingIDMappingIndex }
    ::= { ptPCEIS41BillingIDMappingTable 1 }

PtPCEIS41BillingIDMappingEntry ::=
    SEQUENCE {
        ptPCEIS41BillingIDMappingName   DisplayString,
        ptPCEIS41BillingIDMappingMarketID Integer32,
        ptPCEIS41BillingIDMappingSwitchNumber     Integer32,
        ptPCEIS41BillingIDMappingIDNumberMinimum        Integer32,
        ptPCEIS41BillingIDMappingIDNumberMaximum        Integer32,
        ptPCEIS41BillingIDMappingPrivateNodeName        DisplayString,
        ptPCEIS41BillingIDMappingRecordID Integer32,
        ptPCEIS41BillingIDMappingPCEDatabaseIndex         Integer32,
        ptPCEIS41BillingIDMappingIS41BillingIDMappingsIndex                   Integer32,
        ptPCEIS41BillingIDMappingParentOID  OBJECT IDENTIFIER,
        ptPCEIS41BillingIDMappingRowStatus  RowStatus,
        ptPCEIS41BillingIDMappingIndex  Integer32
    }

ptPCEIS41BillingIDMappingName OBJECT-TYPE
    SYNTAX          DisplayString (SIZE(0..255))
    MAX-ACCESS      read-create
    STATUS          current
    DESCRIPTION     
            "IS41 Billing ID Mapping unique name."
    ::= { ptPCEIS41BillingIDMappingEntry 1 }

ptPCEIS41BillingIDMappingMarketID OBJECT-TYPE
    SYNTAX          Integer32 (0..65535)
    MAX-ACCESS      read-only
    STATUS          current
    DESCRIPTION     
            "IS41 Billing ID Market ID. \nThe 2 octet attribute is represented as an integer."
    ::= { ptPCEIS41BillingIDMappingEntry 2 }

ptPCEIS41BillingIDMappingSwitchNumber OBJECT-TYPE
    SYNTAX          Integer32 (0..255)
    MAX-ACCESS      read-only
    STATUS          current
    DESCRIPTION     
            "IS41 Billing ID Switch Number. \nThe 1 octet attribute is represented as an integer."
    ::= { ptPCEIS41BillingIDMappingEntry 3 }

ptPCEIS41BillingIDMappingIDNumberMinimum OBJECT-TYPE
    SYNTAX          Integer32 (-2147483648..2147483647)
    MAX-ACCESS      read-only
    STATUS          current
    DESCRIPTION     
            "IS41 Billing ID Identifier Number minimum value. \nThe 3 octet attribute is represented as an integer."
    ::= { ptPCEIS41BillingIDMappingEntry 4 }

ptPCEIS41BillingIDMappingIDNumberMaximum OBJECT-TYPE
    SYNTAX          Integer32 (-2147483648..2147483647)
    MAX-ACCESS      read-only
    STATUS          current
    DESCRIPTION     
            "IS41 Billing ID Identifier Number maximum value. \nThe 3 octet attribute is represented as an integer."
    ::= { ptPCEIS41BillingIDMappingEntry 5 }

ptPCEIS41BillingIDMappingPrivateNodeName OBJECT-TYPE
    SYNTAX          DisplayString (SIZE(0..255))
    MAX-ACCESS      read-create
    STATUS          current
    DESCRIPTION     
            "Public initiated TCAP query destination. \nThe node name must point to a Private Node record that already exists in that table."
    ::= { ptPCEIS41BillingIDMappingEntry 6 }

ptPCEIS41BillingIDMappingRecordID OBJECT-TYPE
    SYNTAX          Integer32 (-2147483648..2147483647)
    MAX-ACCESS      read-only
    STATUS          current
    DESCRIPTION     
            "IS41 Billing ID Mapping Record ID. Read-only and hidden. \nRequired for UI Orb synchronization during distribution."
    ::= { ptPCEIS41BillingIDMappingEntry 7 }

ptPCEIS41BillingIDMappingPCEDatabaseIndex OBJECT-TYPE
    SYNTAX          Integer32 (-2147483648..2147483647)
    MAX-ACCESS      not-accessible
    STATUS          current
    DESCRIPTION     
            "This is the index of the parent type for this object.
             This parent type is PCEDatabase."
    ::= { ptPCEIS41BillingIDMappingEntry 242 }

ptPCEIS41BillingIDMappingIS41BillingIDMappingsIndex OBJECT-TYPE
    SYNTAX          Integer32 (-2147483648..2147483647)
    MAX-ACCESS      not-accessible
    STATUS          current
    DESCRIPTION     
            "This is the index of the parent type for this object.
             This parent type is IS41BillingIDMappings."
    ::= { ptPCEIS41BillingIDMappingEntry 243 }

ptPCEIS41BillingIDMappingParentOID OBJECT-TYPE
    SYNTAX          OBJECT IDENTIFIER
    MAX-ACCESS      read-create
    STATUS          current
    DESCRIPTION     
            "The OID of the parent object for this instance"
    ::= { ptPCEIS41BillingIDMappingEntry 253 }

ptPCEIS41BillingIDMappingRowStatus OBJECT-TYPE
    SYNTAX          RowStatus
    MAX-ACCESS      read-create
    STATUS          current
    DESCRIPTION     
            "The row status for the PCEIS41BillingIDMapping table"
    ::= { ptPCEIS41BillingIDMappingEntry 254 }

ptPCEIS41BillingIDMappingIndex OBJECT-TYPE
    SYNTAX          Integer32 (-2147483648..2147483647)
    MAX-ACCESS      not-accessible
    STATUS          current
    DESCRIPTION     
            "The row number for the PCEIS41BillingIDMapping table"
    ::= { ptPCEIS41BillingIDMappingEntry 255 }

ptGWSTGWST OBJECT IDENTIFIER
    ::= { ptConnGroup 571 }

ptGWSTGWSTTable OBJECT-TYPE
    SYNTAX          SEQUENCE OF PtGWSTGWSTEntry
    MAX-ACCESS      not-accessible
    STATUS          current
    DESCRIPTION     
            "No description supplied in the proxy config file."
    ::= { ptGWSTGWST 1 }

ptGWSTGWSTEntry OBJECT-TYPE
    SYNTAX          PtGWSTGWSTEntry
    MAX-ACCESS      not-accessible
    STATUS          current
    DESCRIPTION     
            "A sequence of GWSTGWST attributes."
    INDEX           { ptConnGroupIndex, ptGWSTGWSTIndex }
    ::= { ptGWSTGWSTTable 1 }

PtGWSTGWSTEntry ::=
    SEQUENCE {
        ptGWSTGWSTParentOID             OBJECT IDENTIFIER,
        ptGWSTGWSTRowStatus             RowStatus,
        ptGWSTGWSTIndex                 Integer32
    }

ptGWSTGWSTParentOID OBJECT-TYPE
    SYNTAX          OBJECT IDENTIFIER
    MAX-ACCESS      read-create
    STATUS          current
    DESCRIPTION     
            "The OID of the parent object for this instance"
    ::= { ptGWSTGWSTEntry 253 }

ptGWSTGWSTRowStatus OBJECT-TYPE
    SYNTAX          RowStatus
    MAX-ACCESS      read-create
    STATUS          current
    DESCRIPTION     
            "The row status for the GWSTGWST table"
    ::= { ptGWSTGWSTEntry 254 }

ptGWSTGWSTIndex OBJECT-TYPE
    SYNTAX          Integer32 (-2147483648..2147483647)
    MAX-ACCESS      not-accessible
    STATUS          current
    DESCRIPTION     
            "The row number for the GWSTGWST table"
    ::= { ptGWSTGWSTEntry 255 }

ptGWSTGWSTConfiguration OBJECT IDENTIFIER
    ::= { ptConnGroup 572 }

ptGWSTGWSTConfigurationTable OBJECT-TYPE
    SYNTAX          SEQUENCE OF PtGWSTGWSTConfigurationEntry
    MAX-ACCESS      not-accessible
    STATUS          current
    DESCRIPTION     
            "No description supplied in the proxy config file."
    ::= { ptGWSTGWSTConfiguration 1 }

ptGWSTGWSTConfigurationEntry OBJECT-TYPE
    SYNTAX          PtGWSTGWSTConfigurationEntry
    MAX-ACCESS      not-accessible
    STATUS          current
    DESCRIPTION     
            "A sequence of GWSTGWSTConfiguration attributes."
    INDEX           { ptConnGroupIndex, ptGWSTGWSTConfigurationIndex }
    ::= { ptGWSTGWSTConfigurationTable 1 }

PtGWSTGWSTConfigurationEntry ::=
    SEQUENCE {
        ptGWSTGWSTConfigurationDefaultSS7Variant        INTEGER,
        ptGWSTGWSTConfigurationScreeningTestMode        INTEGER,
        ptGWSTGWSTConfigurationScreeningStatus      INTEGER,
        ptGWSTGWSTConfigurationActivePeerID   Integer32,
        ptGWSTGWSTConfigurationMaxTracingPerInterval            Integer32,
        ptGWSTGWSTConfigurationTracingInterval      INTEGER,
        ptGWSTGWSTConfigurationMaxReportingPerInterval              Integer32,
        ptGWSTGWSTConfigurationReportingInterval        INTEGER,
        ptGWSTGWSTConfigurationMaxSCRERRPerInterval           Integer32,
        ptGWSTGWSTConfigurationSCRERRInterval     INTEGER,
        ptGWSTGWSTConfigurationADAT     INTEGER,
        ptGWSTGWSTConfigurationBDAT     INTEGER,
        ptGWSTGWSTConfigurationADAN     INTEGER,
        ptGWSTGWSTConfigurationBDAN     INTEGER,
        ptGWSTGWSTConfigurationADBT     INTEGER,
        ptGWSTGWSTConfigurationBDBT     INTEGER,
        ptGWSTGWSTConfigurationADBN     INTEGER,
        ptGWSTGWSTConfigurationBDBN     INTEGER,
        ptGWSTGWSTConfigurationSILM     INTEGER,
        ptGWSTGWSTConfigurationSIRM     INTEGER,
        ptGWSTGWSTConfigurationSITM     INTEGER,
        ptGWSTGWSTConfigurationErrors   INTEGER,
        ptGWSTGWSTConfigurationSetupManagement      INTEGER,
        ptGWSTGWSTConfigurationExecutionTrace     INTEGER,
        ptGWSTGWSTConfigurationPeerManagement     INTEGER,
        ptGWSTGWSTConfigurationTableManagement      INTEGER,
        ptGWSTGWSTConfigurationFileManagement     INTEGER,
        ptGWSTGWSTConfigurationMaxScreeningsTotal         Integer32,
        ptGWSTGWSTConfigurationMaxScreeningsPerEPR          Integer32,
        ptGWSTGWSTConfigurationL4IncomingNotification             INTEGER,
        ptGWSTGWSTConfigurationTCERSegmented    INTEGER,
        ptGWSTGWSTConfigurationMaxRedirectsTotal        Integer32,
        ptGWSTGWSTConfigurationMaxRedirectsPerEPR         Integer32,
        ptGWSTGWSTConfigurationRedirectStatus     INTEGER,
        ptGWSTGWSTConfigurationAccountingStatus       INTEGER,
        ptGWSTGWSTConfigurationMaxAccountingsTotal          Integer32,
        ptGWSTGWSTConfigurationMaxAccountingsPerLS          Integer32,
        ptGWSTGWSTConfigurationLDLDebugLevel    Integer32,
        ptGWSTGWSTConfigurationLDLSCTPDebugLevel        Integer32,
        ptGWSTGWSTConfigurationDefaultPCDisplay       DisplayString,
        ptGWSTGWSTConfigurationDefaultPCRouting       DisplayString,
        ptGWSTGWSTConfigurationAccountingSCCPServices             INTEGER,
        ptGWSTGWSTConfigurationMaxStatisticsTotal         Integer32,
        ptGWSTGWSTConfigurationMaxStatisticsPerLS         Integer32,
        ptGWSTGWSTConfigurationStatisticsDataOnly         INTEGER,
        ptGWSTGWSTConfigurationTCAPOpCodeOptional         INTEGER,
        ptGWSTGWSTConfigurationActions  INTEGER,
        ptGWSTGWSTConfigurationParentOID OBJECT IDENTIFIER,
        ptGWSTGWSTConfigurationRowStatus RowStatus,
        ptGWSTGWSTConfigurationIndex    Integer32
    }

ptGWSTGWSTConfigurationDefaultSS7Variant OBJECT-TYPE
    SYNTAX          INTEGER { ansi(1), itu(2) }
    MAX-ACCESS      read-create
    STATUS          current
    DESCRIPTION     
            "Obsolete. Default SS7 Variant as used by new screening records."
    ::= { ptGWSTGWSTConfigurationEntry 1 }

ptGWSTGWSTConfigurationScreeningTestMode OBJECT-TYPE
    SYNTAX          INTEGER { disabled(0), enabled(1) }
    MAX-ACCESS      read-only
    STATUS          current
    DESCRIPTION     
            "Screening Test Mode (ENABLED/DISABLED). \nIf Screening Test Mode is enabled, no messages will be discarded due to gateway screening."
    ::= { ptGWSTGWSTConfigurationEntry 2 }

ptGWSTGWSTConfigurationScreeningStatus OBJECT-TYPE
    SYNTAX          INTEGER { active(0), unlicensed(1) }
    MAX-ACCESS      read-only
    STATUS          current
    DESCRIPTION     
            "Gateway screening status (ACTIVE/UNLICENSED). \nIf the gateway screening is not licensed, the message processing is considered to be in test mode."
    ::= { ptGWSTGWSTConfigurationEntry 3 }

ptGWSTGWSTConfigurationActivePeerID OBJECT-TYPE
    SYNTAX          Integer32 (-2147483648..2147483647)
    MAX-ACCESS      read-only
    STATUS          current
    DESCRIPTION     
            "The active peer identifier as defined by the GWST LDL file. \nThe GWST default LDL file (gws_ldl.conf) is located in the /opt/cpu_ss7gw/current/data directory."
    ::= { ptGWSTGWSTConfigurationEntry 4 }

ptGWSTGWSTConfigurationMaxTracingPerInterval OBJECT-TYPE
    SYNTAX          Integer32 (0..99)
    MAX-ACCESS      read-create
    STATUS          current
    DESCRIPTION     
            "Maximum number of traced MSUs logged in the given interval. \nMSU Tracing, if enabled, assigns a unique identifier to incoming MSUs matching a screening definition. This allows the user to trace the MSUs throughout the system's SS7 applications for debugging purposes. \nMaximum cannot exceed 99. Set to 0 to disable MSU Tracing."
    ::= { ptGWSTGWSTConfigurationEntry 5 }

ptGWSTGWSTConfigurationTracingInterval OBJECT-TYPE
    SYNTAX          INTEGER { five(300000), ten(600000), fifteen(900000), 
                        twenty(1200000), thirty(1800000) }
    MAX-ACCESS      read-create
    STATUS          current
    DESCRIPTION     
            "MSU Tracing logging interval [5, 10, 15, 20, or 30 minutes]."
    ::= { ptGWSTGWSTConfigurationEntry 6 }

ptGWSTGWSTConfigurationMaxReportingPerInterval OBJECT-TYPE
    SYNTAX          Integer32 (0..99)
    MAX-ACCESS      read-create
    STATUS          current
    DESCRIPTION     
            "Maximum number of reported MSUs logged in the given interval. \nThe reported MSUs are MSUs which failed screening and were discarded by the Gateway Screening. A hex dump of the discarded MSU is sent to the debug log including the screening table and EPR responsible for the discard. \nMaximum cannot exceed 99. Set to 0 to disable MSU reporting. \nGateway Screening can actually report up to double the maximum value of this attribute in a given interval if enough different screening table and EPR combinations are hit. This allows for more diversity in the reporting of discarded MSUs in correlation to the existing Gateway Screening configuration."
    ::= { ptGWSTGWSTConfigurationEntry 7 }

ptGWSTGWSTConfigurationReportingInterval OBJECT-TYPE
    SYNTAX          INTEGER { five(300000), ten(600000), fifteen(900000), 
                        twenty(1200000), thirty(1800000) }
    MAX-ACCESS      read-create
    STATUS          current
    DESCRIPTION     
            "MSU Reporting logging interval [5, 10, 15, 20, or 30 minutes]."
    ::= { ptGWSTGWSTConfigurationEntry 8 }

ptGWSTGWSTConfigurationMaxSCRERRPerInterval OBJECT-TYPE
    SYNTAX          Integer32 (0..99)
    MAX-ACCESS      read-create
    STATUS          current
    DESCRIPTION     
            "Maximum number of reported SCRERR logged in the given interval. \nThe SCRERR MSUs are MSUs which were either accepted or discarded based on a screening misconfiguration (see the SCRERR configuration for more details). A hex dump of the SCRERR MSU is sent to the debug log including the screening table responsible for the error. \nMaximum cannot exceed 99. Set to 0 to disable SCRERR reporting."
    ::= { ptGWSTGWSTConfigurationEntry 9 }

ptGWSTGWSTConfigurationSCRERRInterval OBJECT-TYPE
    SYNTAX          INTEGER { five(300000), ten(600000), fifteen(900000), 
                        twenty(1200000), thirty(1800000) }
    MAX-ACCESS      read-create
    STATUS          current
    DESCRIPTION     
            "SCRERR Reporting logging interval [5, 10, 15, 20, or 30 minutes]."
    ::= { ptGWSTGWSTConfigurationEntry 10 }

ptGWSTGWSTConfigurationADAT OBJECT-TYPE
    SYNTAX          INTEGER { disabled(0), enabled(1) }
    MAX-ACCESS      read-create
    STATUS          current
    DESCRIPTION     
            "ADAT when the screening process attempts to accept an MTP-T&M message whose RL DPC did not match the GSTP own unique PC, and matched an Allowed DPC entity. Default screening action is block. As per GR-778-CORE Issue 1."
    ::= { ptGWSTGWSTConfigurationEntry 11 }

ptGWSTGWSTConfigurationBDAT OBJECT-TYPE
    SYNTAX          INTEGER { disabled(0), enabled(1) }
    MAX-ACCESS      read-create
    STATUS          current
    DESCRIPTION     
            "BDAT when the screening process attempts to accept an MTP-T&M message whose RL DPC did not match the GSTP own unique PC and failed to match a Blocked DPC entity. Default screening action is block. As per GR-778-CORE Issue 1."
    ::= { ptGWSTGWSTConfigurationEntry 12 }

ptGWSTGWSTConfigurationADAN OBJECT-TYPE
    SYNTAX          INTEGER { disabled(0), enabled(1) }
    MAX-ACCESS      read-create
    STATUS          current
    DESCRIPTION     
            "ADAN when the screening process attempts to accept an MTPNM message whose RL DPC matched an Allowed DPC entry other than the GSTP own unique PC or it mate PC. Default screening action is block. As per GR-778-CORE Issue 1."
    ::= { ptGWSTGWSTConfigurationEntry 13 }

ptGWSTGWSTConfigurationBDAN OBJECT-TYPE
    SYNTAX          INTEGER { disabled(0), enabled(1) }
    MAX-ACCESS      read-create
    STATUS          current
    DESCRIPTION     
            "BDAN when the screening process attempts to accept an MTPNM message whose RL DPC was other than that of the GSTP unique PC or that of its mate, but failed to match a Blocked DPC entry. Default screening action is block. As per GR-778-CORE Issue 1."
    ::= { ptGWSTGWSTConfigurationEntry 14 }

ptGWSTGWSTConfigurationADBT OBJECT-TYPE
    SYNTAX          INTEGER { disabled(0), enabled(1) }
    MAX-ACCESS      read-create
    STATUS          current
    DESCRIPTION     
            "ADBT when the screening process attempts to reject (block) a MTP-T&M message that failed to match an Allowed DPC but matched the GSTPs own unique PC. As per GR-778-CORE Issue 1."
    ::= { ptGWSTGWSTConfigurationEntry 15 }

ptGWSTGWSTConfigurationBDBT OBJECT-TYPE
    SYNTAX          INTEGER { disabled(0), enabled(1) }
    MAX-ACCESS      read-create
    STATUS          current
    DESCRIPTION     
            "BDBT when the screening process attempts to reject (block) a MTP-T&M message that matched a Blocked DPC entry equal to the GSTP s unique PC. As per GR-778-CORE Issue 1."
    ::= { ptGWSTGWSTConfigurationEntry 16 }

ptGWSTGWSTConfigurationADBN OBJECT-TYPE
    SYNTAX          INTEGER { disabled(0), enabled(1) }
    MAX-ACCESS      read-create
    STATUS          current
    DESCRIPTION     
            "ADBN when the screening process attempts to reject (block) an MTP-NM message that failed to match an Allowed DPC but matched either the GSTP s own unique PC or its mate s PC. As per GR-778-CORE Issue 1."
    ::= { ptGWSTGWSTConfigurationEntry 17 }

ptGWSTGWSTConfigurationBDBN OBJECT-TYPE
    SYNTAX          INTEGER { disabled(0), enabled(1) }
    MAX-ACCESS      read-create
    STATUS          current
    DESCRIPTION     
            "BDBN when the screening process attempts to reject (block) an MTP-NM message that matched a Blocked DPC entry equal to either the GSTP s unique PC or its mate s PC. As per GR-778-CORE Issue 1."
    ::= { ptGWSTGWSTConfigurationEntry 18 }

ptGWSTGWSTConfigurationSILM OBJECT-TYPE
    SYNTAX          INTEGER { disabled(0), enabled(1) }
    MAX-ACCESS      read-create
    STATUS          current
    DESCRIPTION     
            "SILM when the screening process attempts to reject a signaling link management or signaling traffic management message whose SIO-H0-H1 subfields did not match an Allowed SIO entity, but along with its RL OPC indicates a valid Changeover, Emergency Changeover, Link Inhibit, or Signaling Data Link Connection MTP-NM message from an adjacent signaling node. As per GR-778-CORE Issue 1."
    ::= { ptGWSTGWSTConfigurationEntry 19 }

ptGWSTGWSTConfigurationSIRM OBJECT-TYPE
    SYNTAX          INTEGER { disabled(0), enabled(1) }
    MAX-ACCESS      read-create
    STATUS          current
    DESCRIPTION     
            "SIRM when the screening process attempts to reject a signaling route management message or Traffic Restart message whose SIO-H0-H1 subfields did not match an Allowed SIO entity, but along with its RL OPC indicate a valid Transfer, Route-Set Test, or Traffic Restart MTPNM message received from an adjacent GSTP. As per GR-778-CORE Issue 1."
    ::= { ptGWSTGWSTConfigurationEntry 20 }

ptGWSTGWSTConfigurationSITM OBJECT-TYPE
    SYNTAX          INTEGER { disabled(0), enabled(1) }
    MAX-ACCESS      read-create
    STATUS          current
    DESCRIPTION     
            "SITM when the screening process attempts to reject an SLTM or SLTA message whose SIO-H0-H1 subfields did not match an Allowed SIO entity, but along with its RL OPC indicate a valid message of that type from an adjacent signaling node. As per GR-778-CORE Issue 1."
    ::= { ptGWSTGWSTConfigurationEntry 21 }

ptGWSTGWSTConfigurationErrors OBJECT-TYPE
    SYNTAX          INTEGER { notLogged(0), logged(1) }
    MAX-ACCESS      read-create
    STATUS          current
    DESCRIPTION     
            "Enable or disable debug logging of the GWST errors; \nshould be logged for production systems."
    ::= { ptGWSTGWSTConfigurationEntry 22 }

ptGWSTGWSTConfigurationSetupManagement OBJECT-TYPE
    SYNTAX          INTEGER { notLogged(0), logged(1) }
    MAX-ACCESS      read-create
    STATUS          current
    DESCRIPTION     
            "Enable or disable debug logging of setup management; \nshould be logged for production systems."
    ::= { ptGWSTGWSTConfigurationEntry 23 }

ptGWSTGWSTConfigurationExecutionTrace OBJECT-TYPE
    SYNTAX          INTEGER { notLogged(0), logged(1) }
    MAX-ACCESS      read-create
    STATUS          current
    DESCRIPTION     
            "Enable or disable debug logging of the execution trace; \nshould not be logged for production systems."
    ::= { ptGWSTGWSTConfigurationEntry 24 }

ptGWSTGWSTConfigurationPeerManagement OBJECT-TYPE
    SYNTAX          INTEGER { notLogged(0), logged(1) }
    MAX-ACCESS      read-create
    STATUS          current
    DESCRIPTION     
            "Enable or disable debug logging of peer management; \nmust not be logged for production systems."
    ::= { ptGWSTGWSTConfigurationEntry 25 }

ptGWSTGWSTConfigurationTableManagement OBJECT-TYPE
    SYNTAX          INTEGER { notLogged(0), logged(1) }
    MAX-ACCESS      read-create
    STATUS          current
    DESCRIPTION     
            "Enable or disable debug logging of table management; \nmust not be logged for production systems."
    ::= { ptGWSTGWSTConfigurationEntry 26 }

ptGWSTGWSTConfigurationFileManagement OBJECT-TYPE
    SYNTAX          INTEGER { notLogged(0), logged(1) }
    MAX-ACCESS      read-create
    STATUS          current
    DESCRIPTION     
            "Enable or disable debug logging of file management; \nmust not be logged for production systems."
    ::= { ptGWSTGWSTConfigurationEntry 27 }

ptGWSTGWSTConfigurationMaxScreeningsTotal OBJECT-TYPE
    SYNTAX          Integer32 (-2147483648..2147483647)
    MAX-ACCESS      read-only
    STATUS          current
    DESCRIPTION     
            "Maximum number of screening records across all tables."
    ::= { ptGWSTGWSTConfigurationEntry 28 }

ptGWSTGWSTConfigurationMaxScreeningsPerEPR OBJECT-TYPE
    SYNTAX          Integer32 (-2147483648..2147483647)
    MAX-ACCESS      read-only
    STATUS          current
    DESCRIPTION     
            "Maximum number of screening records per EPR in a given table."
    ::= { ptGWSTGWSTConfigurationEntry 29 }

ptGWSTGWSTConfigurationL4IncomingNotification OBJECT-TYPE
    SYNTAX          INTEGER { disabled(0), enabled(1) }
    MAX-ACCESS      read-create
    STATUS          current
    DESCRIPTION     
            "Level 4 incoming information notification (ENABLED/DISABLED). \nIf L4 Incoming Notification is enabled, the GWS incoming NA and Linkset information is sent with every MSU up to registered L4 applications. Enabled if Gateway Accounting is licensed. Disabled for increased performance in allowed deployments. \nMust be enabled for L4 Converter SCCP Relay."
    ::= { ptGWSTGWSTConfigurationEntry 30 }

ptGWSTGWSTConfigurationTCERSegmented OBJECT-TYPE
    SYNTAX          INTEGER { discard(1), passThrough(2) }
    MAX-ACCESS      read-create
    STATUS          current
    DESCRIPTION     
            "Segmented MSU processing."
    ::= { ptGWSTGWSTConfigurationEntry 31 }

ptGWSTGWSTConfigurationMaxRedirectsTotal OBJECT-TYPE
    SYNTAX          Integer32 (-2147483648..2147483647)
    MAX-ACCESS      read-only
    STATUS          current
    DESCRIPTION     
            "Maximum number of redirect records across all tables."
    ::= { ptGWSTGWSTConfigurationEntry 32 }

ptGWSTGWSTConfigurationMaxRedirectsPerEPR OBJECT-TYPE
    SYNTAX          Integer32 (-2147483648..2147483647)
    MAX-ACCESS      read-only
    STATUS          current
    DESCRIPTION     
            "Maximum number of redirect records per EPR in a given table."
    ::= { ptGWSTGWSTConfigurationEntry 33 }

ptGWSTGWSTConfigurationRedirectStatus OBJECT-TYPE
    SYNTAX          INTEGER { active(0), unlicensed(1) }
    MAX-ACCESS      read-only
    STATUS          current
    DESCRIPTION     
            "Gateway redirect status (ACTIVE/UNLICENSED). \nIf the gateway redirect is not licensed, the message processing is considered to be a successful screening."
    ::= { ptGWSTGWSTConfigurationEntry 34 }

ptGWSTGWSTConfigurationAccountingStatus OBJECT-TYPE
    SYNTAX          INTEGER { active(0), unlicensed(1) }
    MAX-ACCESS      read-only
    STATUS          current
    DESCRIPTION     
            "Gateway accounting status (ACTIVE/UNLICENSED). \nIf the gateway accounting is not licensed, no accounting statistics are collected."
    ::= { ptGWSTGWSTConfigurationEntry 35 }

ptGWSTGWSTConfigurationMaxAccountingsTotal OBJECT-TYPE
    SYNTAX          Integer32 (-2147483648..2147483647)
    MAX-ACCESS      read-only
    STATUS          current
    DESCRIPTION     
            "Maximum number of accounting records across all tables."
    ::= { ptGWSTGWSTConfigurationEntry 36 }

ptGWSTGWSTConfigurationMaxAccountingsPerLS OBJECT-TYPE
    SYNTAX          Integer32 (-2147483648..2147483647)
    MAX-ACCESS      read-only
    STATUS          current
    DESCRIPTION     
            "Maximum number of accounting records per Linkset and direction in a given table. A Linkset can be defined as either (NA + APC) or (NA + AppID)"
    ::= { ptGWSTGWSTConfigurationEntry 37 }

ptGWSTGWSTConfigurationLDLDebugLevel OBJECT-TYPE
    SYNTAX          Integer32 (-2147483648..2147483647)
    MAX-ACCESS      read-create
    STATUS          current
    DESCRIPTION     
            "Set the LDL debug level for inter-process communication logging. \nMust not be modified unless instructed by Customer Support. \0 to 255."
    ::= { ptGWSTGWSTConfigurationEntry 38 }

ptGWSTGWSTConfigurationLDLSCTPDebugLevel OBJECT-TYPE
    SYNTAX          Integer32 (-2147483648..2147483647)
    MAX-ACCESS      read-create
    STATUS          current
    DESCRIPTION     
            "Set the LDL SCTP debug level for inter-process protocol logging. \nMust not be modified unless instructed by Customer Support. \n0 to 255."
    ::= { ptGWSTGWSTConfigurationEntry 39 }

ptGWSTGWSTConfigurationDefaultPCDisplay OBJECT-TYPE
    SYNTAX          DisplayString (SIZE(0..255))
    MAX-ACCESS      read-create
    STATUS          current
    DESCRIPTION     
            "Default PC routing format as used by Incoming LS and Redirect to PC. \nBoth the default PC Display and PC Routing must be bit size compatible. \nValid options are: 8.8.8, 3.8.3, ff-ff, 4.4.6, 5.4.7, 3.4.7, 4.3.7, 4.6.4, 6.4.4, 4.7.3, 5.4.5, and Decimal. Note that the dash delimiter is also accepted (i.e. 8-8-8)."
    ::= { ptGWSTGWSTConfigurationEntry 40 }

ptGWSTGWSTConfigurationDefaultPCRouting OBJECT-TYPE
    SYNTAX          DisplayString (SIZE(0..255))
    MAX-ACCESS      read-create
    STATUS          current
    DESCRIPTION     
            "Default PC routing format as used by the screening records. \nBoth the default PC Display and PC Routing must be bit size compatible. \nValid options are: 8.8.8, 3.8.3, 4.4.6, 5.4.7, 3.4.7, 4.3.7, 4.6.4, 6.4.4, 4.7.3, and 5.4.5 (dash delimiter also valid)."
    ::= { ptGWSTGWSTConfigurationEntry 41 }

ptGWSTGWSTConfigurationAccountingSCCPServices OBJECT-TYPE
    SYNTAX          INTEGER { disabled(0), enabled(1) }
    MAX-ACCESS      read-create
    STATUS          current
    DESCRIPTION     
            "Gateway accounting SCCP to include (X)UDTS service messages. \nThere is no protocol class in the (X)UDTS message so the Accounting SCCP Rule match is only possible for a record where the SCCP Class Range attribute is wildcarded. \nThis feature is DISABLED by default."
    ::= { ptGWSTGWSTConfigurationEntry 42 }

ptGWSTGWSTConfigurationMaxStatisticsTotal OBJECT-TYPE
    SYNTAX          Integer32 (-2147483648..2147483647)
    MAX-ACCESS      read-only
    STATUS          current
    DESCRIPTION     
            "Maximum number of statistics rules."
    ::= { ptGWSTGWSTConfigurationEntry 43 }

ptGWSTGWSTConfigurationMaxStatisticsPerLS OBJECT-TYPE
    SYNTAX          Integer32 (-2147483648..2147483647)
    MAX-ACCESS      read-only
    STATUS          current
    DESCRIPTION     
            "Maximum number of statistics rules per Linkset in a given table. A Linkset can be defined as either (NA + APC) or (NA + AppID)"
    ::= { ptGWSTGWSTConfigurationEntry 44 }

ptGWSTGWSTConfigurationStatisticsDataOnly OBJECT-TYPE
    SYNTAX          INTEGER { disabled(0), enabled(1) }
    MAX-ACCESS      read-create
    STATUS          current
    DESCRIPTION     
            "Gateway screening statistics for data messages (SI >=3) only. \nThe system-wide screening statistics instance includes all traffic. By enabling this feature, only data messages (SI >= 3) will be incremented which excludes SLT messages (SI 1 and 2) and SNM messages (SI 0). \nThis feature also impacts the UI-based statistics on a per Incoming Linkset and AppID basis. \nNote that the GWS Statistics Rules have an SI Range attribute to discriminate the MSUs directly. \nThis feature is DISABLED by default."
    ::= { ptGWSTGWSTConfigurationEntry 45 }

ptGWSTGWSTConfigurationTCAPOpCodeOptional OBJECT-TYPE
    SYNTAX          INTEGER { disabled(0), enabled(1) }
    MAX-ACCESS      read-create
    STATUS          current
    DESCRIPTION     
            "TCAP screening support for optional operation code. \nIn the Allowed TCAP Op Codes screening table, MSUs with an optional undefined TCAP operation code are successfully screened. The TCAP operation code is defined as a mandatory field for this screening table. \nBy enabling this feature, MSUs with an optional undefined TCAP operation code hitting the Allowed TCAP Op Codes screening table will match the NOT PRESENT or * wildcard value. If no match is found, the MSU will fail screening. \nBy supporting the screening criteria for TCAP messages with optional operation codes, Gateway Redirection can now be applied to those valid MSUs. \nOnce enabled, the feature can only be disabled is no Allowed TCAP Op Code objects have the NOT PRESENT value defined. \nThis feature is DISABLED by default."
    ::= { ptGWSTGWSTConfigurationEntry 46 }

ptGWSTGWSTConfigurationActions OBJECT-TYPE
    SYNTAX          INTEGER { enableScreening(1), disableScreening(2), 
                        resetTracing(3), resetReporting(4), 
                        resetSCRERR(5), restoreDebugDefaults(6) }
    MAX-ACCESS      read-create
    STATUS          current
    DESCRIPTION     
            "The OID of all possible actions for this instance"
    ::= { ptGWSTGWSTConfigurationEntry 252 }

ptGWSTGWSTConfigurationParentOID OBJECT-TYPE
    SYNTAX          OBJECT IDENTIFIER
    MAX-ACCESS      read-create
    STATUS          current
    DESCRIPTION     
            "The OID of the parent object for this instance"
    ::= { ptGWSTGWSTConfigurationEntry 253 }

ptGWSTGWSTConfigurationRowStatus OBJECT-TYPE
    SYNTAX          RowStatus
    MAX-ACCESS      read-create
    STATUS          current
    DESCRIPTION     
            "The row status for the GWSTGWSTConfiguration table"
    ::= { ptGWSTGWSTConfigurationEntry 254 }

ptGWSTGWSTConfigurationIndex OBJECT-TYPE
    SYNTAX          Integer32 (-2147483648..2147483647)
    MAX-ACCESS      not-accessible
    STATUS          current
    DESCRIPTION     
            "The row number for the GWSTGWSTConfiguration table"
    ::= { ptGWSTGWSTConfigurationEntry 255 }

ptGWSTGWSTTables OBJECT IDENTIFIER
    ::= { ptConnGroup 573 }

ptGWSTGWSTTablesTable OBJECT-TYPE
    SYNTAX          SEQUENCE OF PtGWSTGWSTTablesEntry
    MAX-ACCESS      not-accessible
    STATUS          current
    DESCRIPTION     
            "No description supplied in the proxy config file."
    ::= { ptGWSTGWSTTables 1 }

ptGWSTGWSTTablesEntry OBJECT-TYPE
    SYNTAX          PtGWSTGWSTTablesEntry
    MAX-ACCESS      not-accessible
    STATUS          current
    DESCRIPTION     
            "A sequence of GWSTGWSTTables attributes."
    INDEX           { ptConnGroupIndex, ptGWSTGWSTTablesIndex }
    ::= { ptGWSTGWSTTablesTable 1 }

PtGWSTGWSTTablesEntry ::=
    SEQUENCE {
        ptGWSTGWSTTablesLastModified    DisplayString,
        ptGWSTGWSTTablesLastAction      INTEGER,
        ptGWSTGWSTTablesErrors          Integer32,
        ptGWSTGWSTTablesTotalIncomingLinksets     Integer32,
        ptGWSTGWSTTablesTotalAllowedOPCs Integer32,
        ptGWSTGWSTTablesTotalBlockedOPCs Integer32,
        ptGWSTGWSTTablesTotalAllowedSIOs Integer32,
        ptGWSTGWSTTablesTotalAllowedDPCs Integer32,
        ptGWSTGWSTTablesTotalBlockedDPCs Integer32,
        ptGWSTGWSTTablesTotalAffectedDestinations         Integer32,
        ptGWSTGWSTTablesTotalAllowedISUPMTs   Integer32,
        ptGWSTGWSTTablesTotalAllowedSCCPCLGPAs      Integer32,
        ptGWSTGWSTTablesTotalAllowedSCCPTTs   Integer32,
        ptGWSTGWSTTablesTotalAllowedSCCPCLDPAs      Integer32,
        ptGWSTGWSTTablesTotalAffectedSCCPMgmts      Integer32,
        ptGWSTGWSTTablesTotalAllowedTCAPOpCodes       Integer32,
        ptGWSTGWSTTablesTotalRedirectToAppIDs     Integer32,
        ptGWSTGWSTTablesTotalRedirectToPCs  Integer32,
        ptGWSTGWSTTablesTotalAccountingMTP3Rules        Integer32,
        ptGWSTGWSTTablesTotalAccountingSCCPRules        Integer32,
        ptGWSTGWSTTablesTotalIncomingAppIDs   Integer32,
        ptGWSTGWSTTablesTotalAllowedSCCPCLGDigitsPAs            Integer32,
        ptGWSTGWSTTablesTotalAllowedSCCPCLDDigitsPAs            Integer32,
        ptGWSTGWSTTablesTotalAllowedMAPIMSIs    Integer32,
        ptGWSTGWSTTablesTotalGWSStatisticsRules       Integer32,
        ptGWSTGWSTTablesTotalAllowedTUPMTs  Integer32,
        ptGWSTGWSTTablesActions         INTEGER,
        ptGWSTGWSTTablesParentOID       OBJECT IDENTIFIER,
        ptGWSTGWSTTablesRowStatus       RowStatus,
        ptGWSTGWSTTablesIndex           Integer32
    }

ptGWSTGWSTTablesLastModified OBJECT-TYPE
    SYNTAX          DisplayString (SIZE(0..255))
    MAX-ACCESS      read-only
    STATUS          current
    DESCRIPTION     
            "Date/Time of the last modification."
    ::= { ptGWSTGWSTTablesEntry 1 }

ptGWSTGWSTTablesLastAction OBJECT-TYPE
    SYNTAX          INTEGER { notApplicable(0), manual(1), addRecords(2), 
                        deleteRecords(3), replaceTables(4), 
                        exportTables(5), loadTables(6), purgeTables(7) }
    MAX-ACCESS      read-only
    STATUS          current
    DESCRIPTION     
            "Last action performed on the screening tables."
    ::= { ptGWSTGWSTTablesEntry 2 }

ptGWSTGWSTTablesErrors OBJECT-TYPE
    SYNTAX          Integer32 (-2147483648..2147483647)
    MAX-ACCESS      read-only
    STATUS          current
    DESCRIPTION     
            "Number of errors encountered during the last action."
    ::= { ptGWSTGWSTTablesEntry 3 }

ptGWSTGWSTTablesTotalIncomingLinksets OBJECT-TYPE
    SYNTAX          Integer32 (-2147483648..2147483647)
    MAX-ACCESS      read-only
    STATUS          current
    DESCRIPTION     
            "Number of Incoming Linksets."
    ::= { ptGWSTGWSTTablesEntry 4 }

ptGWSTGWSTTablesTotalAllowedOPCs OBJECT-TYPE
    SYNTAX          Integer32 (-2147483648..2147483647)
    MAX-ACCESS      read-only
    STATUS          current
    DESCRIPTION     
            "Number of Allowed OPCs."
    ::= { ptGWSTGWSTTablesEntry 5 }

ptGWSTGWSTTablesTotalBlockedOPCs OBJECT-TYPE
    SYNTAX          Integer32 (-2147483648..2147483647)
    MAX-ACCESS      read-only
    STATUS          current
    DESCRIPTION     
            "Number of Blocked OPCs."
    ::= { ptGWSTGWSTTablesEntry 6 }

ptGWSTGWSTTablesTotalAllowedSIOs OBJECT-TYPE
    SYNTAX          Integer32 (-2147483648..2147483647)
    MAX-ACCESS      read-only
    STATUS          current
    DESCRIPTION     
            "Number of Allowed SIOS."
    ::= { ptGWSTGWSTTablesEntry 7 }

ptGWSTGWSTTablesTotalAllowedDPCs OBJECT-TYPE
    SYNTAX          Integer32 (-2147483648..2147483647)
    MAX-ACCESS      read-only
    STATUS          current
    DESCRIPTION     
            "Number of Allowed DPCs."
    ::= { ptGWSTGWSTTablesEntry 8 }

ptGWSTGWSTTablesTotalBlockedDPCs OBJECT-TYPE
    SYNTAX          Integer32 (-2147483648..2147483647)
    MAX-ACCESS      read-only
    STATUS          current
    DESCRIPTION     
            "Number of Blocked DPCs."
    ::= { ptGWSTGWSTTablesEntry 9 }

ptGWSTGWSTTablesTotalAffectedDestinations OBJECT-TYPE
    SYNTAX          Integer32 (-2147483648..2147483647)
    MAX-ACCESS      read-only
    STATUS          current
    DESCRIPTION     
            "Number of Affected Destinations."
    ::= { ptGWSTGWSTTablesEntry 10 }

ptGWSTGWSTTablesTotalAllowedISUPMTs OBJECT-TYPE
    SYNTAX          Integer32 (-2147483648..2147483647)
    MAX-ACCESS      read-only
    STATUS          current
    DESCRIPTION     
            "Number of Allowed ISUP MTs."
    ::= { ptGWSTGWSTTablesEntry 11 }

ptGWSTGWSTTablesTotalAllowedSCCPCLGPAs OBJECT-TYPE
    SYNTAX          Integer32 (-2147483648..2147483647)
    MAX-ACCESS      read-only
    STATUS          current
    DESCRIPTION     
            "Number of Allowed SCCP CLG PAs."
    ::= { ptGWSTGWSTTablesEntry 12 }

ptGWSTGWSTTablesTotalAllowedSCCPTTs OBJECT-TYPE
    SYNTAX          Integer32 (-2147483648..2147483647)
    MAX-ACCESS      read-only
    STATUS          current
    DESCRIPTION     
            "Number of Allowed SCCP TTs."
    ::= { ptGWSTGWSTTablesEntry 13 }

ptGWSTGWSTTablesTotalAllowedSCCPCLDPAs OBJECT-TYPE
    SYNTAX          Integer32 (-2147483648..2147483647)
    MAX-ACCESS      read-only
    STATUS          current
    DESCRIPTION     
            "Number of Allowed SCCP CLD PAs."
    ::= { ptGWSTGWSTTablesEntry 14 }

ptGWSTGWSTTablesTotalAffectedSCCPMgmts OBJECT-TYPE
    SYNTAX          Integer32 (-2147483648..2147483647)
    MAX-ACCESS      read-only
    STATUS          current
    DESCRIPTION     
            "Number of Affected SCCP Mgmts."
    ::= { ptGWSTGWSTTablesEntry 15 }

ptGWSTGWSTTablesTotalAllowedTCAPOpCodes OBJECT-TYPE
    SYNTAX          Integer32 (-2147483648..2147483647)
    MAX-ACCESS      read-only
    STATUS          current
    DESCRIPTION     
            "Number of Allowed TCAP Op Codes."
    ::= { ptGWSTGWSTTablesEntry 16 }

ptGWSTGWSTTablesTotalRedirectToAppIDs OBJECT-TYPE
    SYNTAX          Integer32 (-2147483648..2147483647)
    MAX-ACCESS      read-only
    STATUS          current
    DESCRIPTION     
            "Number of Redirect to App IDs."
    ::= { ptGWSTGWSTTablesEntry 17 }

ptGWSTGWSTTablesTotalRedirectToPCs OBJECT-TYPE
    SYNTAX          Integer32 (-2147483648..2147483647)
    MAX-ACCESS      read-only
    STATUS          current
    DESCRIPTION     
            "Number of Redirect to PCs."
    ::= { ptGWSTGWSTTablesEntry 18 }

ptGWSTGWSTTablesTotalAccountingMTP3Rules OBJECT-TYPE
    SYNTAX          Integer32 (-2147483648..2147483647)
    MAX-ACCESS      read-only
    STATUS          current
    DESCRIPTION     
            "Number of Accounting MTP3 Rules."
    ::= { ptGWSTGWSTTablesEntry 19 }

ptGWSTGWSTTablesTotalAccountingSCCPRules OBJECT-TYPE
    SYNTAX          Integer32 (-2147483648..2147483647)
    MAX-ACCESS      read-only
    STATUS          current
    DESCRIPTION     
            "Number of Accounting SCCP Rules."
    ::= { ptGWSTGWSTTablesEntry 20 }

ptGWSTGWSTTablesTotalIncomingAppIDs OBJECT-TYPE
    SYNTAX          Integer32 (-2147483648..2147483647)
    MAX-ACCESS      read-only
    STATUS          current
    DESCRIPTION     
            "Number of Incoming App IDs."
    ::= { ptGWSTGWSTTablesEntry 21 }

ptGWSTGWSTTablesTotalAllowedSCCPCLGDigitsPAs OBJECT-TYPE
    SYNTAX          Integer32 (-2147483648..2147483647)
    MAX-ACCESS      read-only
    STATUS          current
    DESCRIPTION     
            "Number of Allowed SCCP CLG Digits PAs."
    ::= { ptGWSTGWSTTablesEntry 22 }

ptGWSTGWSTTablesTotalAllowedSCCPCLDDigitsPAs OBJECT-TYPE
    SYNTAX          Integer32 (-2147483648..2147483647)
    MAX-ACCESS      read-only
    STATUS          current
    DESCRIPTION     
            "Number of Allowed SCCP CLD Digits PAs."
    ::= { ptGWSTGWSTTablesEntry 23 }

ptGWSTGWSTTablesTotalAllowedMAPIMSIs OBJECT-TYPE
    SYNTAX          Integer32 (-2147483648..2147483647)
    MAX-ACCESS      read-only
    STATUS          current
    DESCRIPTION     
            "Number of Allowed MAP IMSIs."
    ::= { ptGWSTGWSTTablesEntry 24 }

ptGWSTGWSTTablesTotalGWSStatisticsRules OBJECT-TYPE
    SYNTAX          Integer32 (-2147483648..2147483647)
    MAX-ACCESS      read-only
    STATUS          current
    DESCRIPTION     
            "Number of GWS Statistics Rules."
    ::= { ptGWSTGWSTTablesEntry 25 }

ptGWSTGWSTTablesTotalAllowedTUPMTs OBJECT-TYPE
    SYNTAX          Integer32 (-2147483648..2147483647)
    MAX-ACCESS      read-only
    STATUS          current
    DESCRIPTION     
            "Number of Allowed TUP MTs."
    ::= { ptGWSTGWSTTablesEntry 26 }

ptGWSTGWSTTablesActions OBJECT-TYPE
    SYNTAX          INTEGER { clearMSUTracing(1), clearTestMode(2) }
    MAX-ACCESS      read-create
    STATUS          current
    DESCRIPTION     
            "The OID of all possible actions for this instance"
    ::= { ptGWSTGWSTTablesEntry 252 }

ptGWSTGWSTTablesParentOID OBJECT-TYPE
    SYNTAX          OBJECT IDENTIFIER
    MAX-ACCESS      read-create
    STATUS          current
    DESCRIPTION     
            "The OID of the parent object for this instance"
    ::= { ptGWSTGWSTTablesEntry 253 }

ptGWSTGWSTTablesRowStatus OBJECT-TYPE
    SYNTAX          RowStatus
    MAX-ACCESS      read-create
    STATUS          current
    DESCRIPTION     
            "The row status for the GWSTGWSTTables table"
    ::= { ptGWSTGWSTTablesEntry 254 }

ptGWSTGWSTTablesIndex OBJECT-TYPE
    SYNTAX          Integer32 (-2147483648..2147483647)
    MAX-ACCESS      not-accessible
    STATUS          current
    DESCRIPTION     
            "The row number for the GWSTGWSTTables table"
    ::= { ptGWSTGWSTTablesEntry 255 }

ptGWSTBatchOperations OBJECT IDENTIFIER
    ::= { ptGWSTGWSTTables 598 }

ptGWSTBatchOperationsTable OBJECT-TYPE
    SYNTAX          SEQUENCE OF PtGWSTBatchOperationsEntry
    MAX-ACCESS      not-accessible
    STATUS          current
    DESCRIPTION     
            "No description supplied in the proxy config file."
    ::= { ptGWSTBatchOperations 1 }

ptGWSTBatchOperationsEntry OBJECT-TYPE
    SYNTAX          PtGWSTBatchOperationsEntry
    MAX-ACCESS      not-accessible
    STATUS          current
    DESCRIPTION     
            "A sequence of GWSTBatchOperations attributes."
    INDEX           { ptConnGroupIndex, 
                      ptGWSTBatchOperationsGWSTTablesIndex, 
                      ptGWSTBatchOperationsIndex }
    ::= { ptGWSTBatchOperationsTable 1 }

PtGWSTBatchOperationsEntry ::=
    SEQUENCE {
        ptGWSTBatchOperationsMaxPerInterval   Integer32,
        ptGWSTBatchOperationsBatchInterval  Integer32,
        ptGWSTBatchOperationsGWSTTablesIndex    Integer32,
        ptGWSTBatchOperationsActions    INTEGER,
        ptGWSTBatchOperationsParentOID  OBJECT IDENTIFIER,
        ptGWSTBatchOperationsRowStatus  RowStatus,
        ptGWSTBatchOperationsIndex      Integer32
    }

ptGWSTBatchOperationsMaxPerInterval OBJECT-TYPE
    SYNTAX          Integer32 (1..100)
    MAX-ACCESS      read-create
    STATUS          current
    DESCRIPTION     
            "Maximum number of records processed in each batch operation interval."
    ::= { ptGWSTBatchOperationsEntry 1 }

ptGWSTBatchOperationsBatchInterval OBJECT-TYPE
    SYNTAX          Integer32 (1..60000)
    MAX-ACCESS      read-create
    STATUS          current
    DESCRIPTION     
            "Interval at which at most Max Per Interval batch operations records are processed (in milliseconds)."
    ::= { ptGWSTBatchOperationsEntry 2 }

ptGWSTBatchOperationsGWSTTablesIndex OBJECT-TYPE
    SYNTAX          Integer32 (-2147483648..2147483647)
    MAX-ACCESS      not-accessible
    STATUS          current
    DESCRIPTION     
            "This is the index of the parent type for this object.
             This parent type is GWSTTables."
    ::= { ptGWSTBatchOperationsEntry 242 }

ptGWSTBatchOperationsActions OBJECT-TYPE
    SYNTAX          INTEGER { addRecords(1), deleteRecords(2), 
                        replaceTables(3), exportTables(4), 
                        purgeTables(5) }
    MAX-ACCESS      read-create
    STATUS          current
    DESCRIPTION     
            "The OID of all possible actions for this instance"
    ::= { ptGWSTBatchOperationsEntry 252 }

ptGWSTBatchOperationsParentOID OBJECT-TYPE
    SYNTAX          OBJECT IDENTIFIER
    MAX-ACCESS      read-create
    STATUS          current
    DESCRIPTION     
            "The OID of the parent object for this instance"
    ::= { ptGWSTBatchOperationsEntry 253 }

ptGWSTBatchOperationsRowStatus OBJECT-TYPE
    SYNTAX          RowStatus
    MAX-ACCESS      read-create
    STATUS          current
    DESCRIPTION     
            "The row status for the GWSTBatchOperations table"
    ::= { ptGWSTBatchOperationsEntry 254 }

ptGWSTBatchOperationsIndex OBJECT-TYPE
    SYNTAX          Integer32 (-2147483648..2147483647)
    MAX-ACCESS      not-accessible
    STATUS          current
    DESCRIPTION     
            "The row number for the GWSTBatchOperations table"
    ::= { ptGWSTBatchOperationsEntry 255 }

ptGWSTGWSSearchUtility OBJECT IDENTIFIER
    ::= { ptGWSTGWSTTables 1015 }

ptGWSTGWSSearchUtilityTable OBJECT-TYPE
    SYNTAX          SEQUENCE OF PtGWSTGWSSearchUtilityEntry
    MAX-ACCESS      not-accessible
    STATUS          current
    DESCRIPTION     
            "No description supplied in the proxy config file."
    ::= { ptGWSTGWSSearchUtility 1 }

ptGWSTGWSSearchUtilityEntry OBJECT-TYPE
    SYNTAX          PtGWSTGWSSearchUtilityEntry
    MAX-ACCESS      not-accessible
    STATUS          current
    DESCRIPTION     
            "A sequence of GWSTGWSSearchUtility attributes."
    INDEX           { ptConnGroupIndex, 
                      ptGWSTGWSSearchUtilityGWSTTablesIndex, 
                      ptGWSTGWSSearchUtilityIndex }
    ::= { ptGWSTGWSSearchUtilityTable 1 }

PtGWSTGWSSearchUtilityEntry ::=
    SEQUENCE {
        ptGWSTGWSSearchUtilityNA        Integer32,
        ptGWSTGWSSearchUtilityAdjacentPointCode       Integer32,
        ptGWSTGWSSearchUtilityApplicationID   DisplayString,
        ptGWSTGWSSearchUtilityOPC       Integer32,
        ptGWSTGWSSearchUtilityDPC       Integer32,
        ptGWSTGWSSearchUtilitySIO       Integer32,
        ptGWSTGWSSearchUtilityMessageType Integer32,
        ptGWSTGWSSearchUtilityAffectedPC Integer32,
        ptGWSTGWSSearchUtilitySCCPClass INTEGER,
        ptGWSTGWSSearchUtilitySCCPCLGPC Integer32,
        ptGWSTGWSSearchUtilitySCCPCLGSSN INTEGER,
        ptGWSTGWSSearchUtilitySCCPCLGDigits   DisplayString,
        ptGWSTGWSSearchUtilitySCCPCLDRI INTEGER,
        ptGWSTGWSSearchUtilitySCCPCLDTT INTEGER,
        ptGWSTGWSSearchUtilitySCCPCLDSSN INTEGER,
        ptGWSTGWSSearchUtilitySCCPCLDDigits   DisplayString,
        ptGWSTGWSSearchUtilityTCAPMessageType     INTEGER,
        ptGWSTGWSSearchUtilityTCAPApplicationContext            DisplayString,
        ptGWSTGWSSearchUtilityTCAPComponentType       INTEGER,
        ptGWSTGWSSearchUtilityTCAPOpCodeFamily      INTEGER,
        ptGWSTGWSSearchUtilityTCAPOpCode INTEGER,
        ptGWSTGWSSearchUtilityDiagnosticMessage       DisplayString,
        ptGWSTGWSSearchUtilityResult    DisplayString,
        ptGWSTGWSSearchUtilityResultScreeningTestMode             INTEGER,
        ptGWSTGWSSearchUtilityResultMSUTracing      INTEGER,
        ptGWSTGWSSearchUtilityMAPIMSI   DisplayString,
        ptGWSTGWSSearchUtilityGWSTTablesIndex     Integer32,
        ptGWSTGWSSearchUtilityActions   INTEGER,
        ptGWSTGWSSearchUtilityParentOID OBJECT IDENTIFIER,
        ptGWSTGWSSearchUtilityRowStatus RowStatus,
        ptGWSTGWSSearchUtilityIndex     Integer32
    }

ptGWSTGWSSearchUtilityNA OBJECT-TYPE
    SYNTAX          Integer32 (-2147483648..2147483647)
    MAX-ACCESS      read-create
    STATUS          current
    DESCRIPTION     
            "Network Appearance for the Incoming Linkset or AppID."
    ::= { ptGWSTGWSSearchUtilityEntry 1 }

ptGWSTGWSSearchUtilityAdjacentPointCode OBJECT-TYPE
    SYNTAX          Integer32 (-2147483648..2147483647)
    MAX-ACCESS      read-create
    STATUS          current
    DESCRIPTION     
            "Adjacent Point Code used with the NA attribute to identify the Incoming Linkset."
    ::= { ptGWSTGWSSearchUtilityEntry 2 }

ptGWSTGWSSearchUtilityApplicationID OBJECT-TYPE
    SYNTAX          DisplayString (SIZE(0..255))
    MAX-ACCESS      read-create
    STATUS          current
    DESCRIPTION     
            "Application ID used with the NA attribute to identify the Incoming AppID."
    ::= { ptGWSTGWSSearchUtilityEntry 3 }

ptGWSTGWSSearchUtilityOPC OBJECT-TYPE
    SYNTAX          Integer32 (-2147483648..2147483647)
    MAX-ACCESS      read-create
    STATUS          current
    DESCRIPTION     
            "Originating Point Code of the MSU."
    ::= { ptGWSTGWSSearchUtilityEntry 4 }

ptGWSTGWSSearchUtilityDPC OBJECT-TYPE
    SYNTAX          Integer32 (-2147483648..2147483647)
    MAX-ACCESS      read-create
    STATUS          current
    DESCRIPTION     
            "Destination Point Code of the MSU."
    ::= { ptGWSTGWSSearchUtilityEntry 5 }

ptGWSTGWSSearchUtilitySIO OBJECT-TYPE
    SYNTAX          Integer32 (-2147483648..2147483647)
    MAX-ACCESS      read-create
    STATUS          current
    DESCRIPTION     
            "Service Information Octet of the MSU (0 to 255). \n Encodes the Network Indicator (NI), Priority (PRI), and Signaling Indicator (SI) into a decimal value. \n | NI | PRI | SI | \n | 8 7 | 6 5 | 4 3 2 1 |"
    ::= { ptGWSTGWSSearchUtilityEntry 6 }

ptGWSTGWSSearchUtilityMessageType OBJECT-TYPE
    SYNTAX          Integer32 (-2147483648..2147483647)
    MAX-ACCESS      read-create
    STATUS          current
    DESCRIPTION     
            "Message type of the MSU based on SI (0 to 255). \n For SI 0, set to the H1H0 value (Decimal). \n For SI 3, set to the SCCP message type: 9 (UDT), 10 (UDTS), 17 (XUDT) or 18 (XUDTS). \n For SI 4, set to the TUP message type: 17 (IAM), 49 (SAM), etc... \n For SI 5, set to the ISUP message type: 1 (IAM), 2 (SAM), etc..."
    ::= { ptGWSTGWSSearchUtilityEntry 7 }

ptGWSTGWSSearchUtilityAffectedPC OBJECT-TYPE
    SYNTAX          Integer32 (-2147483648..2147483647)
    MAX-ACCESS      read-create
    STATUS          current
    DESCRIPTION     
            "Affected Point Code of the MSU (optional). \n For SI != 0, set to UNSET as not applicable. \n For SI = 0, applicable to only certain H1H0 message types else set to UNSET."
    ::= { ptGWSTGWSSearchUtilityEntry 8 }

ptGWSTGWSSearchUtilitySCCPClass OBJECT-TYPE
    SYNTAX          INTEGER { class0(0), class1(1), class2(2), class3(3), 
                        notPresent(4), none(5) }
    MAX-ACCESS      read-create
    STATUS          current
    DESCRIPTION     
            "SCCP Protocol Class of the MSU (optional). \n Set to CLASS 0, CLASS 1, CLASS 2, CLASS 3, NOT PRESENT as required else set to NONE when not applicable. \n Only applicable and mandatory for SI 3."
    ::= { ptGWSTGWSSearchUtilityEntry 9 }

ptGWSTGWSSearchUtilitySCCPCLGPC OBJECT-TYPE
    SYNTAX          Integer32 (-2147483648..2147483647)
    MAX-ACCESS      read-create
    STATUS          current
    DESCRIPTION     
            "SCCP Calling Point Code of the MSU (optional) \n Set to UNSET if undefined or not applicable. \n Only applicable for SI 3."
    ::= { ptGWSTGWSSearchUtilityEntry 10 }

ptGWSTGWSSearchUtilitySCCPCLGSSN OBJECT-TYPE
    SYNTAX          INTEGER { none(256) }
    MAX-ACCESS      read-create
    STATUS          current
    DESCRIPTION     
            "SCCP Calling SSN of the MSU (0 to 255, NONE (256)) (optional). \n Set to NONE if undefined or not applicable. \n Only applicable for SI 3."
    ::= { ptGWSTGWSSearchUtilityEntry 11 }

ptGWSTGWSSearchUtilitySCCPCLGDigits OBJECT-TYPE
    SYNTAX          DisplayString (SIZE(0..255))
    MAX-ACCESS      read-create
    STATUS          current
    DESCRIPTION     
            "SCCP Calling Digits of the MSU (optional). \n Set to an empty string if undefined or not applicable. \n Accepts up to 32 digits with a-e/A-E hexadecimal. \n Only applicable for SI 3."
    ::= { ptGWSTGWSSearchUtilityEntry 12 }

ptGWSTGWSSearchUtilitySCCPCLDRI OBJECT-TYPE
    SYNTAX          INTEGER { none(2) }
    MAX-ACCESS      read-create
    STATUS          current
    DESCRIPTION     
            "SCCP CLD Routing Indicator of the MSU (0, 1, NONE (2)) (optional). \n Only applicable for SI 3."
    ::= { ptGWSTGWSSearchUtilityEntry 13 }

ptGWSTGWSSearchUtilitySCCPCLDTT OBJECT-TYPE
    SYNTAX          INTEGER { none(256) }
    MAX-ACCESS      read-create
    STATUS          current
    DESCRIPTION     
            "SCCP Called Translation Type of the MSU (o to 255, NONE (256)) (optional). \n Set to NONE if undefined or not applicable. \n Only applicable for SI 3."
    ::= { ptGWSTGWSSearchUtilityEntry 14 }

ptGWSTGWSSearchUtilitySCCPCLDSSN OBJECT-TYPE
    SYNTAX          INTEGER { none(256) }
    MAX-ACCESS      read-create
    STATUS          current
    DESCRIPTION     
            "SCCP Called SSN of the MSU (0 to 255, NONE (256)) (optional). \n Set to NONE if undefined or not applicable. \n Only applicable for SI 3."
    ::= { ptGWSTGWSSearchUtilityEntry 15 }

ptGWSTGWSSearchUtilitySCCPCLDDigits OBJECT-TYPE
    SYNTAX          DisplayString (SIZE(0..255))
    MAX-ACCESS      read-create
    STATUS          current
    DESCRIPTION     
            "SCCP Called Digits of the MSU (optional). \n Set to an empty string if undefined or not applicable. \n Accepts up to 32 digits with a-e/A-E hexadecimal. \n Only applicable for SI 3."
    ::= { ptGWSTGWSSearchUtilityEntry 16 }

ptGWSTGWSSearchUtilityTCAPMessageType OBJECT-TYPE
    SYNTAX          INTEGER { none(255), ituUnidirectional(97), 
                        ituBegin(98), ituEnd(100), ituContinue(101), 
                        ituAbort(103), ansiUnidirectional(225), 
                        ansiQueryWp(226), ansiQueryWop(227), 
                        ansiResponse(228), ansiConversationWp(229), 
                        ansiConversationWop(230), ansiAbort(246) }
    MAX-ACCESS      read-create
    STATUS          current
    DESCRIPTION     
            "TCAP Message Type of the MSU (optional). \n TCAP variant dependent. \n Only applicable for SI 3."
    ::= { ptGWSTGWSSearchUtilityEntry 17 }

ptGWSTGWSSearchUtilityTCAPApplicationContext OBJECT-TYPE
    SYNTAX          DisplayString (SIZE(0..255))
    MAX-ACCESS      read-create
    STATUS          current
    DESCRIPTION     
            "TCAP Application Context of the MSU (optional). \n This attribute may contain a combination of positive integers separated by a single period. Two or more periods in succession are invalid. The maximum number of characters the attribute may contain is 31. \n The TCAP Application Context can be either an Object Identifier (OID) or an integer (ANSI only). \n Set to an empty string if undefined or not applicable. \n Only applicable for SI 3."
    ::= { ptGWSTGWSSearchUtilityEntry 18 }

ptGWSTGWSSearchUtilityTCAPComponentType OBJECT-TYPE
    SYNTAX          INTEGER { none(255), ituInvoke(161), 
                        ituReturnResultLast(162), ituReturnError(163), 
                        ituReject(164), ituReturnResultNotLast(167), 
                        ansiInvokeLast(233), ansiReturnResultLast(234), 
                        ansiReturnError(235), ansiReject(236), 
                        ansiInvokeNotLast(237), 
                        ansiReturnResultNotLast(238) }
    MAX-ACCESS      read-create
    STATUS          current
    DESCRIPTION     
            "TCAP Component Type of the MSU (optional). \n TCAP Variant dependent. \n Only applicable for SI 3."
    ::= { ptGWSTGWSSearchUtilityEntry 19 }

ptGWSTGWSSearchUtilityTCAPOpCodeFamily OBJECT-TYPE
    SYNTAX          INTEGER { none(256) }
    MAX-ACCESS      read-create
    STATUS          current
    DESCRIPTION     
            "TCAP Operation Code Family of the MSU (optional, ANSI only). \n Set to NONE if undefined or not applicable (0 to 255, NONE (256)). \n Attribute is ignored in ITU TCAP Variant. \n Only applicable for SI 3."
    ::= { ptGWSTGWSSearchUtilityEntry 20 }

ptGWSTGWSSearchUtilityTCAPOpCode OBJECT-TYPE
    SYNTAX          INTEGER { none(256) }
    MAX-ACCESS      read-create
    STATUS          current
    DESCRIPTION     
            "TCAP Operation Code of the MSU (0 to 255, NONE (256)) (optional). \n Set to NONE if undefined or not applicable. \n Only applicable for SI 3."
    ::= { ptGWSTGWSSearchUtilityEntry 21 }

ptGWSTGWSSearchUtilityDiagnosticMessage OBJECT-TYPE
    SYNTAX          DisplayString (SIZE(0..255))
    MAX-ACCESS      read-only
    STATUS          current
    DESCRIPTION     
            "Search criteria is meant to be that of a valid MSU. However, if an error is detected in the search criteria, this message will alert the user to what is specifically wrong. If no errors are detected, then SUCCESS will be displayed"
    ::= { ptGWSTGWSSearchUtilityEntry 30 }

ptGWSTGWSSearchUtilityResult OBJECT-TYPE
    SYNTAX          DisplayString (SIZE(0..255))
    MAX-ACCESS      read-only
    STATUS          current
    DESCRIPTION     
            "Result of the GWS search (STOP, FAIL, IGNORE, REDIRECT, or POST GTT). \n If the search criteria contains an error as per the Diagnostic Message, the result is set to an empty string. \n For the REDIRECT and POST GTT values, the Table Name and EPR will also be provided."
    ::= { ptGWSTGWSSearchUtilityEntry 31 }

ptGWSTGWSSearchUtilityResultScreeningTestMode OBJECT-TYPE
    SYNTAX          INTEGER { undefined(-1), disabled(0), enabled(1), 
                        unlicensed(2) }
    MAX-ACCESS      read-only
    STATUS          current
    DESCRIPTION     
            "Screening Test Mode result (UNDEFINED/ENABLED/DISABLED)."
    ::= { ptGWSTGWSSearchUtilityEntry 32 }

ptGWSTGWSSearchUtilityResultMSUTracing OBJECT-TYPE
    SYNTAX          INTEGER { undefined(-1), disabled(0), enabled(1), 
                        unlicensed(2) }
    MAX-ACCESS      read-only
    STATUS          current
    DESCRIPTION     
            "MSU Tracign result (UNDEFINED/ENABLED/DISABLED)."
    ::= { ptGWSTGWSSearchUtilityEntry 33 }

ptGWSTGWSSearchUtilityMAPIMSI OBJECT-TYPE
    SYNTAX          DisplayString (SIZE(0..255))
    MAX-ACCESS      read-create
    STATUS          current
    DESCRIPTION     
            "MAP IMSI of the MSU (optional). \n Set to an empty string if undefined or not applicable. \n Accepts up to 18 digits with a-f/A-F hexadecimal. \n For certain TCAP operation codes, defined as the MSISDN or IMEI. \n Only applicable for ITU TCAP."
    ::= { ptGWSTGWSSearchUtilityEntry 34 }

ptGWSTGWSSearchUtilityGWSTTablesIndex OBJECT-TYPE
    SYNTAX          Integer32 (-2147483648..2147483647)
    MAX-ACCESS      not-accessible
    STATUS          current
    DESCRIPTION     
            "This is the index of the parent type for this object.
             This parent type is GWSTTables."
    ::= { ptGWSTGWSSearchUtilityEntry 242 }

ptGWSTGWSSearchUtilityActions OBJECT-TYPE
    SYNTAX          INTEGER { clearSearchCriteria(1), performSearch(2) }
    MAX-ACCESS      read-create
    STATUS          current
    DESCRIPTION     
            "The OID of all possible actions for this instance"
    ::= { ptGWSTGWSSearchUtilityEntry 252 }

ptGWSTGWSSearchUtilityParentOID OBJECT-TYPE
    SYNTAX          OBJECT IDENTIFIER
    MAX-ACCESS      read-create
    STATUS          current
    DESCRIPTION     
            "The OID of the parent object for this instance"
    ::= { ptGWSTGWSSearchUtilityEntry 253 }

ptGWSTGWSSearchUtilityRowStatus OBJECT-TYPE
    SYNTAX          RowStatus
    MAX-ACCESS      read-create
    STATUS          current
    DESCRIPTION     
            "The row status for the GWSTGWSSearchUtility table"
    ::= { ptGWSTGWSSearchUtilityEntry 254 }

ptGWSTGWSSearchUtilityIndex OBJECT-TYPE
    SYNTAX          Integer32 (-2147483648..2147483647)
    MAX-ACCESS      not-accessible
    STATUS          current
    DESCRIPTION     
            "The row number for the GWSTGWSSearchUtility table"
    ::= { ptGWSTGWSSearchUtilityEntry 255 }

ptGWSTScreeningStepResult OBJECT IDENTIFIER
    ::= { ptGWSTGWSSearchUtility 1016 }

ptGWSTScreeningStepResultTable OBJECT-TYPE
    SYNTAX          SEQUENCE OF PtGWSTScreeningStepResultEntry
    MAX-ACCESS      not-accessible
    STATUS          current
    DESCRIPTION     
            "No description supplied in the proxy config file."
    ::= { ptGWSTScreeningStepResult 1 }

ptGWSTScreeningStepResultEntry OBJECT-TYPE
    SYNTAX          PtGWSTScreeningStepResultEntry
    MAX-ACCESS      not-accessible
    STATUS          current
    DESCRIPTION     
            "A sequence of GWSTScreeningStepResult attributes."
    INDEX           { ptConnGroupIndex, 
                      ptGWSTScreeningStepResultGWSTTablesIndex, 
                      ptGWSTScreeningStepResultGWSSearchUtilityIndex, 
                      ptGWSTScreeningStepResultIndex }
    ::= { ptGWSTScreeningStepResultTable 1 }

PtGWSTScreeningStepResultEntry ::=
    SEQUENCE {
        ptGWSTScreeningStepResultSequenceNumber       Integer32,
        ptGWSTScreeningStepResultTableName  INTEGER,
        ptGWSTScreeningStepResultEPR    DisplayString,
        ptGWSTScreeningStepResultScreeningTestMode          INTEGER,
        ptGWSTScreeningStepResultMSUTracing   INTEGER,
        ptGWSTScreeningStepResultGWSTTablesIndex        Integer32,
        ptGWSTScreeningStepResultGWSSearchUtilityIndex              Integer32,
        ptGWSTScreeningStepResultParentOID  OBJECT IDENTIFIER,
        ptGWSTScreeningStepResultRowStatus  RowStatus,
        ptGWSTScreeningStepResultIndex  Integer32
    }

ptGWSTScreeningStepResultSequenceNumber OBJECT-TYPE
    SYNTAX          Integer32 (-2147483648..2147483647)
    MAX-ACCESS      read-only
    STATUS          current
    DESCRIPTION     
            "Screening Step Result Sequence Number"
    ::= { ptGWSTScreeningStepResultEntry 1 }

ptGWSTScreeningStepResultTableName OBJECT-TYPE
    SYNTAX          INTEGER { notApplicable(0), allowedMapImsis(1), 
                        allowedTcapOpCodes(2), allowedIsupMts(3), 
                        affectedSccpMgmts(4), allowedSccpClds(5), 
                        allowedSccpCldDigits(6), allowedSccpTts(7), 
                        allowedSccpClgDigits(8), allowedSccpClgs(9), 
                        affectedDestinations(10), blockedDpcs(11), 
                        allowedDpcs(12), allowedSios(13), 
                        blockedOpcs(14), allowedOpcs(15), 
                        incomingLinksets(16), incomingAppids(17), 
                        allowedTupMts(18), gwsEndTable(19), 
                        redirectModulo(100), redirectToAppIds(101), 
                        redirectToPcs(102), redirectEndTable(103), 
                        accountingModulo(200), accountingMtp3Rules(201), 
                        accountingSccpRules(202), 
                        accountingEndTable(203), statisticsModulo(250), 
                        gwsStatisticsRules(251), statisticsEndTable(252) }
    MAX-ACCESS      read-only
    STATUS          current
    DESCRIPTION     
            "Screening Step Result Table Name"
    ::= { ptGWSTScreeningStepResultEntry 2 }

ptGWSTScreeningStepResultEPR OBJECT-TYPE
    SYNTAX          DisplayString (SIZE(0..255))
    MAX-ACCESS      read-only
    STATUS          current
    DESCRIPTION     
            "Screening Step Result Entry Point Reference."
    ::= { ptGWSTScreeningStepResultEntry 3 }

ptGWSTScreeningStepResultScreeningTestMode OBJECT-TYPE
    SYNTAX          INTEGER { disabled(0), enabled(1) }
    MAX-ACCESS      read-only
    STATUS          current
    DESCRIPTION     
            "Screening Step Result Screening Test Mode"
    ::= { ptGWSTScreeningStepResultEntry 4 }

ptGWSTScreeningStepResultMSUTracing OBJECT-TYPE
    SYNTAX          INTEGER { disabled(0), enabled(1) }
    MAX-ACCESS      read-only
    STATUS          current
    DESCRIPTION     
            "Screening Step Result MSU Tracing"
    ::= { ptGWSTScreeningStepResultEntry 5 }

ptGWSTScreeningStepResultGWSTTablesIndex OBJECT-TYPE
    SYNTAX          Integer32 (-2147483648..2147483647)
    MAX-ACCESS      not-accessible
    STATUS          current
    DESCRIPTION     
            "This is the index of the parent type for this object.
             This parent type is GWSTTables."
    ::= { ptGWSTScreeningStepResultEntry 242 }

ptGWSTScreeningStepResultGWSSearchUtilityIndex OBJECT-TYPE
    SYNTAX          Integer32 (-2147483648..2147483647)
    MAX-ACCESS      not-accessible
    STATUS          current
    DESCRIPTION     
            "This is the index of the parent type for this object.
             This parent type is GWSSearchUtility."
    ::= { ptGWSTScreeningStepResultEntry 243 }

ptGWSTScreeningStepResultParentOID OBJECT-TYPE
    SYNTAX          OBJECT IDENTIFIER
    MAX-ACCESS      read-create
    STATUS          current
    DESCRIPTION     
            "The OID of the parent object for this instance"
    ::= { ptGWSTScreeningStepResultEntry 253 }

ptGWSTScreeningStepResultRowStatus OBJECT-TYPE
    SYNTAX          RowStatus
    MAX-ACCESS      read-create
    STATUS          current
    DESCRIPTION     
            "The row status for the GWSTScreeningStepResult table"
    ::= { ptGWSTScreeningStepResultEntry 254 }

ptGWSTScreeningStepResultIndex OBJECT-TYPE
    SYNTAX          Integer32 (-2147483648..2147483647)
    MAX-ACCESS      not-accessible
    STATUS          current
    DESCRIPTION     
            "The row number for the GWSTScreeningStepResult table"
    ::= { ptGWSTScreeningStepResultEntry 255 }

ptGWSTRedirectionResult OBJECT IDENTIFIER
    ::= { ptGWSTGWSSearchUtility 1017 }

ptGWSTRedirectionResultTable OBJECT-TYPE
    SYNTAX          SEQUENCE OF PtGWSTRedirectionResultEntry
    MAX-ACCESS      not-accessible
    STATUS          current
    DESCRIPTION     
            "No description supplied in the proxy config file."
    ::= { ptGWSTRedirectionResult 1 }

ptGWSTRedirectionResultEntry OBJECT-TYPE
    SYNTAX          PtGWSTRedirectionResultEntry
    MAX-ACCESS      not-accessible
    STATUS          current
    DESCRIPTION     
            "A sequence of GWSTRedirectionResult attributes."
    INDEX           { ptConnGroupIndex, 
                      ptGWSTRedirectionResultGWSTTablesIndex, 
                      ptGWSTRedirectionResultGWSSearchUtilityIndex, 
                      ptGWSTRedirectionResultIndex }
    ::= { ptGWSTRedirectionResultTable 1 }

PtGWSTRedirectionResultEntry ::=
    SEQUENCE {
        ptGWSTRedirectionResultSequenceNumber     Integer32,
        ptGWSTRedirectionResultRedirectionValue       DisplayString,
        ptGWSTRedirectionResultCost     Integer32,
        ptGWSTRedirectionResultRedirectionOption        INTEGER,
        ptGWSTRedirectionResultLoadshareOption      INTEGER,
        ptGWSTRedirectionResultErrorHandling    INTEGER,
        ptGWSTRedirectionResultGWSTTablesIndex      Integer32,
        ptGWSTRedirectionResultGWSSearchUtilityIndex            Integer32,
        ptGWSTRedirectionResultParentOID OBJECT IDENTIFIER,
        ptGWSTRedirectionResultRowStatus RowStatus,
        ptGWSTRedirectionResultIndex    Integer32
    }

ptGWSTRedirectionResultSequenceNumber OBJECT-TYPE
    SYNTAX          Integer32 (-2147483648..2147483647)
    MAX-ACCESS      read-only
    STATUS          current
    DESCRIPTION     
            "Redirection Result Sequence Number"
    ::= { ptGWSTRedirectionResultEntry 1 }

ptGWSTRedirectionResultRedirectionValue OBJECT-TYPE
    SYNTAX          DisplayString (SIZE(0..255))
    MAX-ACCESS      read-only
    STATUS          current
    DESCRIPTION     
            "Redirection Result PC or Application ID (based on Result)"
    ::= { ptGWSTRedirectionResultEntry 2 }

ptGWSTRedirectionResultCost OBJECT-TYPE
    SYNTAX          Integer32 (-2147483648..2147483647)
    MAX-ACCESS      read-only
    STATUS          current
    DESCRIPTION     
            "Redirection Result Cost"
    ::= { ptGWSTRedirectionResultEntry 3 }

ptGWSTRedirectionResultRedirectionOption OBJECT-TYPE
    SYNTAX          INTEGER { redirectOriginal(1), redirectDuplicate(2), 
                        redirectOverrideDpc(3) }
    MAX-ACCESS      read-only
    STATUS          current
    DESCRIPTION     
            "Redirection Result Redirection Option"
    ::= { ptGWSTRedirectionResultEntry 4 }

ptGWSTRedirectionResultLoadshareOption OBJECT-TYPE
    SYNTAX          INTEGER { roundRobin(1), slsBased(2) }
    MAX-ACCESS      read-only
    STATUS          current
    DESCRIPTION     
            "Redirection Result Loadshare Option"
    ::= { ptGWSTRedirectionResultEntry 5 }

ptGWSTRedirectionResultErrorHandling OBJECT-TYPE
    SYNTAX          INTEGER { discard(1), passThrough(2) }
    MAX-ACCESS      read-only
    STATUS          current
    DESCRIPTION     
            "Redirection Result Error Handling"
    ::= { ptGWSTRedirectionResultEntry 6 }

ptGWSTRedirectionResultGWSTTablesIndex OBJECT-TYPE
    SYNTAX          Integer32 (-2147483648..2147483647)
    MAX-ACCESS      not-accessible
    STATUS          current
    DESCRIPTION     
            "This is the index of the parent type for this object.
             This parent type is GWSTTables."
    ::= { ptGWSTRedirectionResultEntry 242 }

ptGWSTRedirectionResultGWSSearchUtilityIndex OBJECT-TYPE
    SYNTAX          Integer32 (-2147483648..2147483647)
    MAX-ACCESS      not-accessible
    STATUS          current
    DESCRIPTION     
            "This is the index of the parent type for this object.
             This parent type is GWSSearchUtility."
    ::= { ptGWSTRedirectionResultEntry 243 }

ptGWSTRedirectionResultParentOID OBJECT-TYPE
    SYNTAX          OBJECT IDENTIFIER
    MAX-ACCESS      read-create
    STATUS          current
    DESCRIPTION     
            "The OID of the parent object for this instance"
    ::= { ptGWSTRedirectionResultEntry 253 }

ptGWSTRedirectionResultRowStatus OBJECT-TYPE
    SYNTAX          RowStatus
    MAX-ACCESS      read-create
    STATUS          current
    DESCRIPTION     
            "The row status for the GWSTRedirectionResult table"
    ::= { ptGWSTRedirectionResultEntry 254 }

ptGWSTRedirectionResultIndex OBJECT-TYPE
    SYNTAX          Integer32 (-2147483648..2147483647)
    MAX-ACCESS      not-accessible
    STATUS          current
    DESCRIPTION     
            "The row number for the GWSTRedirectionResult table"
    ::= { ptGWSTRedirectionResultEntry 255 }

ptSlotMonitor OBJECT IDENTIFIER
    ::= { ptConnGroup 601 }

ptSlotMonitorTable OBJECT-TYPE
    SYNTAX          SEQUENCE OF PtSlotMonitorEntry
    MAX-ACCESS      not-accessible
    STATUS          current
    DESCRIPTION     
            "No description supplied in the proxy config file."
    ::= { ptSlotMonitor 1 }

ptSlotMonitorEntry OBJECT-TYPE
    SYNTAX          PtSlotMonitorEntry
    MAX-ACCESS      not-accessible
    STATUS          current
    DESCRIPTION     
            "A sequence of SlotMonitor attributes."
    INDEX           { ptConnGroupIndex, ptSlotMonitorIndex }
    ::= { ptSlotMonitorTable 1 }

PtSlotMonitorEntry ::=
    SEQUENCE {
        ptSlotMonitorChassisType        INTEGER,
        ptSlotMonitorHostname           DisplayString,
        ptSlotMonitorDebugLogging       INTEGER,
        ptSlotMonitorActions            INTEGER,
        ptSlotMonitorParentOID          OBJECT IDENTIFIER,
        ptSlotMonitorRowStatus          RowStatus,
        ptSlotMonitorIndex              Integer32
    }

ptSlotMonitorChassisType OBJECT-TYPE
    SYNTAX          INTEGER { unknown(0), x301(1), x401(2), x211(3), 
                        x401e(4), sp2k(5), dsc8000(6), dscvm(7) }
    MAX-ACCESS      read-only
    STATUS          current
    DESCRIPTION     
            "Type of chassis (e.g. X301, X401, SP2K)"
    ::= { ptSlotMonitorEntry 1 }

ptSlotMonitorHostname OBJECT-TYPE
    SYNTAX          DisplayString (SIZE(0..255))
    MAX-ACCESS      read-only
    STATUS          current
    DESCRIPTION     
            "Hostname of the Management CPU board that the active Slot Monitor application is executing on"
    ::= { ptSlotMonitorEntry 2 }

ptSlotMonitorDebugLogging OBJECT-TYPE
    SYNTAX          INTEGER { disabled(0), default(1), verbose(2) }
    MAX-ACCESS      read-create
    STATUS          current
    DESCRIPTION     
            "Debug logging level for this application. DISABLED, DEFAULT or VERBOSE."
    ::= { ptSlotMonitorEntry 3 }

ptSlotMonitorActions OBJECT-TYPE
    SYNTAX          INTEGER { restoreDebugDefaults(1) }
    MAX-ACCESS      read-create
    STATUS          current
    DESCRIPTION     
            "The OID of all possible actions for this instance"
    ::= { ptSlotMonitorEntry 252 }

ptSlotMonitorParentOID OBJECT-TYPE
    SYNTAX          OBJECT IDENTIFIER
    MAX-ACCESS      read-create
    STATUS          current
    DESCRIPTION     
            "The OID of the parent object for this instance"
    ::= { ptSlotMonitorEntry 253 }

ptSlotMonitorRowStatus OBJECT-TYPE
    SYNTAX          RowStatus
    MAX-ACCESS      read-create
    STATUS          current
    DESCRIPTION     
            "The row status for the SlotMonitor table"
    ::= { ptSlotMonitorEntry 254 }

ptSlotMonitorIndex OBJECT-TYPE
    SYNTAX          Integer32 (-2147483648..2147483647)
    MAX-ACCESS      not-accessible
    STATUS          current
    DESCRIPTION     
            "The row number for the SlotMonitor table"
    ::= { ptSlotMonitorEntry 255 }

ptSlot OBJECT IDENTIFIER
    ::= { ptSlotMonitor 602 }

ptSlotTable OBJECT-TYPE
    SYNTAX          SEQUENCE OF PtSlotEntry
    MAX-ACCESS      not-accessible
    STATUS          current
    DESCRIPTION     
            "No description supplied in the proxy config file."
    ::= { ptSlot 1 }

ptSlotEntry OBJECT-TYPE
    SYNTAX          PtSlotEntry
    MAX-ACCESS      not-accessible
    STATUS          current
    DESCRIPTION     
            "A sequence of Slot attributes."
    INDEX           { ptConnGroupIndex, ptSlotSlotMonitorIndex, 
                      ptSlotIndex }
    ::= { ptSlotTable 1 }

PtSlotEntry ::=
    SEQUENCE {
        ptSlotSlotNumber                Integer32,
        ptSlotSlotType                  INTEGER,
        ptSlotSlotStatus                INTEGER,
        ptSlotPrimaryIP                 DisplayString,
        ptSlotSecondaryIP               DisplayString,
        ptSlotPrimaryIPState            INTEGER,
        ptSlotSecondaryIPState          INTEGER,
        ptSlotMonitorState              INTEGER,
        ptSlotCPUMemoryUsage            INTEGER,
        ptSlotBackupSpaceUsage          INTEGER,
        ptSlotCPULoadUsage              DisplayString,
        ptSlotOMsSpaceUsage             INTEGER,
        ptSlotLastFailedSFTPBackupDestIP DisplayString,
        ptSlotLastFailedSFTPBackupDestUserID    DisplayString,
        ptSlotLastFailedSFTPBackupDestDir DisplayString,
        ptSlotSlotMonitorIndex          Integer32,
        ptSlotParentOID                 OBJECT IDENTIFIER,
        ptSlotRowStatus                 RowStatus,
        ptSlotIndex                     Integer32
    }

ptSlotSlotNumber OBJECT-TYPE
    SYNTAX          Integer32 (-2147483648..2147483647)
    MAX-ACCESS      read-only
    STATUS          current
    DESCRIPTION     
            "Physical slot location of the board in the chassis."
    ::= { ptSlotEntry 1 }

ptSlotSlotType OBJECT-TYPE
    SYNTAX          INTEGER { unknownType(0), rtngCpu(1), mgmtCpu(2), 
                        rtngMgmtCpu(3), ss7Io(4), hardrive(5), switch(6), 
                        ismA(7), ismB(8), applCpu(9), custCpu(10), 
                        vacant(11) }
    MAX-ACCESS      read-only
    STATUS          current
    DESCRIPTION     
            "Type of board in the slot number in question. CPU, IO, or ISM."
    ::= { ptSlotEntry 2 }

ptSlotSlotStatus OBJECT-TYPE
    SYNTAX          INTEGER { unknownState(0), extracted(1), 
                        available(2), pendingExtractionRequest(3), 
                        readyToBeExtracted(4), lostConnection(5) }
    MAX-ACCESS      read-only
    STATUS          current
    DESCRIPTION     
            "Current status for this slot, as determined by the slot monitoring application. Can be one of the following states; EXTRACTED: slot has been properly extracted. AVAILABLE: slot is communicating normally with the Slot Monitor. UNKNOWN_STATE: slot is not present. PENDING_EXTRACTION_REQUEST: Slot Monitor has sent an extraction request to this slot. READY_TO_BE_EXTRACTED: slot is ready for extraction. LOST_CONNECTION: Slot Monitor has lost connection to this slot."
    ::= { ptSlotEntry 3 }

ptSlotPrimaryIP OBJECT-TYPE
    SYNTAX          DisplayString (SIZE(0..255))
    MAX-ACCESS      read-only
    STATUS          current
    DESCRIPTION     
            "Primary IP address of the slot"
    ::= { ptSlotEntry 4 }

ptSlotSecondaryIP OBJECT-TYPE
    SYNTAX          DisplayString (SIZE(0..255))
    MAX-ACCESS      read-only
    STATUS          current
    DESCRIPTION     
            "Secondary IP address of the slot"
    ::= { ptSlotEntry 5 }

ptSlotPrimaryIPState OBJECT-TYPE
    SYNTAX          INTEGER { noConnection(0), responding(1), notUsed(2) }
    MAX-ACCESS      read-only
    STATUS          current
    DESCRIPTION     
            "State of the primary IP address of the slot"
    ::= { ptSlotEntry 6 }

ptSlotSecondaryIPState OBJECT-TYPE
    SYNTAX          INTEGER { noConnection(0), responding(1), notUsed(2) }
    MAX-ACCESS      read-only
    STATUS          current
    DESCRIPTION     
            "State of the secondary IP address of the slot"
    ::= { ptSlotEntry 7 }

ptSlotMonitorState OBJECT-TYPE
    SYNTAX          INTEGER { disabled(0), enabled(1) }
    MAX-ACCESS      read-only
    STATUS          current
    DESCRIPTION     
            "If enabled raise events on slot state changes. If disabled ignore states."
    ::= { ptSlotEntry 16 }

ptSlotCPUMemoryUsage OBJECT-TYPE
    SYNTAX          INTEGER { noReport(0) }
    MAX-ACCESS      read-only
    STATUS          current
    DESCRIPTION     
            "Reported CPU memory usage (only reported for alarms)."
    ::= { ptSlotEntry 17 }

ptSlotBackupSpaceUsage OBJECT-TYPE
    SYNTAX          INTEGER { noReport(0) }
    MAX-ACCESS      read-only
    STATUS          current
    DESCRIPTION     
            "Reported Backup Space usage (only reported for alarms)."
    ::= { ptSlotEntry 18 }

ptSlotCPULoadUsage OBJECT-TYPE
    SYNTAX          DisplayString (SIZE(0..255))
    MAX-ACCESS      read-only
    STATUS          current
    DESCRIPTION     
            "Reported CPU load usage (only reported for alarms)."
    ::= { ptSlotEntry 19 }

ptSlotOMsSpaceUsage OBJECT-TYPE
    SYNTAX          INTEGER { noReport(0) }
    MAX-ACCESS      read-only
    STATUS          current
    DESCRIPTION     
            "Reported OMs Directory Space usage (only reported for alarms)."
    ::= { ptSlotEntry 20 }

ptSlotLastFailedSFTPBackupDestIP OBJECT-TYPE
    SYNTAX          DisplayString (SIZE(0..255))
    MAX-ACCESS      read-only
    STATUS          current
    DESCRIPTION     
            "Reported Destination IP of last failed SFTP backup transfer (only reported for alarms)."
    ::= { ptSlotEntry 21 }

ptSlotLastFailedSFTPBackupDestUserID OBJECT-TYPE
    SYNTAX          DisplayString (SIZE(0..255))
    MAX-ACCESS      read-only
    STATUS          current
    DESCRIPTION     
            "Reported Destination UserID of last failed SFTP backup transfer (only reported for alarms)."
    ::= { ptSlotEntry 22 }

ptSlotLastFailedSFTPBackupDestDir OBJECT-TYPE
    SYNTAX          DisplayString (SIZE(0..255))
    MAX-ACCESS      read-only
    STATUS          current
    DESCRIPTION     
            "Reported Destination Directory of last failed SFTP backup transfer (only reported for alarms)."
    ::= { ptSlotEntry 23 }

ptSlotSlotMonitorIndex OBJECT-TYPE
    SYNTAX          Integer32 (-2147483648..2147483647)
    MAX-ACCESS      not-accessible
    STATUS          current
    DESCRIPTION     
            "This is the index of the parent type for this object.
             This parent type is SlotMonitor."
    ::= { ptSlotEntry 242 }

ptSlotParentOID OBJECT-TYPE
    SYNTAX          OBJECT IDENTIFIER
    MAX-ACCESS      read-create
    STATUS          current
    DESCRIPTION     
            "The OID of the parent object for this instance"
    ::= { ptSlotEntry 253 }

ptSlotRowStatus OBJECT-TYPE
    SYNTAX          RowStatus
    MAX-ACCESS      read-create
    STATUS          current
    DESCRIPTION     
            "The row status for the Slot table"
    ::= { ptSlotEntry 254 }

ptSlotIndex OBJECT-TYPE
    SYNTAX          Integer32 (-2147483648..2147483647)
    MAX-ACCESS      not-accessible
    STATUS          current
    DESCRIPTION     
            "The row number for the Slot table"
    ::= { ptSlotEntry 255 }

ptApplication OBJECT IDENTIFIER
    ::= { ptSlot 603 }

ptApplicationTable OBJECT-TYPE
    SYNTAX          SEQUENCE OF PtApplicationEntry
    MAX-ACCESS      not-accessible
    STATUS          current
    DESCRIPTION     
            "No description supplied in the proxy config file."
    ::= { ptApplication 1 }

ptApplicationEntry OBJECT-TYPE
    SYNTAX          PtApplicationEntry
    MAX-ACCESS      not-accessible
    STATUS          current
    DESCRIPTION     
            "A sequence of Application attributes."
    INDEX           { ptConnGroupIndex, ptApplicationSlotMonitorIndex, 
                      ptApplicationSlotIndex, ptApplicationIndex }
    ::= { ptApplicationTable 1 }

PtApplicationEntry ::=
    SEQUENCE {
        ptApplicationSlotNumber         Integer32,
        ptApplicationApplicationName    DisplayString,
        ptApplicationApplicationState   INTEGER,
        ptApplicationSlotMonitorIndex   Integer32,
        ptApplicationSlotIndex          Integer32,
        ptApplicationParentOID          OBJECT IDENTIFIER,
        ptApplicationRowStatus          RowStatus,
        ptApplicationIndex              Integer32
    }

ptApplicationSlotNumber OBJECT-TYPE
    SYNTAX          Integer32 (-2147483648..2147483647)
    MAX-ACCESS      read-only
    STATUS          current
    DESCRIPTION     
            "Physical slot location of the board hosting the application."
    ::= { ptApplicationEntry 1 }

ptApplicationApplicationName OBJECT-TYPE
    SYNTAX          DisplayString (SIZE(0..255))
    MAX-ACCESS      read-only
    STATUS          current
    DESCRIPTION     
            "Name of the application."
    ::= { ptApplicationEntry 2 }

ptApplicationApplicationState OBJECT-TYPE
    SYNTAX          INTEGER { running(0), stopped(1) }
    MAX-ACCESS      read-only
    STATUS          current
    DESCRIPTION     
            "Reported state of the application."
    ::= { ptApplicationEntry 3 }

ptApplicationSlotMonitorIndex OBJECT-TYPE
    SYNTAX          Integer32 (-2147483648..2147483647)
    MAX-ACCESS      not-accessible
    STATUS          current
    DESCRIPTION     
            "This is the index of the parent type for this object.
             This parent type is SlotMonitor."
    ::= { ptApplicationEntry 242 }

ptApplicationSlotIndex OBJECT-TYPE
    SYNTAX          Integer32 (-2147483648..2147483647)
    MAX-ACCESS      not-accessible
    STATUS          current
    DESCRIPTION     
            "This is the index of the parent type for this object.
             This parent type is Slot."
    ::= { ptApplicationEntry 243 }

ptApplicationParentOID OBJECT-TYPE
    SYNTAX          OBJECT IDENTIFIER
    MAX-ACCESS      read-create
    STATUS          current
    DESCRIPTION     
            "The OID of the parent object for this instance"
    ::= { ptApplicationEntry 253 }

ptApplicationRowStatus OBJECT-TYPE
    SYNTAX          RowStatus
    MAX-ACCESS      read-create
    STATUS          current
    DESCRIPTION     
            "The row status for the Application table"
    ::= { ptApplicationEntry 254 }

ptApplicationIndex OBJECT-TYPE
    SYNTAX          Integer32 (-2147483648..2147483647)
    MAX-ACCESS      not-accessible
    STATUS          current
    DESCRIPTION     
            "The row number for the Application table"
    ::= { ptApplicationEntry 255 }

ptGTTGTT OBJECT IDENTIFIER
    ::= { ptConnGroup 651 }

ptGTTGTTTable OBJECT-TYPE
    SYNTAX          SEQUENCE OF PtGTTGTTEntry
    MAX-ACCESS      not-accessible
    STATUS          current
    DESCRIPTION     
            "No description supplied in the proxy config file."
    ::= { ptGTTGTT 1 }

ptGTTGTTEntry OBJECT-TYPE
    SYNTAX          PtGTTGTTEntry
    MAX-ACCESS      not-accessible
    STATUS          current
    DESCRIPTION     
            "A sequence of GTTGTT attributes."
    INDEX           { ptConnGroupIndex, ptGTTGTTIndex }
    ::= { ptGTTGTTTable 1 }

PtGTTGTTEntry ::=
    SEQUENCE {
        ptGTTGTTParentOID               OBJECT IDENTIFIER,
        ptGTTGTTRowStatus               RowStatus,
        ptGTTGTTIndex                   Integer32
    }

ptGTTGTTParentOID OBJECT-TYPE
    SYNTAX          OBJECT IDENTIFIER
    MAX-ACCESS      read-create
    STATUS          current
    DESCRIPTION     
            "The OID of the parent object for this instance"
    ::= { ptGTTGTTEntry 253 }

ptGTTGTTRowStatus OBJECT-TYPE
    SYNTAX          RowStatus
    MAX-ACCESS      read-create
    STATUS          current
    DESCRIPTION     
            "The row status for the GTTGTT table"
    ::= { ptGTTGTTEntry 254 }

ptGTTGTTIndex OBJECT-TYPE
    SYNTAX          Integer32 (-2147483648..2147483647)
    MAX-ACCESS      not-accessible
    STATUS          current
    DESCRIPTION     
            "The row number for the GTTGTT table"
    ::= { ptGTTGTTEntry 255 }

ptGTTGTTConfiguration OBJECT IDENTIFIER
    ::= { ptConnGroup 652 }

ptGTTGTTConfigurationTable OBJECT-TYPE
    SYNTAX          SEQUENCE OF PtGTTGTTConfigurationEntry
    MAX-ACCESS      not-accessible
    STATUS          current
    DESCRIPTION     
            "No description supplied in the proxy config file."
    ::= { ptGTTGTTConfiguration 1 }

ptGTTGTTConfigurationEntry OBJECT-TYPE
    SYNTAX          PtGTTGTTConfigurationEntry
    MAX-ACCESS      not-accessible
    STATUS          current
    DESCRIPTION     
            "A sequence of GTTGTTConfiguration attributes."
    INDEX           { ptConnGroupIndex, ptGTTGTTConfigurationIndex }
    ::= { ptGTTGTTConfigurationTable 1 }

PtGTTGTTConfigurationEntry ::=
    SEQUENCE {
        ptGTTGTTConfigurationName       DisplayString,
        ptGTTGTTConfigurationSS7Variant INTEGER,
        ptGTTGTTConfigurationGTDigitsFiller   INTEGER,
        ptGTTGTTConfigurationDefaultPCListName      DisplayString,
        ptGTTGTTConfigurationTranslateUDTS  INTEGER,
        ptGTTGTTConfigurationLicenseStatus  INTEGER,
        ptGTTGTTConfigurationErrors     INTEGER,
        ptGTTGTTConfigurationSetupManagement    INTEGER,
        ptGTTGTTConfigurationDatabaseManagement       INTEGER,
        ptGTTGTTConfigurationMSUTrace   INTEGER,
        ptGTTGTTConfigurationExecutionTrace   INTEGER,
        ptGTTGTTConfigurationSCCPMessages INTEGER,
        ptGTTGTTConfigurationFileManagement   INTEGER,
        ptGTTGTTConfigurationPeerManagement   INTEGER,
        ptGTTGTTConfigurationLDLDebugLevel  INTEGER,
        ptGTTGTTConfigurationSCTPDebugLevel   INTEGER,
        ptGTTGTTConfigurationUIPort     Integer32,
        ptGTTGTTConfigurationMaxGTSearches  Integer32,
        ptGTTGTTConfigurationMaxGTModifications       Integer32,
        ptGTTGTTConfigurationGTTTraffic INTEGER,
        ptGTTGTTConfigurationUnavailablePeerIDs       DisplayString,
        ptGTTGTTConfigurationAdvancedSearch   INTEGER,
        ptGTTGTTConfigurationDefaultDBDefName     DisplayString,
        ptGTTGTTConfigurationCrossNAUDTS INTEGER,
        ptGTTGTTConfigurationActions    INTEGER,
        ptGTTGTTConfigurationParentOID  OBJECT IDENTIFIER,
        ptGTTGTTConfigurationRowStatus  RowStatus,
        ptGTTGTTConfigurationIndex      Integer32
    }

ptGTTGTTConfigurationName OBJECT-TYPE
    SYNTAX          DisplayString (SIZE(0..255))
    MAX-ACCESS      read-only
    STATUS          current
    DESCRIPTION     
            "Obsolete as of 9.0."
    ::= { ptGTTGTTConfigurationEntry 1 }

ptGTTGTTConfigurationSS7Variant OBJECT-TYPE
    SYNTAX          INTEGER { itu(0), ansi(1), china(2), ntt(3), ttc(4) }
    MAX-ACCESS      read-create
    STATUS          current
    DESCRIPTION     
            "Obsolete as of 9.0. Moved to GTT DB Def."
    ::= { ptGTTGTTConfigurationEntry 2 }

ptGTTGTTConfigurationGTDigitsFiller OBJECT-TYPE
    SYNTAX          INTEGER { zero(0), f(1) }
    MAX-ACCESS      read-create
    STATUS          current
    DESCRIPTION     
            "Obsolete as of 9.0. Moved to GTT DB Def."
    ::= { ptGTTGTTConfigurationEntry 3 }

ptGTTGTTConfigurationDefaultPCListName OBJECT-TYPE
    SYNTAX          DisplayString (SIZE(0..255))
    MAX-ACCESS      read-create
    STATUS          current
    DESCRIPTION     
            "Obsolete as of 9.0. Moved to GTT DB Def."
    ::= { ptGTTGTTConfigurationEntry 4 }

ptGTTGTTConfigurationTranslateUDTS OBJECT-TYPE
    SYNTAX          INTEGER { disabled(0), enabled(1) }
    MAX-ACCESS      read-create
    STATUS          current
    DESCRIPTION     
            "Obsolete as of 9.0. Moved to GTT DB Def."
    ::= { ptGTTGTTConfigurationEntry 5 }

ptGTTGTTConfigurationLicenseStatus OBJECT-TYPE
    SYNTAX          INTEGER { unlicensed(0), licensedFor100Records(1), 
                        licensedFor10000Records(2), 
                        licensedFor30000Records(3), 
                        licensedFor100000Records(4), 
                        licensedFor500000Records(5) }
    MAX-ACCESS      read-only
    STATUS          current
    DESCRIPTION     
            "GTT license status (UNLICENSED, LICENSED). Global Title Translations is a licensable feature. The feature must be licensed to forward traffic. Also the number of records in the database is also a licensed amount."
    ::= { ptGTTGTTConfigurationEntry 6 }

ptGTTGTTConfigurationErrors OBJECT-TYPE
    SYNTAX          INTEGER { notLogged(0), logged(1) }
    MAX-ACCESS      read-create
    STATUS          current
    DESCRIPTION     
            "This flag Enables or disables the sending of error information to the DEBUGLOG files. These are system level errors, not errors relating to translations and searches for specific levels. Most of these system level messages are also sent to the SYSLOG file. \nThis flag should be set to LOGGED for production systems."
    ::= { ptGTTGTTConfigurationEntry 7 }

ptGTTGTTConfigurationSetupManagement OBJECT-TYPE
    SYNTAX          INTEGER { notLogged(0), logged(1) }
    MAX-ACCESS      read-create
    STATUS          current
    DESCRIPTION     
            "This flag enables or disables the sending of information concerning the process start-up and setup activities, to the DEBUGLOG. It is only used when there is a system start-up or a communication problem between the CPUs of a two CPU system. \nThe Setup Management Debug flag is normally set to LOGGED on most production systems, because its messages usually occur only at system start-up."
    ::= { ptGTTGTTConfigurationEntry 8 }

ptGTTGTTConfigurationDatabaseManagement OBJECT-TYPE
    SYNTAX          INTEGER { notLogged(0), logged(1) }
    MAX-ACCESS      read-create
    STATUS          current
    DESCRIPTION     
            "This flag enables or disables the sending of information concerning the translation database and its provisioning. \nThe Database Management Debug flag is normally set to NOT_LOGGED on most production systems, so that the system does not spend an undue amount of time logging messages."
    ::= { ptGTTGTTConfigurationEntry 9 }

ptGTTGTTConfigurationMSUTrace OBJECT-TYPE
    SYNTAX          INTEGER { notLogged(0), logged(1) }
    MAX-ACCESS      read-create
    STATUS          current
    DESCRIPTION     
            "Obsolete as of 9.0. \nThis flag enables or disables the logging of MSU Tracing to the DEBUGLOG file. By default, this flag is turned on."
    ::= { ptGTTGTTConfigurationEntry 10 }

ptGTTGTTConfigurationExecutionTrace OBJECT-TYPE
    SYNTAX          INTEGER { notLogged(0), logged(1) }
    MAX-ACCESS      read-create
    STATUS          current
    DESCRIPTION     
            "This flag enables or disables the sending of information concerning the internal sections of code being executed, to the DEBUGLOG file. \nIt is intended for the use of Sonus Networks customer support for specific error situations. The resultant messages in the DEBUGLOG are not meant to be interpreted by customers. \nThe Execution Trace Debug flag is should be set to NOT_LOGGED on all production systems, unless directed by Sonus Networks customer support. Otherwise the system performance may be impacted as the system may spend an undue amount of time logging messages."
    ::= { ptGTTGTTConfigurationEntry 11 }

ptGTTGTTConfigurationSCCPMessages OBJECT-TYPE
    SYNTAX          INTEGER { notLogged(0), logged(1) }
    MAX-ACCESS      read-create
    STATUS          current
    DESCRIPTION     
            "This flag enables or disables the sending of information concerning the messages received from the SCCP to the DEBUGLOG. The messages are presented in the DEBUGLOG as a hexadecimal output of the contents. The format of the message is in a proprietary protocol and is not one used by customers. \nThis flag is only relevant if the GTT is executed as a process as when PCE is licensed. When GTT is executed as a library of SCCP, the SCCP SS7 Messages debug flag should be used to obtain a more thorough decoded hex output. \nThe SCCP Messages Debug flag should be set to NOT_LOGGED on all production systems, unless directed by Sonus Networks customer support. Otherwise the system performance may be impacted as the system may spend an undue amount of time logging messages."
    ::= { ptGTTGTTConfigurationEntry 12 }

ptGTTGTTConfigurationFileManagement OBJECT-TYPE
    SYNTAX          INTEGER { notLogged(0), logged(1) }
    MAX-ACCESS      read-create
    STATUS          current
    DESCRIPTION     
            "This flag enables or disables the sending of information concerning the files that contain the translation database. The information is sent to the DEBUGLOG. \nThe File Management Debug flag should be set to NOT_LOGGED on all production systems, unless directed by Sonus Networks customer support. Otherwise the system performance may be impacted as the system may spend an undue amount of time logging messages."
    ::= { ptGTTGTTConfigurationEntry 13 }

ptGTTGTTConfigurationPeerManagement OBJECT-TYPE
    SYNTAX          INTEGER { notLogged(0), logged(1) }
    MAX-ACCESS      read-create
    STATUS          current
    DESCRIPTION     
            "This flag enables or disables the sending of information concerning the communications between the distributed software on a two CPU system. The messages exchanged between the two systems are presented by this flag. The information is sent to the DEBUGLOG. \nThe Peer Management Debug flag should be set to NOT_LOGGED on all production systems, unless directed by Sonus Networks customer support. Otherwise the system performance may be impacted as the system may spend an undue amount of time logging messages."
    ::= { ptGTTGTTConfigurationEntry 14 }

ptGTTGTTConfigurationLDLDebugLevel OBJECT-TYPE
    SYNTAX          INTEGER { notLogged(0) }
    MAX-ACCESS      read-create
    STATUS          current
    DESCRIPTION     
            "The LDL Debug Level should be set to 2 or lower on all production systems, unless directed by support. Otherwise the system performance may be impacted by an undue amount of time logging messages. Valid range is (0 [NOT LOGGED], 1 to 10)."
    ::= { ptGTTGTTConfigurationEntry 15 }

ptGTTGTTConfigurationSCTPDebugLevel OBJECT-TYPE
    SYNTAX          INTEGER { notLogged(0) }
    MAX-ACCESS      read-create
    STATUS          current
    DESCRIPTION     
            "The SCTP Debug Level should be set to 0 on all production systems, unless directed by support. Otherwise the system performance may be impacted by an undue amount of time logging messages. Valid range is (0 [NOT LOGGED], 1 to 10)."
    ::= { ptGTTGTTConfigurationEntry 16 }

ptGTTGTTConfigurationUIPort OBJECT-TYPE
    SYNTAX          Integer32 (-2147483648..2147483647)
    MAX-ACCESS      read-only
    STATUS          current
    DESCRIPTION     
            "This value shows the TCP/IP port used for User Interface connections. This is a read-only value and provided for informational purposes only."
    ::= { ptGTTGTTConfigurationEntry 17 }

ptGTTGTTConfigurationMaxGTSearches OBJECT-TYPE
    SYNTAX          Integer32 (-2147483648..2147483647)
    MAX-ACCESS      read-only
    STATUS          current
    DESCRIPTION     
            "This value shows the current maximum size of the sum of the GT Searches tables permitted by your license. If you wish to have more GT searches than is shown here, please contact your Sonus Networks sales associate."
    ::= { ptGTTGTTConfigurationEntry 18 }

ptGTTGTTConfigurationMaxGTModifications OBJECT-TYPE
    SYNTAX          Integer32 (-2147483648..2147483647)
    MAX-ACCESS      read-only
    STATUS          current
    DESCRIPTION     
            "This value shows the current maximum size of the GT Modifications table permitted by your license. If you wish to have more GT Modifications than is shown here, please contact your Sonus Networks sales associate."
    ::= { ptGTTGTTConfigurationEntry 19 }

ptGTTGTTConfigurationGTTTraffic OBJECT-TYPE
    SYNTAX          INTEGER { inactive(0), active(1) }
    MAX-ACCESS      read-only
    STATUS          current
    DESCRIPTION     
            "GTT traffic (INACTIVE/ACTIVE). \nActivate/deactivate all the NAs. \nWill not activate an NA deactivated by the user. \nObsolete as of 12.2."
    ::= { ptGTTGTTConfigurationEntry 20 }

ptGTTGTTConfigurationUnavailablePeerIDs OBJECT-TYPE
    SYNTAX          DisplayString (SIZE(0..255))
    MAX-ACCESS      read-only
    STATUS          current
    DESCRIPTION     
            "List of peers that are currently unavailable to the active GTT. \nShould one or more CPUs lose communication with this CPU, then those CPUs will be listed here. The most common cause of commuication problems are IP network related."
    ::= { ptGTTGTTConfigurationEntry 21 }

ptGTTGTTConfigurationAdvancedSearch OBJECT-TYPE
    SYNTAX          INTEGER { unlicensed(0), licensed(1) }
    MAX-ACCESS      read-only
    STATUS          current
    DESCRIPTION     
            "GTT advanced search license status (UNLICENSED, LICENSED). Advanced search is a licensable feature. The feature must be licensed to allow GT routing search on not only the Called Party Address but also the Calling Party Address and the OPC from the routing label."
    ::= { ptGTTGTTConfigurationEntry 22 }

ptGTTGTTConfigurationDefaultDBDefName OBJECT-TYPE
    SYNTAX          DisplayString (SIZE(0..255))
    MAX-ACCESS      read-create
    STATUS          current
    DESCRIPTION     
            "Default GTT Database Definition Name. This feature is used during UI DB record creation if no associated DB Def Name is specified to facilitate provisioning. \nThe corresponding GTT DB Def object must exist prior to setting this attribute. \nSet the Default DB Def Name to an empty string to disable this feature."
    ::= { ptGTTGTTConfigurationEntry 23 }

ptGTTGTTConfigurationCrossNAUDTS OBJECT-TYPE
    SYNTAX          INTEGER { notApplicable(-1), disabled(0), enabled(1) }
    MAX-ACCESS      read-create
    STATUS          current
    DESCRIPTION     
            "Enable or disable the cross NA (X)UDTS support. \nIf the cross NA feature is licensed, and an (X)UDT is undeliverable in the destination NA, a (X)UDTS message is generated if required and sent back to the originating NA to report the routing failure. \nThis feature is enabled by default if cross NA is licensed. If unlicensed, the feature is set to NOT APPLICABLE."
    ::= { ptGTTGTTConfigurationEntry 24 }

ptGTTGTTConfigurationActions OBJECT-TYPE
    SYNTAX          INTEGER { restoreDebugDefaults(1) }
    MAX-ACCESS      read-create
    STATUS          current
    DESCRIPTION     
            "The OID of all possible actions for this instance"
    ::= { ptGTTGTTConfigurationEntry 252 }

ptGTTGTTConfigurationParentOID OBJECT-TYPE
    SYNTAX          OBJECT IDENTIFIER
    MAX-ACCESS      read-create
    STATUS          current
    DESCRIPTION     
            "The OID of the parent object for this instance"
    ::= { ptGTTGTTConfigurationEntry 253 }

ptGTTGTTConfigurationRowStatus OBJECT-TYPE
    SYNTAX          RowStatus
    MAX-ACCESS      read-create
    STATUS          current
    DESCRIPTION     
            "The row status for the GTTGTTConfiguration table"
    ::= { ptGTTGTTConfigurationEntry 254 }

ptGTTGTTConfigurationIndex OBJECT-TYPE
    SYNTAX          Integer32 (-2147483648..2147483647)
    MAX-ACCESS      not-accessible
    STATUS          current
    DESCRIPTION     
            "The row number for the GTTGTTConfiguration table"
    ::= { ptGTTGTTConfigurationEntry 255 }

ptGTTGTTNAManager OBJECT IDENTIFIER
    ::= { ptConnGroup 653 }

ptGTTGTTNAManagerTable OBJECT-TYPE
    SYNTAX          SEQUENCE OF PtGTTGTTNAManagerEntry
    MAX-ACCESS      not-accessible
    STATUS          current
    DESCRIPTION     
            "No description supplied in the proxy config file."
    ::= { ptGTTGTTNAManager 1 }

ptGTTGTTNAManagerEntry OBJECT-TYPE
    SYNTAX          PtGTTGTTNAManagerEntry
    MAX-ACCESS      not-accessible
    STATUS          current
    DESCRIPTION     
            "A sequence of GTTGTTNAManager attributes."
    INDEX           { ptConnGroupIndex, ptGTTGTTNAManagerIndex }
    ::= { ptGTTGTTNAManagerTable 1 }

PtGTTGTTNAManagerEntry ::=
    SEQUENCE {
        ptGTTGTTNAManagerGTTNAs         Integer32,
        ptGTTGTTNAManagerParentOID      OBJECT IDENTIFIER,
        ptGTTGTTNAManagerRowStatus      RowStatus,
        ptGTTGTTNAManagerIndex          Integer32
    }

ptGTTGTTNAManagerGTTNAs OBJECT-TYPE
    SYNTAX          Integer32 (-2147483648..2147483647)
    MAX-ACCESS      read-only
    STATUS          current
    DESCRIPTION     
            "Number of GTT Network Appearances."
    ::= { ptGTTGTTNAManagerEntry 1 }

ptGTTGTTNAManagerParentOID OBJECT-TYPE
    SYNTAX          OBJECT IDENTIFIER
    MAX-ACCESS      read-create
    STATUS          current
    DESCRIPTION     
            "The OID of the parent object for this instance"
    ::= { ptGTTGTTNAManagerEntry 253 }

ptGTTGTTNAManagerRowStatus OBJECT-TYPE
    SYNTAX          RowStatus
    MAX-ACCESS      read-create
    STATUS          current
    DESCRIPTION     
            "The row status for the GTTGTTNAManager table"
    ::= { ptGTTGTTNAManagerEntry 254 }

ptGTTGTTNAManagerIndex OBJECT-TYPE
    SYNTAX          Integer32 (-2147483648..2147483647)
    MAX-ACCESS      not-accessible
    STATUS          current
    DESCRIPTION     
            "The row number for the GTTGTTNAManager table"
    ::= { ptGTTGTTNAManagerEntry 255 }

ptGTTGTTNA OBJECT IDENTIFIER
    ::= { ptGTTGTTNAManager 654 }

ptGTTGTTNATable OBJECT-TYPE
    SYNTAX          SEQUENCE OF PtGTTGTTNAEntry
    MAX-ACCESS      not-accessible
    STATUS          current
    DESCRIPTION     
            "No description supplied in the proxy config file."
    ::= { ptGTTGTTNA 1 }

ptGTTGTTNAEntry OBJECT-TYPE
    SYNTAX          PtGTTGTTNAEntry
    MAX-ACCESS      not-accessible
    STATUS          current
    DESCRIPTION     
            "A sequence of GTTGTTNA attributes."
    INDEX           { ptConnGroupIndex, ptGTTGTTNAGTTNAManagerIndex, 
                      ptGTTGTTNAIndex }
    ::= { ptGTTGTTNATable 1 }

PtGTTGTTNAEntry ::=
    SEQUENCE {
        ptGTTGTTNANetworkAppearance     Integer32,
        ptGTTGTTNAPCRegistrations       Integer32,
        ptGTTGTTNANonConnectedPeerIDs   DisplayString,
        ptGTTGTTNADBDefName             DisplayString,
        ptGTTGTTNAAppIDRegistrations    Integer32,
        ptGTTGTTNANATraffic             INTEGER,
        ptGTTGTTNAUserDeactivated       INTEGER,
        ptGTTGTTNALPCRegistration       INTEGER,
        ptGTTGTTNAConnectionType        INTEGER,
        ptGTTGTTNAGTTNAManagerIndex     Integer32,
        ptGTTGTTNAActions               INTEGER,
        ptGTTGTTNAParentOID             OBJECT IDENTIFIER,
        ptGTTGTTNARowStatus             RowStatus,
        ptGTTGTTNAIndex                 Integer32
    }

ptGTTGTTNANetworkAppearance OBJECT-TYPE
    SYNTAX          Integer32 (-2147483648..2147483647)
    MAX-ACCESS      read-only
    STATUS          current
    DESCRIPTION     
            "Network Appearance identifier. \nUsed to determine the default SCCP GTT port."
    ::= { ptGTTGTTNAEntry 1 }

ptGTTGTTNAPCRegistrations OBJECT-TYPE
    SYNTAX          Integer32 (-2147483648..2147483647)
    MAX-ACCESS      read-only
    STATUS          current
    DESCRIPTION     
            "This attribute provides the number of PC Registrations managed by this Network Appearance. The GTT process may register to the STP with a Virtual Point Code to support another Point Code on the network. Please see the VNode feature at the MTP level for more information. \nThis attribute shows the number of successful registrations across all CPUs. \nBefore a successful registration can take place the MTP level 3 process must have an active VNode provisioned."
    ::= { ptGTTGTTNAEntry 3 }

ptGTTGTTNANonConnectedPeerIDs OBJECT-TYPE
    SYNTAX          DisplayString (SIZE(0..255))
    MAX-ACCESS      read-only
    STATUS          current
    DESCRIPTION     
            "List of peers that are currently not connected to SCCP as per the active GTT. \nIf the traffic is active but the SCCP is not connected, make sure the peers are available."
    ::= { ptGTTGTTNAEntry 4 }

ptGTTGTTNADBDefName OBJECT-TYPE
    SYNTAX          DisplayString (SIZE(0..255))
    MAX-ACCESS      read-create
    STATUS          current
    DESCRIPTION     
            "GTT Database Definition Name. \nThis attribute specifies which translation database to use for incoming messages from the NA."
    ::= { ptGTTGTTNAEntry 6 }

ptGTTGTTNAAppIDRegistrations OBJECT-TYPE
    SYNTAX          Integer32 (-2147483648..2147483647)
    MAX-ACCESS      read-only
    STATUS          current
    DESCRIPTION     
            "This attribute provides the number of AppID Registrations managed by this Network Appearance. \nThis attribute shows the number of successful registrations across all CPUs."
    ::= { ptGTTGTTNAEntry 7 }

ptGTTGTTNANATraffic OBJECT-TYPE
    SYNTAX          INTEGER { inactive(0), active(1) }
    MAX-ACCESS      read-only
    STATUS          current
    DESCRIPTION     
            "NA traffic (INACTIVE/ACTIVE)."
    ::= { ptGTTGTTNAEntry 8 }

ptGTTGTTNAUserDeactivated OBJECT-TYPE
    SYNTAX          INTEGER { disabled(0), enabled(1) }
    MAX-ACCESS      read-only
    STATUS          current
    DESCRIPTION     
            "Activation flag for NA vs system-wide."
    ::= { ptGTTGTTNAEntry 9 }

ptGTTGTTNALPCRegistration OBJECT-TYPE
    SYNTAX          INTEGER { disabled(0), enabled(1) }
    MAX-ACCESS      read-create
    STATUS          current
    DESCRIPTION     
            "Determines whether or not the LPC will be automatically registered with SCCP."
    ::= { ptGTTGTTNAEntry 10 }

ptGTTGTTNAConnectionType OBJECT-TYPE
    SYNTAX          INTEGER { sccp(0), pce(1) }
    MAX-ACCESS      read-only
    STATUS          current
    DESCRIPTION     
            "Network Appearance Connection Type (SCCP/PCE). \nBy default, set to SCCP. For PCE licensed systems, set to PCE for NAs used by PCE for SCCP/TCAP routing."
    ::= { ptGTTGTTNAEntry 11 }

ptGTTGTTNAGTTNAManagerIndex OBJECT-TYPE
    SYNTAX          Integer32 (-2147483648..2147483647)
    MAX-ACCESS      not-accessible
    STATUS          current
    DESCRIPTION     
            "This is the index of the parent type for this object.
             This parent type is GTTNAManager."
    ::= { ptGTTGTTNAEntry 242 }

ptGTTGTTNAActions OBJECT-TYPE
    SYNTAX          INTEGER { activateTraffic(1), deactivateTraffic(2) }
    MAX-ACCESS      read-create
    STATUS          current
    DESCRIPTION     
            "The OID of all possible actions for this instance"
    ::= { ptGTTGTTNAEntry 252 }

ptGTTGTTNAParentOID OBJECT-TYPE
    SYNTAX          OBJECT IDENTIFIER
    MAX-ACCESS      read-create
    STATUS          current
    DESCRIPTION     
            "The OID of the parent object for this instance"
    ::= { ptGTTGTTNAEntry 253 }

ptGTTGTTNARowStatus OBJECT-TYPE
    SYNTAX          RowStatus
    MAX-ACCESS      read-create
    STATUS          current
    DESCRIPTION     
            "The row status for the GTTGTTNA table"
    ::= { ptGTTGTTNAEntry 254 }

ptGTTGTTNAIndex OBJECT-TYPE
    SYNTAX          Integer32 (-2147483648..2147483647)
    MAX-ACCESS      not-accessible
    STATUS          current
    DESCRIPTION     
            "The row number for the GTTGTTNA table"
    ::= { ptGTTGTTNAEntry 255 }

ptGTTPCRegistration OBJECT IDENTIFIER
    ::= { ptGTTGTTNA 655 }

ptGTTPCRegistrationTable OBJECT-TYPE
    SYNTAX          SEQUENCE OF PtGTTPCRegistrationEntry
    MAX-ACCESS      not-accessible
    STATUS          current
    DESCRIPTION     
            "No description supplied in the proxy config file."
    ::= { ptGTTPCRegistration 1 }

ptGTTPCRegistrationEntry OBJECT-TYPE
    SYNTAX          PtGTTPCRegistrationEntry
    MAX-ACCESS      not-accessible
    STATUS          current
    DESCRIPTION     
            "A sequence of GTTPCRegistration attributes."
    INDEX           { ptConnGroupIndex, 
                      ptGTTPCRegistrationGTTNAManagerIndex, 
                      ptGTTPCRegistrationGTTNAIndex, 
                      ptGTTPCRegistrationIndex }
    ::= { ptGTTPCRegistrationTable 1 }

PtGTTPCRegistrationEntry ::=
    SEQUENCE {
        ptGTTPCRegistrationPointCode    Integer32,
        ptGTTPCRegistrationStatus       INTEGER,
        ptGTTPCRegistrationDBDefName    DisplayString,
        ptGTTPCRegistrationGTTNAManagerIndex    Integer32,
        ptGTTPCRegistrationGTTNAIndex   Integer32,
        ptGTTPCRegistrationParentOID    OBJECT IDENTIFIER,
        ptGTTPCRegistrationRowStatus    RowStatus,
        ptGTTPCRegistrationIndex        Integer32
    }

ptGTTPCRegistrationPointCode OBJECT-TYPE
    SYNTAX          Integer32 (-2147483648..2147483647)
    MAX-ACCESS      read-only
    STATUS          current
    DESCRIPTION     
            "Point code used to register GTT with SCCP."
    ::= { ptGTTPCRegistrationEntry 1 }

ptGTTPCRegistrationStatus OBJECT-TYPE
    SYNTAX          INTEGER { notRegistered(0), partiallyRegistered(1), 
                        registered(2), blocked(3) }
    MAX-ACCESS      read-only
    STATUS          current
    DESCRIPTION     
            "PC Registration status (NOT REGISTERED, PARTIALLY REGISTERED, REGISTERED, BLOCKED). \nOn a properly provisioned system this attribute should read 'REGISTERED.' IF there are no GTT processes on any CPUs connected to any SCCP, then this attribute will read 'NOT REGISTERED.' If there are some connections, but not on all CPUs then the attribute will display 'PARTIALLY REGISTERED.' If 'LPC Registration' is disabled on the GTT NA Configuration, then the attribute will display 'BLOCKED'. \nIf the status is anything but REGISTERED, check the SYSLOG to determine the cause of the registration problems. A likely cause of registration problems is attempting to have the GTT process register with a Virtual Point Code, that has not been created as a VNODE at the MTP level."
    ::= { ptGTTPCRegistrationEntry 2 }

ptGTTPCRegistrationDBDefName OBJECT-TYPE
    SYNTAX          DisplayString (SIZE(0..255))
    MAX-ACCESS      read-create
    STATUS          current
    DESCRIPTION     
            "GTT Database Definition Name. \nThis attribute specifies which translation database to use for incoming messages from this PC registration. \nBy default, the string is unset (empty string) which translates to using the parent NA value. \nIf the PC Registration Point Code attribute is set to the LPC of the NA, the DB Def Name cannot be modified and remains unset (empty string) to always apply the corresponding NA DB Def."
    ::= { ptGTTPCRegistrationEntry 3 }

ptGTTPCRegistrationGTTNAManagerIndex OBJECT-TYPE
    SYNTAX          Integer32 (-2147483648..2147483647)
    MAX-ACCESS      not-accessible
    STATUS          current
    DESCRIPTION     
            "This is the index of the parent type for this object.
             This parent type is GTTNAManager."
    ::= { ptGTTPCRegistrationEntry 242 }

ptGTTPCRegistrationGTTNAIndex OBJECT-TYPE
    SYNTAX          Integer32 (-2147483648..2147483647)
    MAX-ACCESS      not-accessible
    STATUS          current
    DESCRIPTION     
            "This is the index of the parent type for this object.
             This parent type is GTTNA."
    ::= { ptGTTPCRegistrationEntry 243 }

ptGTTPCRegistrationParentOID OBJECT-TYPE
    SYNTAX          OBJECT IDENTIFIER
    MAX-ACCESS      read-create
    STATUS          current
    DESCRIPTION     
            "The OID of the parent object for this instance"
    ::= { ptGTTPCRegistrationEntry 253 }

ptGTTPCRegistrationRowStatus OBJECT-TYPE
    SYNTAX          RowStatus
    MAX-ACCESS      read-create
    STATUS          current
    DESCRIPTION     
            "The row status for the GTTPCRegistration table"
    ::= { ptGTTPCRegistrationEntry 254 }

ptGTTPCRegistrationIndex OBJECT-TYPE
    SYNTAX          Integer32 (-2147483648..2147483647)
    MAX-ACCESS      not-accessible
    STATUS          current
    DESCRIPTION     
            "The row number for the GTTPCRegistration table"
    ::= { ptGTTPCRegistrationEntry 255 }

ptGTTAppIDRegistration OBJECT IDENTIFIER
    ::= { ptGTTGTTNA 674 }

ptGTTAppIDRegistrationTable OBJECT-TYPE
    SYNTAX          SEQUENCE OF PtGTTAppIDRegistrationEntry
    MAX-ACCESS      not-accessible
    STATUS          current
    DESCRIPTION     
            "No description supplied in the proxy config file."
    ::= { ptGTTAppIDRegistration 1 }

ptGTTAppIDRegistrationEntry OBJECT-TYPE
    SYNTAX          PtGTTAppIDRegistrationEntry
    MAX-ACCESS      not-accessible
    STATUS          current
    DESCRIPTION     
            "A sequence of GTTAppIDRegistration attributes."
    INDEX           { ptConnGroupIndex, 
                      ptGTTAppIDRegistrationGTTNAManagerIndex, 
                      ptGTTAppIDRegistrationGTTNAIndex, 
                      ptGTTAppIDRegistrationIndex }
    ::= { ptGTTAppIDRegistrationTable 1 }

PtGTTAppIDRegistrationEntry ::=
    SEQUENCE {
        ptGTTAppIDRegistrationApplicationID   DisplayString,
        ptGTTAppIDRegistrationStatus    INTEGER,
        ptGTTAppIDRegistrationRecordID  Integer32,
        ptGTTAppIDRegistrationDBDefName DisplayString,
        ptGTTAppIDRegistrationRetainOrigination       INTEGER,
        ptGTTAppIDRegistrationGTTNAManagerIndex       Integer32,
        ptGTTAppIDRegistrationGTTNAIndex Integer32,
        ptGTTAppIDRegistrationParentOID OBJECT IDENTIFIER,
        ptGTTAppIDRegistrationRowStatus RowStatus,
        ptGTTAppIDRegistrationIndex     Integer32
    }

ptGTTAppIDRegistrationApplicationID OBJECT-TYPE
    SYNTAX          DisplayString (SIZE(0..255))
    MAX-ACCESS      read-only
    STATUS          current
    DESCRIPTION     
            "Application ID used to register GTT with SCCP."
    ::= { ptGTTAppIDRegistrationEntry 1 }

ptGTTAppIDRegistrationStatus OBJECT-TYPE
    SYNTAX          INTEGER { notRegistered(0), partiallyRegistered(1), 
                        registered(2), blocked(3) }
    MAX-ACCESS      read-only
    STATUS          current
    DESCRIPTION     
            "Application ID Registration status (NOT REGISTERED, PARTIALLY REGISTERED, REGISTERED). \nOn a properly provisioned system this attribute should read 'REGISTERED.' If there are no GTT processes on any CPUs connected to any SCCP, then this attribute will read 'NOT REGISTERED.' If there are some connections, but not on all CPUs then the attribute will display 'PARTIALLY REGISTERED.' \nIf the status is anything but REGISTERED, check the SYSLOG to determine the cause of the registration problems. A likely cause of registration problems is attempting to have the GTT process register with an AppID already registered by another process."
    ::= { ptGTTAppIDRegistrationEntry 2 }

ptGTTAppIDRegistrationRecordID OBJECT-TYPE
    SYNTAX          Integer32 (-2147483648..2147483647)
    MAX-ACCESS      read-only
    STATUS          current
    DESCRIPTION     
            "Hidden attribute for proxy handling."
    ::= { ptGTTAppIDRegistrationEntry 3 }

ptGTTAppIDRegistrationDBDefName OBJECT-TYPE
    SYNTAX          DisplayString (SIZE(0..255))
    MAX-ACCESS      read-create
    STATUS          current
    DESCRIPTION     
            "GTT Database Definition Name. \nThis attribute specifies which translation database to use for incoming messages from this AppID registration. \nBy default, the string is unset (empty string) which translates to using the parent NA value."
    ::= { ptGTTAppIDRegistrationEntry 4 }

ptGTTAppIDRegistrationRetainOrigination OBJECT-TYPE
    SYNTAX          INTEGER { disabled(0), enabled(1) }
    MAX-ACCESS      read-create
    STATUS          current
    DESCRIPTION     
            "Application ID Registration Retain Origination. The Retain Origination attribute provides a mechanism where by the GTT notifies the SCCP to retain the Originating OPC in the Routing Label of the MSU when forwarding the MSU to to its new destination. Only MSUs redirected to GTT via the Gateway Screening App ID redirection table are affected by this attribute. By default, the Retain Origination attribute when set to disabled, maintains the standard GTT Routing implementation."
    ::= { ptGTTAppIDRegistrationEntry 5 }

ptGTTAppIDRegistrationGTTNAManagerIndex OBJECT-TYPE
    SYNTAX          Integer32 (-2147483648..2147483647)
    MAX-ACCESS      not-accessible
    STATUS          current
    DESCRIPTION     
            "This is the index of the parent type for this object.
             This parent type is GTTNAManager."
    ::= { ptGTTAppIDRegistrationEntry 242 }

ptGTTAppIDRegistrationGTTNAIndex OBJECT-TYPE
    SYNTAX          Integer32 (-2147483648..2147483647)
    MAX-ACCESS      not-accessible
    STATUS          current
    DESCRIPTION     
            "This is the index of the parent type for this object.
             This parent type is GTTNA."
    ::= { ptGTTAppIDRegistrationEntry 243 }

ptGTTAppIDRegistrationParentOID OBJECT-TYPE
    SYNTAX          OBJECT IDENTIFIER
    MAX-ACCESS      read-create
    STATUS          current
    DESCRIPTION     
            "The OID of the parent object for this instance"
    ::= { ptGTTAppIDRegistrationEntry 253 }

ptGTTAppIDRegistrationRowStatus OBJECT-TYPE
    SYNTAX          RowStatus
    MAX-ACCESS      read-create
    STATUS          current
    DESCRIPTION     
            "The row status for the GTTAppIDRegistration table"
    ::= { ptGTTAppIDRegistrationEntry 254 }

ptGTTAppIDRegistrationIndex OBJECT-TYPE
    SYNTAX          Integer32 (-2147483648..2147483647)
    MAX-ACCESS      not-accessible
    STATUS          current
    DESCRIPTION     
            "The row number for the GTTAppIDRegistration table"
    ::= { ptGTTAppIDRegistrationEntry 255 }

ptGTTGTTDBManager OBJECT IDENTIFIER
    ::= { ptConnGroup 669 }

ptGTTGTTDBManagerTable OBJECT-TYPE
    SYNTAX          SEQUENCE OF PtGTTGTTDBManagerEntry
    MAX-ACCESS      not-accessible
    STATUS          current
    DESCRIPTION     
            "No description supplied in the proxy config file."
    ::= { ptGTTGTTDBManager 1 }

ptGTTGTTDBManagerEntry OBJECT-TYPE
    SYNTAX          PtGTTGTTDBManagerEntry
    MAX-ACCESS      not-accessible
    STATUS          current
    DESCRIPTION     
            "A sequence of GTTGTTDBManager attributes."
    INDEX           { ptConnGroupIndex, ptGTTGTTDBManagerIndex }
    ::= { ptGTTGTTDBManagerTable 1 }

PtGTTGTTDBManagerEntry ::=
    SEQUENCE {
        ptGTTGTTDBManagerActions        INTEGER,
        ptGTTGTTDBManagerParentOID      OBJECT IDENTIFIER,
        ptGTTGTTDBManagerRowStatus      RowStatus,
        ptGTTGTTDBManagerIndex          Integer32
    }

ptGTTGTTDBManagerActions OBJECT-TYPE
    SYNTAX          INTEGER { liveToWorkspace(1), workspaceToLive(2) }
    MAX-ACCESS      read-create
    STATUS          current
    DESCRIPTION     
            "The OID of all possible actions for this instance"
    ::= { ptGTTGTTDBManagerEntry 252 }

ptGTTGTTDBManagerParentOID OBJECT-TYPE
    SYNTAX          OBJECT IDENTIFIER
    MAX-ACCESS      read-create
    STATUS          current
    DESCRIPTION     
            "The OID of the parent object for this instance"
    ::= { ptGTTGTTDBManagerEntry 253 }

ptGTTGTTDBManagerRowStatus OBJECT-TYPE
    SYNTAX          RowStatus
    MAX-ACCESS      read-create
    STATUS          current
    DESCRIPTION     
            "The row status for the GTTGTTDBManager table"
    ::= { ptGTTGTTDBManagerEntry 254 }

ptGTTGTTDBManagerIndex OBJECT-TYPE
    SYNTAX          Integer32 (-2147483648..2147483647)
    MAX-ACCESS      not-accessible
    STATUS          current
    DESCRIPTION     
            "The row number for the GTTGTTDBManager table"
    ::= { ptGTTGTTDBManagerEntry 255 }

ptGTTGTTDBSummary OBJECT IDENTIFIER
    ::= { ptGTTGTTDBManager 670 }

ptGTTGTTDBSummaryTable OBJECT-TYPE
    SYNTAX          SEQUENCE OF PtGTTGTTDBSummaryEntry
    MAX-ACCESS      not-accessible
    STATUS          current
    DESCRIPTION     
            "No description supplied in the proxy config file."
    ::= { ptGTTGTTDBSummary 1 }

ptGTTGTTDBSummaryEntry OBJECT-TYPE
    SYNTAX          PtGTTGTTDBSummaryEntry
    MAX-ACCESS      not-accessible
    STATUS          current
    DESCRIPTION     
            "A sequence of GTTGTTDBSummary attributes."
    INDEX           { ptConnGroupIndex, 
                      ptGTTGTTDBSummaryGTTDBManagerIndex, 
                      ptGTTGTTDBSummaryIndex }
    ::= { ptGTTGTTDBSummaryTable 1 }

PtGTTGTTDBSummaryEntry ::=
    SEQUENCE {
        ptGTTGTTDBSummaryDatabaseType   INTEGER,
        ptGTTGTTDBSummaryLastAction     INTEGER,
        ptGTTGTTDBSummaryLastModified   DisplayString,
        ptGTTGTTDBSummaryErrors         Integer32,
        ptGTTGTTDBSummaryGTCalledSearches Integer32,
        ptGTTGTTDBSummaryGTModifications Integer32,
        ptGTTGTTDBSummaryPCLists        Integer32,
        ptGTTGTTDBSummaryCommandLists   Integer32,
        ptGTTGTTDBSummaryCurrentStatus  DisplayString,
        ptGTTGTTDBSummaryGTCallingSearches  Integer32,
        ptGTTGTTDBSummaryGTOPCSearches  Integer32,
        ptGTTGTTDBSummaryGTTDBManagerIndex  Integer32,
        ptGTTGTTDBSummaryParentOID      OBJECT IDENTIFIER,
        ptGTTGTTDBSummaryRowStatus      RowStatus,
        ptGTTGTTDBSummaryIndex          Integer32
    }

ptGTTGTTDBSummaryDatabaseType OBJECT-TYPE
    SYNTAX          INTEGER { live(0), workspace(1), gtt(2) }
    MAX-ACCESS      read-only
    STATUS          current
    DESCRIPTION     
            "Database type (LIVE, WORKSPACE, and GTT for SEAS)."
    ::= { ptGTTGTTDBSummaryEntry 1 }

ptGTTGTTDBSummaryLastAction OBJECT-TYPE
    SYNTAX          INTEGER { notApplicable(0), manual(1), addRecords(2), 
                        deleteRecords(3), replaceDatabase(4), 
                        exportDatabase(5), loadDatabase(6), 
                        reloadDatabase(7), purgeDatabase(8), 
                        saveDatabase(9), commitLiveFromWorkspace(10), 
                        resetWorkspaceFromLive(11), addRecordsFailed(12), 
                        deleteRecordsFailed(13), 
                        replaceDatabaseFailed(14), 
                        exportDatabaseFailed(15), loadDatabaseFailed(16), 
                        reloadDatabaseFailed(17), 
                        purgeDatabaseFailed(18), saveDatabaseFailed(19), 
                        commitLiveFromWsFailed(20), 
                        resetWsFromLiveFailed(21), clearDatabase(22), 
                        clearDatabaseFailed(23) }
    MAX-ACCESS      read-only
    STATUS          current
    DESCRIPTION     
            "Last action performed on the database."
    ::= { ptGTTGTTDBSummaryEntry 2 }

ptGTTGTTDBSummaryLastModified OBJECT-TYPE
    SYNTAX          DisplayString (SIZE(0..255))
    MAX-ACCESS      read-only
    STATUS          current
    DESCRIPTION     
            "Date and time of Last Action."
    ::= { ptGTTGTTDBSummaryEntry 3 }

ptGTTGTTDBSummaryErrors OBJECT-TYPE
    SYNTAX          Integer32 (-2147483648..2147483647)
    MAX-ACCESS      read-only
    STATUS          current
    DESCRIPTION     
            "Number of errors during Last Action."
    ::= { ptGTTGTTDBSummaryEntry 4 }

ptGTTGTTDBSummaryGTCalledSearches OBJECT-TYPE
    SYNTAX          Integer32 (-2147483648..2147483647)
    MAX-ACCESS      read-only
    STATUS          current
    DESCRIPTION     
            "Number of GT Called Searches."
    ::= { ptGTTGTTDBSummaryEntry 5 }

ptGTTGTTDBSummaryGTModifications OBJECT-TYPE
    SYNTAX          Integer32 (-2147483648..2147483647)
    MAX-ACCESS      read-only
    STATUS          current
    DESCRIPTION     
            "Number of GT Modifications."
    ::= { ptGTTGTTDBSummaryEntry 6 }

ptGTTGTTDBSummaryPCLists OBJECT-TYPE
    SYNTAX          Integer32 (-2147483648..2147483647)
    MAX-ACCESS      read-only
    STATUS          current
    DESCRIPTION     
            "Number of PC Lists."
    ::= { ptGTTGTTDBSummaryEntry 7 }

ptGTTGTTDBSummaryCommandLists OBJECT-TYPE
    SYNTAX          Integer32 (-2147483648..2147483647)
    MAX-ACCESS      read-only
    STATUS          current
    DESCRIPTION     
            "Number of Command Lists."
    ::= { ptGTTGTTDBSummaryEntry 8 }

ptGTTGTTDBSummaryCurrentStatus OBJECT-TYPE
    SYNTAX          DisplayString (SIZE(0..255))
    MAX-ACCESS      read-only
    STATUS          current
    DESCRIPTION     
            "Current database status"
    ::= { ptGTTGTTDBSummaryEntry 9 }

ptGTTGTTDBSummaryGTCallingSearches OBJECT-TYPE
    SYNTAX          Integer32 (-2147483648..2147483647)
    MAX-ACCESS      read-only
    STATUS          current
    DESCRIPTION     
            "Number of GT Calling Searches."
    ::= { ptGTTGTTDBSummaryEntry 10 }

ptGTTGTTDBSummaryGTOPCSearches OBJECT-TYPE
    SYNTAX          Integer32 (-2147483648..2147483647)
    MAX-ACCESS      read-only
    STATUS          current
    DESCRIPTION     
            "Number of GT OPC Searches."
    ::= { ptGTTGTTDBSummaryEntry 11 }

ptGTTGTTDBSummaryGTTDBManagerIndex OBJECT-TYPE
    SYNTAX          Integer32 (-2147483648..2147483647)
    MAX-ACCESS      not-accessible
    STATUS          current
    DESCRIPTION     
            "This is the index of the parent type for this object.
             This parent type is GTTDBManager."
    ::= { ptGTTGTTDBSummaryEntry 242 }

ptGTTGTTDBSummaryParentOID OBJECT-TYPE
    SYNTAX          OBJECT IDENTIFIER
    MAX-ACCESS      read-create
    STATUS          current
    DESCRIPTION     
            "The OID of the parent object for this instance"
    ::= { ptGTTGTTDBSummaryEntry 253 }

ptGTTGTTDBSummaryRowStatus OBJECT-TYPE
    SYNTAX          RowStatus
    MAX-ACCESS      read-create
    STATUS          current
    DESCRIPTION     
            "The row status for the GTTGTTDBSummary table"
    ::= { ptGTTGTTDBSummaryEntry 254 }

ptGTTGTTDBSummaryIndex OBJECT-TYPE
    SYNTAX          Integer32 (-2147483648..2147483647)
    MAX-ACCESS      not-accessible
    STATUS          current
    DESCRIPTION     
            "The row number for the GTTGTTDBSummary table"
    ::= { ptGTTGTTDBSummaryEntry 255 }

ptGTTGTTDatabase OBJECT IDENTIFIER
    ::= { ptConnGroup 672 }

ptGTTGTTDatabaseTable OBJECT-TYPE
    SYNTAX          SEQUENCE OF PtGTTGTTDatabaseEntry
    MAX-ACCESS      not-accessible
    STATUS          current
    DESCRIPTION     
            "No description supplied in the proxy config file."
    ::= { ptGTTGTTDatabase 1 }

ptGTTGTTDatabaseEntry OBJECT-TYPE
    SYNTAX          PtGTTGTTDatabaseEntry
    MAX-ACCESS      not-accessible
    STATUS          current
    DESCRIPTION     
            "A sequence of GTTGTTDatabase attributes."
    INDEX           { ptConnGroupIndex, ptGTTGTTDatabaseIndex }
    ::= { ptGTTGTTDatabaseTable 1 }

PtGTTGTTDatabaseEntry ::=
    SEQUENCE {
        ptGTTGTTDatabaseType            INTEGER,
        ptGTTGTTDatabaseLastModified    DisplayString,
        ptGTTGTTDatabaseParentOID       OBJECT IDENTIFIER,
        ptGTTGTTDatabaseRowStatus       RowStatus,
        ptGTTGTTDatabaseIndex           Integer32
    }

ptGTTGTTDatabaseType OBJECT-TYPE
    SYNTAX          INTEGER { live(0), workspace(1), gtt(2) }
    MAX-ACCESS      read-only
    STATUS          current
    DESCRIPTION     
            "Database type (LIVE, WORKSPACE, and GTT for SEAS)."
    ::= { ptGTTGTTDatabaseEntry 1 }

ptGTTGTTDatabaseLastModified OBJECT-TYPE
    SYNTAX          DisplayString (SIZE(0..255))
    MAX-ACCESS      read-only
    STATUS          current
    DESCRIPTION     
            "Date/Time of last modification"
    ::= { ptGTTGTTDatabaseEntry 2 }

ptGTTGTTDatabaseParentOID OBJECT-TYPE
    SYNTAX          OBJECT IDENTIFIER
    MAX-ACCESS      read-create
    STATUS          current
    DESCRIPTION     
            "The OID of the parent object for this instance"
    ::= { ptGTTGTTDatabaseEntry 253 }

ptGTTGTTDatabaseRowStatus OBJECT-TYPE
    SYNTAX          RowStatus
    MAX-ACCESS      read-create
    STATUS          current
    DESCRIPTION     
            "The row status for the GTTGTTDatabase table"
    ::= { ptGTTGTTDatabaseEntry 254 }

ptGTTGTTDatabaseIndex OBJECT-TYPE
    SYNTAX          Integer32 (-2147483648..2147483647)
    MAX-ACCESS      not-accessible
    STATUS          current
    DESCRIPTION     
            "The row number for the GTTGTTDatabase table"
    ::= { ptGTTGTTDatabaseEntry 255 }

ptGTTBatchOperations OBJECT IDENTIFIER
    ::= { ptGTTGTTDatabase 667 }

ptGTTBatchOperationsTable OBJECT-TYPE
    SYNTAX          SEQUENCE OF PtGTTBatchOperationsEntry
    MAX-ACCESS      not-accessible
    STATUS          current
    DESCRIPTION     
            "No description supplied in the proxy config file."
    ::= { ptGTTBatchOperations 1 }

ptGTTBatchOperationsEntry OBJECT-TYPE
    SYNTAX          PtGTTBatchOperationsEntry
    MAX-ACCESS      not-accessible
    STATUS          current
    DESCRIPTION     
            "A sequence of GTTBatchOperations attributes."
    INDEX           { ptConnGroupIndex, 
                      ptGTTBatchOperationsGTTDatabaseIndex, 
                      ptGTTBatchOperationsIndex }
    ::= { ptGTTBatchOperationsTable 1 }

PtGTTBatchOperationsEntry ::=
    SEQUENCE {
        ptGTTBatchOperationsCurrentStatus DisplayString,
        ptGTTBatchOperationsLastAction  INTEGER,
        ptGTTBatchOperationsLastModified DisplayString,
        ptGTTBatchOperationsGTTDatabaseIndex    Integer32,
        ptGTTBatchOperationsActions     INTEGER,
        ptGTTBatchOperationsParentOID   OBJECT IDENTIFIER,
        ptGTTBatchOperationsRowStatus   RowStatus,
        ptGTTBatchOperationsIndex       Integer32
    }

ptGTTBatchOperationsCurrentStatus OBJECT-TYPE
    SYNTAX          DisplayString (SIZE(0..255))
    MAX-ACCESS      read-only
    STATUS          current
    DESCRIPTION     
            "Current database status"
    ::= { ptGTTBatchOperationsEntry 1 }

ptGTTBatchOperationsLastAction OBJECT-TYPE
    SYNTAX          INTEGER { notApplicable(0), manual(1), addRecords(2), 
                        deleteRecords(3), replaceDatabase(4), 
                        exportDatabase(5), loadDatabase(6), 
                        reloadDatabase(7), purgeDatabase(8), 
                        saveDatabase(9), commitLiveFromWorkspace(10), 
                        resetWorkspaceFromLive(11), addRecordsFailed(12), 
                        deleteRecordsFailed(13), 
                        replaceDatabaseFailed(14), 
                        exportDatabaseFailed(15), loadDatabaseFailed(16), 
                        reloadDatabaseFailed(17), 
                        purgeDatabaseFailed(18), saveDatabaseFailed(19), 
                        commitLiveFromWsFailed(20), 
                        resetWsFromLiveFailed(21), clearDatabase(22), 
                        clearDatabaseFailed(23) }
    MAX-ACCESS      read-only
    STATUS          current
    DESCRIPTION     
            "Last action performed on the database."
    ::= { ptGTTBatchOperationsEntry 2 }

ptGTTBatchOperationsLastModified OBJECT-TYPE
    SYNTAX          DisplayString (SIZE(0..255))
    MAX-ACCESS      read-only
    STATUS          current
    DESCRIPTION     
            "Date and time of Last Action."
    ::= { ptGTTBatchOperationsEntry 3 }

ptGTTBatchOperationsGTTDatabaseIndex OBJECT-TYPE
    SYNTAX          Integer32 (-2147483648..2147483647)
    MAX-ACCESS      not-accessible
    STATUS          current
    DESCRIPTION     
            "This is the index of the parent type for this object.
             This parent type is GTTDatabase."
    ::= { ptGTTBatchOperationsEntry 242 }

ptGTTBatchOperationsActions OBJECT-TYPE
    SYNTAX          INTEGER { addRecords(1), deleteRecords(2), 
                        replaceDatabase(3), exportDatabase(4), 
                        purgeDatabase(5), exportGTSearches(6) }
    MAX-ACCESS      read-create
    STATUS          current
    DESCRIPTION     
            "The OID of all possible actions for this instance"
    ::= { ptGTTBatchOperationsEntry 252 }

ptGTTBatchOperationsParentOID OBJECT-TYPE
    SYNTAX          OBJECT IDENTIFIER
    MAX-ACCESS      read-create
    STATUS          current
    DESCRIPTION     
            "The OID of the parent object for this instance"
    ::= { ptGTTBatchOperationsEntry 253 }

ptGTTBatchOperationsRowStatus OBJECT-TYPE
    SYNTAX          RowStatus
    MAX-ACCESS      read-create
    STATUS          current
    DESCRIPTION     
            "The row status for the GTTBatchOperations table"
    ::= { ptGTTBatchOperationsEntry 254 }

ptGTTBatchOperationsIndex OBJECT-TYPE
    SYNTAX          Integer32 (-2147483648..2147483647)
    MAX-ACCESS      not-accessible
    STATUS          current
    DESCRIPTION     
            "The row number for the GTTBatchOperations table"
    ::= { ptGTTBatchOperationsEntry 255 }

ptGTTGTSearchUtility OBJECT IDENTIFIER
    ::= { ptGTTGTTDatabase 685 }

ptGTTGTSearchUtilityTable OBJECT-TYPE
    SYNTAX          SEQUENCE OF PtGTTGTSearchUtilityEntry
    MAX-ACCESS      not-accessible
    STATUS          current
    DESCRIPTION     
            "No description supplied in the proxy config file."
    ::= { ptGTTGTSearchUtility 1 }

ptGTTGTSearchUtilityEntry OBJECT-TYPE
    SYNTAX          PtGTTGTSearchUtilityEntry
    MAX-ACCESS      not-accessible
    STATUS          current
    DESCRIPTION     
            "A sequence of GTTGTSearchUtility attributes."
    INDEX           { ptConnGroupIndex, 
                      ptGTTGTSearchUtilityGTTDatabaseIndex, 
                      ptGTTGTSearchUtilityIndex }
    ::= { ptGTTGTSearchUtilityTable 1 }

PtGTTGTSearchUtilityEntry ::=
    SEQUENCE {
        ptGTTGTSearchUtilityDBDefName   DisplayString,
        ptGTTGTSearchUtilityCalledDigits DisplayString,
        ptGTTGTSearchUtilityCalledGTI   INTEGER,
        ptGTTGTSearchUtilityCalledNP    INTEGER,
        ptGTTGTSearchUtilityCalledTT    INTEGER,
        ptGTTGTSearchUtilityCalledNAI   INTEGER,
        ptGTTGTSearchUtilityCallingDigits DisplayString,
        ptGTTGTSearchUtilityCallingGTI  INTEGER,
        ptGTTGTSearchUtilityCallingNP   INTEGER,
        ptGTTGTSearchUtilityCallingTT   INTEGER,
        ptGTTGTSearchUtilityCallingNAI  INTEGER,
        ptGTTGTSearchUtilityOPC         Integer32,
        ptGTTGTSearchUtilityCalledSearchRecord      DisplayString,
        ptGTTGTSearchUtilityCallingSearchRecord       DisplayString,
        ptGTTGTSearchUtilityOPCSearchRecord   DisplayString,
        ptGTTGTSearchUtilityDiagnosticMessage     DisplayString,
        ptGTTGTSearchUtilityAppliedCalledGTModName          DisplayString,
        ptGTTGTSearchUtilityAppliedCallingGTModName           DisplayString,
        ptGTTGTSearchUtilityPCListResult DisplayString,
        ptGTTGTSearchUtilityCalledSSN   INTEGER,
        ptGTTGTSearchUtilityCallingSSN  INTEGER,
        ptGTTGTSearchUtilityGTTDatabaseIndex    Integer32,
        ptGTTGTSearchUtilityActions     INTEGER,
        ptGTTGTSearchUtilityParentOID   OBJECT IDENTIFIER,
        ptGTTGTSearchUtilityRowStatus   RowStatus,
        ptGTTGTSearchUtilityIndex       Integer32
    }

ptGTTGTSearchUtilityDBDefName OBJECT-TYPE
    SYNTAX          DisplayString (SIZE(0..255))
    MAX-ACCESS      read-create
    STATUS          current
    DESCRIPTION     
            "GTT Database definition."
    ::= { ptGTTGTSearchUtilityEntry 1 }

ptGTTGTSearchUtilityCalledDigits OBJECT-TYPE
    SYNTAX          DisplayString (SIZE(0..255))
    MAX-ACCESS      read-create
    STATUS          current
    DESCRIPTION     
            "Global Title digits of SCCP called party."
    ::= { ptGTTGTSearchUtilityEntry 2 }

ptGTTGTSearchUtilityCalledGTI OBJECT-TYPE
    SYNTAX          INTEGER { gti0000(0), gti0001(1), gti0010(2), 
                        gti0011(3), gti0100(4) }
    MAX-ACCESS      read-create
    STATUS          current
    DESCRIPTION     
            "Global Title Indicator of SCCP called party."
    ::= { ptGTTGTSearchUtilityEntry 3 }

ptGTTGTSearchUtilityCalledNP OBJECT-TYPE
    SYNTAX          INTEGER { none(16) }
    MAX-ACCESS      read-create
    STATUS          current
    DESCRIPTION     
            "Numbering plan of SCCP called party."
    ::= { ptGTTGTSearchUtilityEntry 4 }

ptGTTGTSearchUtilityCalledTT OBJECT-TYPE
    SYNTAX          INTEGER { none(256) }
    MAX-ACCESS      read-create
    STATUS          current
    DESCRIPTION     
            "Translation type of SCCP called party."
    ::= { ptGTTGTSearchUtilityEntry 5 }

ptGTTGTSearchUtilityCalledNAI OBJECT-TYPE
    SYNTAX          INTEGER { none(128) }
    MAX-ACCESS      read-create
    STATUS          current
    DESCRIPTION     
            "Nature of Address of SCCP called party."
    ::= { ptGTTGTSearchUtilityEntry 6 }

ptGTTGTSearchUtilityCallingDigits OBJECT-TYPE
    SYNTAX          DisplayString (SIZE(0..255))
    MAX-ACCESS      read-create
    STATUS          current
    DESCRIPTION     
            "Global Title digits of SCCP calling party."
    ::= { ptGTTGTSearchUtilityEntry 7 }

ptGTTGTSearchUtilityCallingGTI OBJECT-TYPE
    SYNTAX          INTEGER { gti0000(0), gti0001(1), gti0010(2), 
                        gti0011(3), gti0100(4) }
    MAX-ACCESS      read-create
    STATUS          current
    DESCRIPTION     
            "Global Title Indicator of SCCP calling party."
    ::= { ptGTTGTSearchUtilityEntry 8 }

ptGTTGTSearchUtilityCallingNP OBJECT-TYPE
    SYNTAX          INTEGER { none(16) }
    MAX-ACCESS      read-create
    STATUS          current
    DESCRIPTION     
            "Numbering plan of SCCP calling party."
    ::= { ptGTTGTSearchUtilityEntry 9 }

ptGTTGTSearchUtilityCallingTT OBJECT-TYPE
    SYNTAX          INTEGER { none(256) }
    MAX-ACCESS      read-create
    STATUS          current
    DESCRIPTION     
            "Translation type of SCCP calling party."
    ::= { ptGTTGTSearchUtilityEntry 10 }

ptGTTGTSearchUtilityCallingNAI OBJECT-TYPE
    SYNTAX          INTEGER { none(128) }
    MAX-ACCESS      read-create
    STATUS          current
    DESCRIPTION     
            "Nature of Address of SCCP calling party."
    ::= { ptGTTGTSearchUtilityEntry 11 }

ptGTTGTSearchUtilityOPC OBJECT-TYPE
    SYNTAX          Integer32 (-2147483648..2147483647)
    MAX-ACCESS      read-create
    STATUS          current
    DESCRIPTION     
            "OPC of the MSU."
    ::= { ptGTTGTSearchUtilityEntry 12 }

ptGTTGTSearchUtilityCalledSearchRecord OBJECT-TYPE
    SYNTAX          DisplayString (SIZE(0..255))
    MAX-ACCESS      read-only
    STATUS          current
    DESCRIPTION     
            "Using the Called criteria an attempt is made to find a resultant Called Search Record within the DB Def provided. The result will be one of the following: \n- FOUND : Record found which yields a PC List Result. \n- FOUND > EPR X : A record was found which caused a \n query attempt for a Calling Search Record using \n EPR X. \n- NOT FOUND : No record was found. \n- NO SEARCH PEFORMED: An error was identified with the \n search criteria which prevented a query attempt."
    ::= { ptGTTGTSearchUtilityEntry 13 }

ptGTTGTSearchUtilityCallingSearchRecord OBJECT-TYPE
    SYNTAX          DisplayString (SIZE(0..255))
    MAX-ACCESS      read-only
    STATUS          current
    DESCRIPTION     
            "Using the Calling criteria an attempt is made to find a resultant Calling Search Record within the DB Def provided. The result will be one of the following: \n- FOUND : Record found which yields a PC List Result. \n- FOUND > EPR X : A record was found which caused a \n query attempt for an OPC Search Record using EPR X. \n- NOT FOUND : No record was found. \n- NO SEARCH PEFORMED: An error was identified with the \n search criteria which prevented a query attempt \n or a PC List Result was previously found."
    ::= { ptGTTGTSearchUtilityEntry 14 }

ptGTTGTSearchUtilityOPCSearchRecord OBJECT-TYPE
    SYNTAX          DisplayString (SIZE(0..255))
    MAX-ACCESS      read-only
    STATUS          current
    DESCRIPTION     
            "Using the OPC criteria an attempt is made to find a resultant OPC Search Record within the DB Def provided. The result will be one of the following: \n- FOUND : Record found which yields a PC List Result. \n- NOT FOUND : No record was found. \n- NO SEARCH PEFORMED: An error was identified with the \n search criteria which prevented a query attempt \n or a PC List Result was previously found."
    ::= { ptGTTGTSearchUtilityEntry 15 }

ptGTTGTSearchUtilityDiagnosticMessage OBJECT-TYPE
    SYNTAX          DisplayString (SIZE(0..255))
    MAX-ACCESS      read-only
    STATUS          current
    DESCRIPTION     
            "Search criteria is meant to be that of a valid MSU. However, if an error is detected in the search criteria, this message will alert the user to what is specifically wrong. If no errors detected, then SUCCESS will be displayed"
    ::= { ptGTTGTSearchUtilityEntry 16 }

ptGTTGTSearchUtilityAppliedCalledGTModName OBJECT-TYPE
    SYNTAX          DisplayString (SIZE(0..255))
    MAX-ACCESS      read-only
    STATUS          current
    DESCRIPTION     
            "GT Modification record associated with the Called Search Record which will be applied when routing the MSU."
    ::= { ptGTTGTSearchUtilityEntry 17 }

ptGTTGTSearchUtilityAppliedCallingGTModName OBJECT-TYPE
    SYNTAX          DisplayString (SIZE(0..255))
    MAX-ACCESS      read-only
    STATUS          current
    DESCRIPTION     
            "GT Modification record associated with the Calling Search Record which will be applied when routing the MSU."
    ::= { ptGTTGTSearchUtilityEntry 18 }

ptGTTGTSearchUtilityPCListResult OBJECT-TYPE
    SYNTAX          DisplayString (SIZE(0..255))
    MAX-ACCESS      read-only
    STATUS          current
    DESCRIPTION     
            "PC List which will be used for routing the MSU. This will display the PC List name used to route the MSU based on the supplied criteria. The PC List name will be prefaced by one of the following, indicating the search record used to choose the PC List: \n- CLD : The PC List associated with the Called Search Record is used. \n- CLG : The PC List associated with the Calling Search Record is used. \n- OPC : The PC List associated with the OPC Search Record is used. \n- DEFAULT : The default PC List is used. \n Possible results also include: \n- NONE: No PC List was identified, either because there was an error in the search criteria, or no Default PC List is defined."
    ::= { ptGTTGTSearchUtilityEntry 19 }

ptGTTGTSearchUtilityCalledSSN OBJECT-TYPE
    SYNTAX          INTEGER { none(256) }
    MAX-ACCESS      read-create
    STATUS          current
    DESCRIPTION     
            "Subsystem Number of SCCP called party."
    ::= { ptGTTGTSearchUtilityEntry 20 }

ptGTTGTSearchUtilityCallingSSN OBJECT-TYPE
    SYNTAX          INTEGER { none(256) }
    MAX-ACCESS      read-create
    STATUS          current
    DESCRIPTION     
            "Subsystem Number of SCCP calling party."
    ::= { ptGTTGTSearchUtilityEntry 21 }

ptGTTGTSearchUtilityGTTDatabaseIndex OBJECT-TYPE
    SYNTAX          Integer32 (-2147483648..2147483647)
    MAX-ACCESS      not-accessible
    STATUS          current
    DESCRIPTION     
            "This is the index of the parent type for this object.
             This parent type is GTTDatabase."
    ::= { ptGTTGTSearchUtilityEntry 242 }

ptGTTGTSearchUtilityActions OBJECT-TYPE
    SYNTAX          INTEGER { clearSearchCriteria(1), performSearch(2) }
    MAX-ACCESS      read-create
    STATUS          current
    DESCRIPTION     
            "The OID of all possible actions for this instance"
    ::= { ptGTTGTSearchUtilityEntry 252 }

ptGTTGTSearchUtilityParentOID OBJECT-TYPE
    SYNTAX          OBJECT IDENTIFIER
    MAX-ACCESS      read-create
    STATUS          current
    DESCRIPTION     
            "The OID of the parent object for this instance"
    ::= { ptGTTGTSearchUtilityEntry 253 }

ptGTTGTSearchUtilityRowStatus OBJECT-TYPE
    SYNTAX          RowStatus
    MAX-ACCESS      read-create
    STATUS          current
    DESCRIPTION     
            "The row status for the GTTGTSearchUtility table"
    ::= { ptGTTGTSearchUtilityEntry 254 }

ptGTTGTSearchUtilityIndex OBJECT-TYPE
    SYNTAX          Integer32 (-2147483648..2147483647)
    MAX-ACCESS      not-accessible
    STATUS          current
    DESCRIPTION     
            "The row number for the GTTGTSearchUtility table"
    ::= { ptGTTGTSearchUtilityEntry 255 }

ptGTTGTTDBDefManager OBJECT IDENTIFIER
    ::= { ptConnGroup 683 }

ptGTTGTTDBDefManagerTable OBJECT-TYPE
    SYNTAX          SEQUENCE OF PtGTTGTTDBDefManagerEntry
    MAX-ACCESS      not-accessible
    STATUS          current
    DESCRIPTION     
            "No description supplied in the proxy config file."
    ::= { ptGTTGTTDBDefManager 1 }

ptGTTGTTDBDefManagerEntry OBJECT-TYPE
    SYNTAX          PtGTTGTTDBDefManagerEntry
    MAX-ACCESS      not-accessible
    STATUS          current
    DESCRIPTION     
            "A sequence of GTTGTTDBDefManager attributes."
    INDEX           { ptConnGroupIndex, ptGTTGTTDBDefManagerIndex }
    ::= { ptGTTGTTDBDefManagerTable 1 }

PtGTTGTTDBDefManagerEntry ::=
    SEQUENCE {
        ptGTTGTTDBDefManagerGTTDBDefs   Integer32,
        ptGTTGTTDBDefManagerParentOID   OBJECT IDENTIFIER,
        ptGTTGTTDBDefManagerRowStatus   RowStatus,
        ptGTTGTTDBDefManagerIndex       Integer32
    }

ptGTTGTTDBDefManagerGTTDBDefs OBJECT-TYPE
    SYNTAX          Integer32 (-2147483648..2147483647)
    MAX-ACCESS      read-only
    STATUS          current
    DESCRIPTION     
            "Number of GTT Database Definitions."
    ::= { ptGTTGTTDBDefManagerEntry 1 }

ptGTTGTTDBDefManagerParentOID OBJECT-TYPE
    SYNTAX          OBJECT IDENTIFIER
    MAX-ACCESS      read-create
    STATUS          current
    DESCRIPTION     
            "The OID of the parent object for this instance"
    ::= { ptGTTGTTDBDefManagerEntry 253 }

ptGTTGTTDBDefManagerRowStatus OBJECT-TYPE
    SYNTAX          RowStatus
    MAX-ACCESS      read-create
    STATUS          current
    DESCRIPTION     
            "The row status for the GTTGTTDBDefManager table"
    ::= { ptGTTGTTDBDefManagerEntry 254 }

ptGTTGTTDBDefManagerIndex OBJECT-TYPE
    SYNTAX          Integer32 (-2147483648..2147483647)
    MAX-ACCESS      not-accessible
    STATUS          current
    DESCRIPTION     
            "The row number for the GTTGTTDBDefManager table"
    ::= { ptGTTGTTDBDefManagerEntry 255 }

ptGTTGTTDBDef OBJECT IDENTIFIER
    ::= { ptGTTGTTDBDefManager 684 }

ptGTTGTTDBDefTable OBJECT-TYPE
    SYNTAX          SEQUENCE OF PtGTTGTTDBDefEntry
    MAX-ACCESS      not-accessible
    STATUS          current
    DESCRIPTION     
            "No description supplied in the proxy config file."
    ::= { ptGTTGTTDBDef 1 }

ptGTTGTTDBDefEntry OBJECT-TYPE
    SYNTAX          PtGTTGTTDBDefEntry
    MAX-ACCESS      not-accessible
    STATUS          current
    DESCRIPTION     
            "A sequence of GTTGTTDBDef attributes."
    INDEX           { ptConnGroupIndex, 
                      ptGTTGTTDBDefGTTDBDefManagerIndex, 
                      ptGTTGTTDBDefIndex }
    ::= { ptGTTGTTDBDefTable 1 }

PtGTTGTTDBDefEntry ::=
    SEQUENCE {
        ptGTTGTTDBDefName               DisplayString,
        ptGTTGTTDBDefSS7Variant         INTEGER,
        ptGTTGTTDBDefGTDigitsFiller     INTEGER,
        ptGTTGTTDBDefDefaultPCListName  DisplayString,
        ptGTTGTTDBDefTranslateUDTS      INTEGER,
        ptGTTGTTDBDefPCDisplayFormat    DisplayString,
        ptGTTGTTDBDefPCRoutingFormat    DisplayString,
        ptGTTGTTDBDefPCListLoadshare    INTEGER,
        ptGTTGTTDBDefOPCLoopDetection   INTEGER,
        ptGTTGTTDBDefGTTDBDefManagerIndex Integer32,
        ptGTTGTTDBDefParentOID          OBJECT IDENTIFIER,
        ptGTTGTTDBDefRowStatus          RowStatus,
        ptGTTGTTDBDefIndex              Integer32
    }

ptGTTGTTDBDefName OBJECT-TYPE
    SYNTAX          DisplayString (SIZE(0..255))
    MAX-ACCESS      read-only
    STATUS          current
    DESCRIPTION     
            "GTT DB Definition Name attribute is a textual unique identifier. \nIt is used by all database records as a reference to the GTT DB Def object. It is suggested that these names be descriptive, yet easy to type to facilitate UI provisioning of the database. \nValid values: alphanumeric characters, dashes, and underscores (maximum size of 16). \nCannot start the name with reserved unset (case insensitive)."
    ::= { ptGTTGTTDBDefEntry 1 }

ptGTTGTTDBDefSS7Variant OBJECT-TYPE
    SYNTAX          INTEGER { itu(0), ansi(1), china(2), ntt(3), ttc(4) }
    MAX-ACCESS      read-create
    STATUS          current
    DESCRIPTION     
            "The SS7 Variant (ANSI, ITU, CHINA, NTT, and TTC) of the translation database definition. \nWhen assigning to a GTT NA, the SS7 Variant must be the same as defined the corresponding SCCP NA."
    ::= { ptGTTGTTDBDefEntry 2 }

ptGTTGTTDBDefGTDigitsFiller OBJECT-TYPE
    SYNTAX          INTEGER { zero(0), f(1) }
    MAX-ACCESS      read-create
    STATUS          current
    DESCRIPTION     
            "The Global Title digits filler sets the value that will be used when the translation of a Called or Calling Party Address results in an uneven number of digits. If it is odd, the final digit space will be filled with the value given here. Can either be F (0x0f) or ZERO (0x00)."
    ::= { ptGTTGTTDBDefEntry 3 }

ptGTTGTTDBDefDefaultPCListName OBJECT-TYPE
    SYNTAX          DisplayString (SIZE(0..255))
    MAX-ACCESS      read-create
    STATUS          current
    DESCRIPTION     
            "The Default Point Code List Name is the name of list giving destinations to be used for queried messages that do not match any other result. Use of this feature will result in NO translations failing. This is not a commonly used feature, as most operators chose to be explicit about what may or may not be translated through the STP. There are very valid reasons to NOT translate a particular message. \nSet the Default Point Code List Name to an empty string to disable this feature."
    ::= { ptGTTGTTDBDefEntry 4 }

ptGTTGTTDBDefTranslateUDTS OBJECT-TYPE
    SYNTAX          INTEGER { disabled(0), enabled(1) }
    MAX-ACCESS      read-create
    STATUS          current
    DESCRIPTION     
            "Enable or disable the translation of SCCP UDTS messages. \nWith proper translations, this flag should not be required. For example: if a remote node is responding to UDTS from this node with a Global Title routed UDTS of its own, circular routing could result. The Translate UDTS flag if set to DISABLED, would avoid this scenario. \nA UDTS is a SCCP level connectionless message used when the UDT message is undeliverable. The UDTS is essentially a report of the routing failure of the UDT."
    ::= { ptGTTGTTDBDefEntry 5 }

ptGTTGTTDBDefPCDisplayFormat OBJECT-TYPE
    SYNTAX          DisplayString (SIZE(0..255))
    MAX-ACCESS      read-create
    STATUS          current
    DESCRIPTION     
            "Point Code Display Format based on SS7 Variant. \n For ITU based, must be 14-bit compatible, for Japan 16-bit, while ANSI and China 24-bit. \n\n Valid options are: 8.8.8, 3.8.3, ff-ff, 4.4.6, 5.4.7, 3.4.7, 4.3.7, 4.6.4, 6.4.4, 4.7.3, 5.4.5, and Decimal. Note that the dash delimiter is also accepted (i.e. 8-8-8). \n\n For ANSI platforms using SNAMI, the format must be 8.8.8"
    ::= { ptGTTGTTDBDefEntry 6 }

ptGTTGTTDBDefPCRoutingFormat OBJECT-TYPE
    SYNTAX          DisplayString (SIZE(0..255))
    MAX-ACCESS      read-create
    STATUS          current
    DESCRIPTION     
            "Point Code Routing Format based on SS7 Variant. \n For ITU based, must be 14-bit compatible, for Japan 16-bit, while ANSI and China 24-bit. The x-y or x-y-z fields must be 8-bit or less. \n Valid options are: 8.8.8, 3.8.3, 4.4.6, 5.4.7, 3.4.7, 4.3.7, 4.6.4, 6.4.4, 4.7.3, and 5.4.5."
    ::= { ptGTTGTTDBDefEntry 7 }

ptGTTGTTDBDefPCListLoadshare OBJECT-TYPE
    SYNTAX          INTEGER { sls(0), tid(1) }
    MAX-ACCESS      read-create
    STATUS          current
    DESCRIPTION     
            "Used as the basis for traffic load sharing algorithms. SCCP messages classes 1 to 3 are sequence guaranteed. They may be loadshared using SLS or TCAP Transaction ID if TID is available in the message. SLS is the default. Selecting SLS means that all loadsharing of traffic will determined using the SLS of the message as the basis of the loadshare algorithms. Selecting TID means that an attempt will be made to extract the TID from the TCAP portion of the message and use that TID as the basis for the loadshare algorithms. If TID and class 1 or greater messages which do not contain TCAP Transaction IDs will be sequenced and loadshared based on the SLS value in message."
    ::= { ptGTTGTTDBDefEntry 8 }

ptGTTGTTDBDefOPCLoopDetection OBJECT-TYPE
    SYNTAX          INTEGER { disabled(0), enabled(1) }
    MAX-ACCESS      read-create
    STATUS          current
    DESCRIPTION     
            "Enable or disable loop detection based on OPC. \nIf set to ENABLED, GTT tranlated messages are prevented from being forwarded to the OPC of the original MSU. If no other point code is available in the translated PC List, the message is discarded. \nBy default, the attribute is set to DISABLED."
    ::= { ptGTTGTTDBDefEntry 9 }

ptGTTGTTDBDefGTTDBDefManagerIndex OBJECT-TYPE
    SYNTAX          Integer32 (-2147483648..2147483647)
    MAX-ACCESS      not-accessible
    STATUS          current
    DESCRIPTION     
            "This is the index of the parent type for this object.
             This parent type is GTTDBDefManager."
    ::= { ptGTTGTTDBDefEntry 242 }

ptGTTGTTDBDefParentOID OBJECT-TYPE
    SYNTAX          OBJECT IDENTIFIER
    MAX-ACCESS      read-create
    STATUS          current
    DESCRIPTION     
            "The OID of the parent object for this instance"
    ::= { ptGTTGTTDBDefEntry 253 }

ptGTTGTTDBDefRowStatus OBJECT-TYPE
    SYNTAX          RowStatus
    MAX-ACCESS      read-create
    STATUS          current
    DESCRIPTION     
            "The row status for the GTTGTTDBDef table"
    ::= { ptGTTGTTDBDefEntry 254 }

ptGTTGTTDBDefIndex OBJECT-TYPE
    SYNTAX          Integer32 (-2147483648..2147483647)
    MAX-ACCESS      not-accessible
    STATUS          current
    DESCRIPTION     
            "The row number for the GTTGTTDBDef table"
    ::= { ptGTTGTTDBDefEntry 255 }

ptmsaMSAC OBJECT IDENTIFIER
    ::= { ptConnGroup 961 }

ptmsaMSACTable OBJECT-TYPE
    SYNTAX          SEQUENCE OF PtmsaMSACEntry
    MAX-ACCESS      not-accessible
    STATUS          current
    DESCRIPTION     
            "No description supplied in the proxy config file."
    ::= { ptmsaMSAC 1 }

ptmsaMSACEntry OBJECT-TYPE
    SYNTAX          PtmsaMSACEntry
    MAX-ACCESS      not-accessible
    STATUS          current
    DESCRIPTION     
            "A sequence of msaMSAC attributes."
    INDEX           { ptConnGroupIndex, ptmsaMSACIndex }
    ::= { ptmsaMSACTable 1 }

PtmsaMSACEntry ::=
    SEQUENCE {
        ptmsaMSACName                   DisplayString,
        ptmsaMSACParentOID              OBJECT IDENTIFIER,
        ptmsaMSACRowStatus              RowStatus,
        ptmsaMSACIndex                  Integer32
    }

ptmsaMSACName OBJECT-TYPE
    SYNTAX          DisplayString (SIZE(0..255))
    MAX-ACCESS      read-only
    STATUS          current
    DESCRIPTION     
            "Memory Space Accounting (MSA) Container Name."
    ::= { ptmsaMSACEntry 1 }

ptmsaMSACParentOID OBJECT-TYPE
    SYNTAX          OBJECT IDENTIFIER
    MAX-ACCESS      read-create
    STATUS          current
    DESCRIPTION     
            "The OID of the parent object for this instance"
    ::= { ptmsaMSACEntry 253 }

ptmsaMSACRowStatus OBJECT-TYPE
    SYNTAX          RowStatus
    MAX-ACCESS      read-create
    STATUS          current
    DESCRIPTION     
            "The row status for the msaMSAC table"
    ::= { ptmsaMSACEntry 254 }

ptmsaMSACIndex OBJECT-TYPE
    SYNTAX          Integer32 (-2147483648..2147483647)
    MAX-ACCESS      not-accessible
    STATUS          current
    DESCRIPTION     
            "The row number for the msaMSAC table"
    ::= { ptmsaMSACEntry 255 }

ptmsaMSA OBJECT IDENTIFIER
    ::= { ptmsaMSAC 962 }

ptmsaMSATable OBJECT-TYPE
    SYNTAX          SEQUENCE OF PtmsaMSAEntry
    MAX-ACCESS      not-accessible
    STATUS          current
    DESCRIPTION     
            "No description supplied in the proxy config file."
    ::= { ptmsaMSA 1 }

ptmsaMSAEntry OBJECT-TYPE
    SYNTAX          PtmsaMSAEntry
    MAX-ACCESS      not-accessible
    STATUS          current
    DESCRIPTION     
            "A sequence of msaMSA attributes."
    INDEX           { ptConnGroupIndex, ptmsaMSAMSACIndex, ptmsaMSAIndex }
    ::= { ptmsaMSATable 1 }

PtmsaMSAEntry ::=
    SEQUENCE {
        ptmsaMSAName                    DisplayString,
        ptmsaMSACurrentSize             Integer32,
        ptmsaMSAMaximumSize             Integer32,
        ptmsaMSACurrentUsage            Integer32,
        ptmsaMSAThreshold1              Integer32,
        ptmsaMSAThreshold2              Integer32,
        ptmsaMSAThreshold3              Integer32,
        ptmsaMSAReporting               INTEGER,
        ptmsaMSAMSACIndex               Integer32,
        ptmsaMSAParentOID               OBJECT IDENTIFIER,
        ptmsaMSARowStatus               RowStatus,
        ptmsaMSAIndex                   Integer32
    }

ptmsaMSAName OBJECT-TYPE
    SYNTAX          DisplayString (SIZE(0..255))
    MAX-ACCESS      read-only
    STATUS          current
    DESCRIPTION     
            "Unique name of the Memory Space Accounting object. \nIf applicable, this attribute may serve as a link to the associated object."
    ::= { ptmsaMSAEntry 1 }

ptmsaMSACurrentSize OBJECT-TYPE
    SYNTAX          Integer32 (-2147483648..2147483647)
    MAX-ACCESS      read-only
    STATUS          current
    DESCRIPTION     
            "Current size of the Memory Space Accounting object."
    ::= { ptmsaMSAEntry 2 }

ptmsaMSAMaximumSize OBJECT-TYPE
    SYNTAX          Integer32 (-2147483648..2147483647)
    MAX-ACCESS      read-only
    STATUS          current
    DESCRIPTION     
            "Maximum size of the Memory Space Accounting object."
    ::= { ptmsaMSAEntry 3 }

ptmsaMSACurrentUsage OBJECT-TYPE
    SYNTAX          Integer32
    MAX-ACCESS      read-only
    STATUS          current
    DESCRIPTION     
            "Current usage of the Memory Space Accounting object."
    ::= { ptmsaMSAEntry 4 }

ptmsaMSAThreshold1 OBJECT-TYPE
    SYNTAX          Integer32
    MAX-ACCESS      read-create
    STATUS          current
    DESCRIPTION     
            "Threshold 1 of the Memory Space Accounting object (0-99 %). \nMust be set to less than Threshold 2. \nA minor alarm is raised when the current usage reaches this threshold. The alarm is cleared when the usage no longer crosses the threshold."
    ::= { ptmsaMSAEntry 5 }

ptmsaMSAThreshold2 OBJECT-TYPE
    SYNTAX          Integer32
    MAX-ACCESS      read-create
    STATUS          current
    DESCRIPTION     
            "Threshold 2 of the Memory Space Accounting object (0-99 %). \nMust be set to less than Threshold 3. \nA minor alarm is raised when the current usage reaches this threshold. The alarm is cleared when the usage no longer crosses the threshold."
    ::= { ptmsaMSAEntry 6 }

ptmsaMSAThreshold3 OBJECT-TYPE
    SYNTAX          Integer32
    MAX-ACCESS      read-create
    STATUS          current
    DESCRIPTION     
            "Threshold 3 of the Memory Space Accounting object (0-99 %). \nA major alarm is raised when the current usage reaches this threshold. The alarm is cleared when the usage no longer crosses the threshold."
    ::= { ptmsaMSAEntry 7 }

ptmsaMSAReporting OBJECT-TYPE
    SYNTAX          INTEGER { disabled(0), enabled(1) }
    MAX-ACCESS      read-create
    STATUS          current
    DESCRIPTION     
            "Memory Space Accounting alarm reporting (ENABLED/DISABLED)"
    ::= { ptmsaMSAEntry 8 }

ptmsaMSAMSACIndex OBJECT-TYPE
    SYNTAX          Integer32 (-2147483648..2147483647)
    MAX-ACCESS      not-accessible
    STATUS          current
    DESCRIPTION     
            "This is the index of the parent type for this object.
             This parent type is MSAC."
    ::= { ptmsaMSAEntry 242 }

ptmsaMSAParentOID OBJECT-TYPE
    SYNTAX          OBJECT IDENTIFIER
    MAX-ACCESS      read-create
    STATUS          current
    DESCRIPTION     
            "The OID of the parent object for this instance"
    ::= { ptmsaMSAEntry 253 }

ptmsaMSARowStatus OBJECT-TYPE
    SYNTAX          RowStatus
    MAX-ACCESS      read-create
    STATUS          current
    DESCRIPTION     
            "The row status for the msaMSA table"
    ::= { ptmsaMSAEntry 254 }

ptmsaMSAIndex OBJECT-TYPE
    SYNTAX          Integer32 (-2147483648..2147483647)
    MAX-ACCESS      not-accessible
    STATUS          current
    DESCRIPTION     
            "The row number for the msaMSA table"
    ::= { ptmsaMSAEntry 255 }

ptLIBEVEventManager OBJECT IDENTIFIER
    ::= { ptConnGroup 981 }

ptLIBEVEventManagerTable OBJECT-TYPE
    SYNTAX          SEQUENCE OF PtLIBEVEventManagerEntry
    MAX-ACCESS      not-accessible
    STATUS          current
    DESCRIPTION     
            "No description supplied in the proxy config file."
    ::= { ptLIBEVEventManager 1 }

ptLIBEVEventManagerEntry OBJECT-TYPE
    SYNTAX          PtLIBEVEventManagerEntry
    MAX-ACCESS      not-accessible
    STATUS          current
    DESCRIPTION     
            "A sequence of LIBEVEventManager attributes."
    INDEX           { ptConnGroupIndex, ptLIBEVEventManagerIndex }
    ::= { ptLIBEVEventManagerTable 1 }

PtLIBEVEventManagerEntry ::=
    SEQUENCE {
        ptLIBEVEventManagerCriticalAlarms Integer32,
        ptLIBEVEventManagerMajorAlarms  Integer32,
        ptLIBEVEventManagerMinorAlarms  Integer32,
        ptLIBEVEventManagerWarningAlarms Integer32,
        ptLIBEVEventManagerClearedAlarms Integer32,
        ptLIBEVEventManagerName         DisplayString,
        ptLIBEVEventManagerParentOID    OBJECT IDENTIFIER,
        ptLIBEVEventManagerRowStatus    RowStatus,
        ptLIBEVEventManagerIndex        Integer32
    }

ptLIBEVEventManagerCriticalAlarms OBJECT-TYPE
    SYNTAX          Integer32 (-2147483648..2147483647)
    MAX-ACCESS      read-only
    STATUS          current
    DESCRIPTION     
            "No description supplied in the proxy config file."
    ::= { ptLIBEVEventManagerEntry 1 }

ptLIBEVEventManagerMajorAlarms OBJECT-TYPE
    SYNTAX          Integer32 (-2147483648..2147483647)
    MAX-ACCESS      read-only
    STATUS          current
    DESCRIPTION     
            "No description supplied in the proxy config file."
    ::= { ptLIBEVEventManagerEntry 2 }

ptLIBEVEventManagerMinorAlarms OBJECT-TYPE
    SYNTAX          Integer32 (-2147483648..2147483647)
    MAX-ACCESS      read-only
    STATUS          current
    DESCRIPTION     
            "No description supplied in the proxy config file."
    ::= { ptLIBEVEventManagerEntry 3 }

ptLIBEVEventManagerWarningAlarms OBJECT-TYPE
    SYNTAX          Integer32 (-2147483648..2147483647)
    MAX-ACCESS      read-only
    STATUS          current
    DESCRIPTION     
            "No description supplied in the proxy config file."
    ::= { ptLIBEVEventManagerEntry 4 }

ptLIBEVEventManagerClearedAlarms OBJECT-TYPE
    SYNTAX          Integer32 (-2147483648..2147483647)
    MAX-ACCESS      read-only
    STATUS          current
    DESCRIPTION     
            "No description supplied in the proxy config file."
    ::= { ptLIBEVEventManagerEntry 5 }

ptLIBEVEventManagerName OBJECT-TYPE
    SYNTAX          DisplayString (SIZE(0..255))
    MAX-ACCESS      read-only
    STATUS          current
    DESCRIPTION     
            "No description supplied in the proxy config file."
    ::= { ptLIBEVEventManagerEntry 6 }

ptLIBEVEventManagerParentOID OBJECT-TYPE
    SYNTAX          OBJECT IDENTIFIER
    MAX-ACCESS      read-create
    STATUS          current
    DESCRIPTION     
            "The OID of the parent object for this instance"
    ::= { ptLIBEVEventManagerEntry 253 }

ptLIBEVEventManagerRowStatus OBJECT-TYPE
    SYNTAX          RowStatus
    MAX-ACCESS      read-create
    STATUS          current
    DESCRIPTION     
            "The row status for the LIBEVEventManager table"
    ::= { ptLIBEVEventManagerEntry 254 }

ptLIBEVEventManagerIndex OBJECT-TYPE
    SYNTAX          Integer32 (-2147483648..2147483647)
    MAX-ACCESS      not-accessible
    STATUS          current
    DESCRIPTION     
            "The row number for the LIBEVEventManager table"
    ::= { ptLIBEVEventManagerEntry 255 }

ptLIBEVEvent OBJECT IDENTIFIER
    ::= { ptLIBEVEventManager 982 }

ptLIBEVEventTable OBJECT-TYPE
    SYNTAX          SEQUENCE OF PtLIBEVEventEntry
    MAX-ACCESS      not-accessible
    STATUS          current
    DESCRIPTION     
            "No description supplied in the proxy config file."
    ::= { ptLIBEVEvent 1 }

ptLIBEVEventEntry OBJECT-TYPE
    SYNTAX          PtLIBEVEventEntry
    MAX-ACCESS      not-accessible
    STATUS          current
    DESCRIPTION     
            "A sequence of LIBEVEvent attributes."
    INDEX           { ptConnGroupIndex, ptLIBEVEventEventManagerIndex, 
                      ptLIBEVEventIndex }
    ::= { ptLIBEVEventTable 1 }

PtLIBEVEventEntry ::=
    SEQUENCE {
        ptLIBEVEventCrossObjLinkDn      Integer32,
        ptLIBEVEventEventFlag           Integer32,
        ptLIBEVEventSeverity            INTEGER,
        ptLIBEVEventEventName           DisplayString,
        ptLIBEVEventEventNumber         Integer32,
        ptLIBEVEventInstanceId          Integer32,
        ptLIBEVEventTrapIndicator       Integer32,
        ptLIBEVEventProbableCause       INTEGER,
        ptLIBEVEventTrapType            INTEGER,
        ptLIBEVEventClearType           INTEGER,
        ptLIBEVEventEventTimeNumber     Integer32,
        ptLIBEVEventEventTime           DisplayString,
        ptLIBEVEventEventText           DisplayString,
        ptLIBEVEventEventContext        DisplayString,
        ptLIBEVEventAckFlag             Integer32,
        ptLIBEVEventAckBy               DisplayString,
        ptLIBEVEventAckTime             DisplayString,
        ptLIBEVEventClearFlag           Integer32,
        ptLIBEVEventClearBy             DisplayString,
        ptLIBEVEventClearTime           DisplayString,
        ptLIBEVEventEventTabIndex       Integer32,
        ptLIBEVEventCommentFlag         Integer32,
        ptLIBEVEventComment             DisplayString,
        ptLIBEVEventEventManagerIndex   Integer32,
        ptLIBEVEventParentOID           OBJECT IDENTIFIER,
        ptLIBEVEventRowStatus           RowStatus,
        ptLIBEVEventIndex               Integer32
    }

ptLIBEVEventCrossObjLinkDn OBJECT-TYPE
    SYNTAX          Integer32
    MAX-ACCESS      read-only
    STATUS          current
    DESCRIPTION     
            "No description supplied in the proxy config file."
    ::= { ptLIBEVEventEntry 1 }

ptLIBEVEventEventFlag OBJECT-TYPE
    SYNTAX          Integer32 (-2147483648..2147483647)
    MAX-ACCESS      read-only
    STATUS          current
    DESCRIPTION     
            "No description supplied in the proxy config file."
    ::= { ptLIBEVEventEntry 2 }

ptLIBEVEventSeverity OBJECT-TYPE
    SYNTAX          INTEGER { critical(1), major(2), minor(3), 
                        warning(4), cleared(5) }
    MAX-ACCESS      read-only
    STATUS          current
    DESCRIPTION     
            "The value indicates the severity of the alarm Following values are defined: CRITICAL MAJOR MINOR WARNING"
    ::= { ptLIBEVEventEntry 3 }

ptLIBEVEventEventName OBJECT-TYPE
    SYNTAX          DisplayString (SIZE(0..255))
    MAX-ACCESS      read-only
    STATUS          current
    DESCRIPTION     
            "The type name is the name of the type of the alarm"
    ::= { ptLIBEVEventEntry 4 }

ptLIBEVEventEventNumber OBJECT-TYPE
    SYNTAX          Integer32 (-2147483648..2147483647)
    MAX-ACCESS      read-only
    STATUS          current
    DESCRIPTION     
            "Every alarm has unique number that identifies the alarm"
    ::= { ptLIBEVEventEntry 5 }

ptLIBEVEventInstanceId OBJECT-TYPE
    SYNTAX          Integer32 (-2147483648..2147483647)
    MAX-ACCESS      read-only
    STATUS          current
    DESCRIPTION     
            "The Instance Id is incremented by the application every time it raises the alarm Every alarm raised by the application has unique Type number and Instance Id combination"
    ::= { ptLIBEVEventEntry 6 }

ptLIBEVEventTrapIndicator OBJECT-TYPE
    SYNTAX          Integer32 (-2147483648..2147483647)
    MAX-ACCESS      read-only
    STATUS          current
    DESCRIPTION     
            "No description supplied in the proxy config file."
    ::= { ptLIBEVEventEntry 7 }

ptLIBEVEventProbableCause OBJECT-TYPE
    SYNTAX          INTEGER { undefined(0), 
                        applicationSubsystemFailure(2), 
                        callEstablishmentError(4), 
                        communicationsProtocolError(5), 
                        communicationsSubsystemError(6), 
                        configurationOrCustomizationError(7), 
                        congestion(8), corruptData(9), 
                        cpuCyclesLimitExceeded(10), 
                        datasetOrModemError(11), degradedSignal(12), 
                        dteDceInterfaceError(13), enclosureDoorOpen(14), 
                        equipmentMalfunction(15), fileError(17), 
                        fireDetected(18), floodDetected(19), 
                        framingError(20), inputOutputDeviceError(23), 
                        inputDeviceError(24), lanError(25), 
                        localNodeTransmissionError(27), lossOfFrame(28), 
                        lossOfSignal(29), multiplexerProblem(31), 
                        outOfMemory(32), outputDeviceError(33), 
                        performanceDegraded(34), powerProblem(35), 
                        processorProblem(37), queueSizeExceeded(39), 
                        receiveFailure(40), 
                        remoteNodeTransmissionError(42), 
                        resourceAtOrNearCapacity(43), 
                        responseTimeExcessive(44), 
                        retransmissionRateExcessive(45), 
                        softwareError(46), 
                        softwareProgramAbnormallyTerminated(47), 
                        softwareProgramError(48), 
                        storageCapacityProblem(49), thresholdCrossed(51), 
                        timingProblem(52), transmitFailure(54), 
                        underlyingResourceUnavailable(56), 
                        versionMismatch(57) }
    MAX-ACCESS      read-only
    STATUS          current
    DESCRIPTION     
            "The probable cause identities the possible cause of the alarm"
    ::= { ptLIBEVEventEntry 8 }

ptLIBEVEventTrapType OBJECT-TYPE
    SYNTAX          INTEGER { undefined(1), communicationalarm(2), 
                        environmentalarm(3), equipmentalarm(4), 
                        processingalarm(10), qualityofservicealarm(11) }
    MAX-ACCESS      read-only
    STATUS          current
    DESCRIPTION     
            "It describes the type of the trap for the alarm"
    ::= { ptLIBEVEventEntry 9 }

ptLIBEVEventClearType OBJECT-TYPE
    SYNTAX          INTEGER { fmic(1), oic(2), undefined(3) }
    MAX-ACCESS      read-only
    STATUS          current
    DESCRIPTION     
            "No description supplied in the proxy config file."
    ::= { ptLIBEVEventEntry 10 }

ptLIBEVEventEventTimeNumber OBJECT-TYPE
    SYNTAX          Integer32 (-2147483648..2147483647)
    MAX-ACCESS      read-only
    STATUS          current
    DESCRIPTION     
            "No description supplied in the proxy config file."
    ::= { ptLIBEVEventEntry 11 }

ptLIBEVEventEventTime OBJECT-TYPE
    SYNTAX          DisplayString (SIZE(0..255))
    MAX-ACCESS      read-only
    STATUS          current
    DESCRIPTION     
            "The event time is the time of the occurrence of the alarm"
    ::= { ptLIBEVEventEntry 12 }

ptLIBEVEventEventText OBJECT-TYPE
    SYNTAX          DisplayString (SIZE(0..255))
    MAX-ACCESS      read-only
    STATUS          current
    DESCRIPTION     
            "describes the alarm"
    ::= { ptLIBEVEventEntry 13 }

ptLIBEVEventEventContext OBJECT-TYPE
    SYNTAX          DisplayString (SIZE(0..255))
    MAX-ACCESS      read-only
    STATUS          current
    DESCRIPTION     
            "describes the proxy object that raised the alarm"
    ::= { ptLIBEVEventEntry 14 }

ptLIBEVEventAckFlag OBJECT-TYPE
    SYNTAX          Integer32 (-2147483648..2147483647)
    MAX-ACCESS      read-only
    STATUS          current
    DESCRIPTION     
            "No description supplied in the proxy config file."
    ::= { ptLIBEVEventEntry 15 }

ptLIBEVEventAckBy OBJECT-TYPE
    SYNTAX          DisplayString (SIZE(0..255))
    MAX-ACCESS      read-create
    STATUS          current
    DESCRIPTION     
            "The field for manually acknowledging the alarm"
    ::= { ptLIBEVEventEntry 16 }

ptLIBEVEventAckTime OBJECT-TYPE
    SYNTAX          DisplayString (SIZE(0..255))
    MAX-ACCESS      read-only
    STATUS          current
    DESCRIPTION     
            "The Ack Time is the time at which the alarm is acknowledged"
    ::= { ptLIBEVEventEntry 17 }

ptLIBEVEventClearFlag OBJECT-TYPE
    SYNTAX          Integer32 (-2147483648..2147483647)
    MAX-ACCESS      read-only
    STATUS          current
    DESCRIPTION     
            "No description supplied in the proxy config file."
    ::= { ptLIBEVEventEntry 18 }

ptLIBEVEventClearBy OBJECT-TYPE
    SYNTAX          DisplayString (SIZE(0..255))
    MAX-ACCESS      read-create
    STATUS          current
    DESCRIPTION     
            "The field for manually clearing the alarm"
    ::= { ptLIBEVEventEntry 19 }

ptLIBEVEventClearTime OBJECT-TYPE
    SYNTAX          DisplayString (SIZE(0..255))
    MAX-ACCESS      read-only
    STATUS          current
    DESCRIPTION     
            "The Clear time is the time at which the alarm is manually cleared"
    ::= { ptLIBEVEventEntry 20 }

ptLIBEVEventEventTabIndex OBJECT-TYPE
    SYNTAX          Integer32 (-2147483648..2147483647)
    MAX-ACCESS      read-only
    STATUS          current
    DESCRIPTION     
            "No description supplied in the proxy config file."
    ::= { ptLIBEVEventEntry 21 }

ptLIBEVEventCommentFlag OBJECT-TYPE
    SYNTAX          Integer32 (-2147483648..2147483647)
    MAX-ACCESS      read-only
    STATUS          current
    DESCRIPTION     
            "No description supplied in the proxy config file."
    ::= { ptLIBEVEventEntry 22 }

ptLIBEVEventComment OBJECT-TYPE
    SYNTAX          DisplayString (SIZE(0..255))
    MAX-ACCESS      read-create
    STATUS          current
    DESCRIPTION     
            "The field for manually entering a comment for the alarm"
    ::= { ptLIBEVEventEntry 23 }

ptLIBEVEventEventManagerIndex OBJECT-TYPE
    SYNTAX          Integer32 (-2147483648..2147483647)
    MAX-ACCESS      not-accessible
    STATUS          current
    DESCRIPTION     
            "This is the index of the parent type for this object.
             This parent type is EventManager."
    ::= { ptLIBEVEventEntry 242 }

ptLIBEVEventParentOID OBJECT-TYPE
    SYNTAX          OBJECT IDENTIFIER
    MAX-ACCESS      read-create
    STATUS          current
    DESCRIPTION     
            "The OID of the parent object for this instance"
    ::= { ptLIBEVEventEntry 253 }

ptLIBEVEventRowStatus OBJECT-TYPE
    SYNTAX          RowStatus
    MAX-ACCESS      read-create
    STATUS          current
    DESCRIPTION     
            "The row status for the LIBEVEvent table"
    ::= { ptLIBEVEventEntry 254 }

ptLIBEVEventIndex OBJECT-TYPE
    SYNTAX          Integer32 (-2147483648..2147483647)
    MAX-ACCESS      not-accessible
    STATUS          current
    DESCRIPTION     
            "The row number for the LIBEVEvent table"
    ::= { ptLIBEVEventEntry 255 }

ptuppUserProfiles OBJECT IDENTIFIER
    ::= { ptConnGroup 1021 }

ptuppUserProfilesTable OBJECT-TYPE
    SYNTAX          SEQUENCE OF PtuppUserProfilesEntry
    MAX-ACCESS      not-accessible
    STATUS          current
    DESCRIPTION     
            "No description supplied in the proxy config file."
    ::= { ptuppUserProfiles 1 }

ptuppUserProfilesEntry OBJECT-TYPE
    SYNTAX          PtuppUserProfilesEntry
    MAX-ACCESS      not-accessible
    STATUS          current
    DESCRIPTION     
            "A sequence of uppUserProfiles attributes."
    INDEX           { ptConnGroupIndex, ptuppUserProfilesIndex }
    ::= { ptuppUserProfilesTable 1 }

PtuppUserProfilesEntry ::=
    SEQUENCE {
        ptuppUserProfilesParentOID      OBJECT IDENTIFIER,
        ptuppUserProfilesRowStatus      RowStatus,
        ptuppUserProfilesIndex          Integer32
    }

ptuppUserProfilesParentOID OBJECT-TYPE
    SYNTAX          OBJECT IDENTIFIER
    MAX-ACCESS      read-create
    STATUS          current
    DESCRIPTION     
            "The OID of the parent object for this instance"
    ::= { ptuppUserProfilesEntry 253 }

ptuppUserProfilesRowStatus OBJECT-TYPE
    SYNTAX          RowStatus
    MAX-ACCESS      read-create
    STATUS          current
    DESCRIPTION     
            "The row status for the uppUserProfiles table"
    ::= { ptuppUserProfilesEntry 254 }

ptuppUserProfilesIndex OBJECT-TYPE
    SYNTAX          Integer32 (-2147483648..2147483647)
    MAX-ACCESS      not-accessible
    STATUS          current
    DESCRIPTION     
            "The row number for the uppUserProfiles table"
    ::= { ptuppUserProfilesEntry 255 }

ptuppProfile OBJECT IDENTIFIER
    ::= { ptuppUserProfiles 1022 }

ptuppProfileTable OBJECT-TYPE
    SYNTAX          SEQUENCE OF PtuppProfileEntry
    MAX-ACCESS      not-accessible
    STATUS          current
    DESCRIPTION     
            "No description supplied in the proxy config file."
    ::= { ptuppProfile 1 }

ptuppProfileEntry OBJECT-TYPE
    SYNTAX          PtuppProfileEntry
    MAX-ACCESS      not-accessible
    STATUS          current
    DESCRIPTION     
            "A sequence of uppProfile attributes."
    INDEX           { ptConnGroupIndex, ptuppProfileUserProfilesIndex, 
                      ptuppProfileIndex }
    ::= { ptuppProfileTable 1 }

PtuppProfileEntry ::=
    SEQUENCE {
        ptuppProfileProfileName         DisplayString,
        ptuppProfileNumberOfUsers       Integer32,
        ptuppProfileUserProfilesIndex   Integer32,
        ptuppProfileParentOID           OBJECT IDENTIFIER,
        ptuppProfileRowStatus           RowStatus,
        ptuppProfileIndex               Integer32
    }

ptuppProfileProfileName OBJECT-TYPE
    SYNTAX          DisplayString (SIZE(0..255))
    MAX-ACCESS      read-only
    STATUS          current
    DESCRIPTION     
            "This field displays the name of the profile. All users assigned the current profile are listed below."
    ::= { ptuppProfileEntry 1 }

ptuppProfileNumberOfUsers OBJECT-TYPE
    SYNTAX          Integer32 (-2147483648..2147483647)
    MAX-ACCESS      read-only
    STATUS          current
    DESCRIPTION     
            "This field displays the number of users attached to the profile."
    ::= { ptuppProfileEntry 2 }

ptuppProfileUserProfilesIndex OBJECT-TYPE
    SYNTAX          Integer32 (-2147483648..2147483647)
    MAX-ACCESS      not-accessible
    STATUS          current
    DESCRIPTION     
            "This is the index of the parent type for this object.
             This parent type is UserProfiles."
    ::= { ptuppProfileEntry 242 }

ptuppProfileParentOID OBJECT-TYPE
    SYNTAX          OBJECT IDENTIFIER
    MAX-ACCESS      read-create
    STATUS          current
    DESCRIPTION     
            "The OID of the parent object for this instance"
    ::= { ptuppProfileEntry 253 }

ptuppProfileRowStatus OBJECT-TYPE
    SYNTAX          RowStatus
    MAX-ACCESS      read-create
    STATUS          current
    DESCRIPTION     
            "The row status for the uppProfile table"
    ::= { ptuppProfileEntry 254 }

ptuppProfileIndex OBJECT-TYPE
    SYNTAX          Integer32 (-2147483648..2147483647)
    MAX-ACCESS      not-accessible
    STATUS          current
    DESCRIPTION     
            "The row number for the uppProfile table"
    ::= { ptuppProfileEntry 255 }

ptuppUser OBJECT IDENTIFIER
    ::= { ptuppProfile 1023 }

ptuppUserTable OBJECT-TYPE
    SYNTAX          SEQUENCE OF PtuppUserEntry
    MAX-ACCESS      not-accessible
    STATUS          current
    DESCRIPTION     
            "No description supplied in the proxy config file."
    ::= { ptuppUser 1 }

ptuppUserEntry OBJECT-TYPE
    SYNTAX          PtuppUserEntry
    MAX-ACCESS      not-accessible
    STATUS          current
    DESCRIPTION     
            "A sequence of uppUser attributes."
    INDEX           { ptConnGroupIndex, ptuppUserUserProfilesIndex, 
                      ptuppUserProfileIndex, ptuppUserIndex }
    ::= { ptuppUserTable 1 }

PtuppUserEntry ::=
    SEQUENCE {
        ptuppUserUserName               DisplayString,
        ptuppUserProfile                INTEGER,
        ptuppUserUserProfilesIndex      Integer32,
        ptuppUserProfileIndex           Integer32,
        ptuppUserParentOID              OBJECT IDENTIFIER,
        ptuppUserRowStatus              RowStatus,
        ptuppUserIndex                  Integer32
    }

ptuppUserUserName OBJECT-TYPE
    SYNTAX          DisplayString (SIZE(0..255))
    MAX-ACCESS      read-only
    STATUS          current
    DESCRIPTION     
            "This field displays the Name of the user."
    ::= { ptuppUserEntry 1 }

ptuppUserProfile OBJECT-TYPE
    SYNTAX          INTEGER { unprofiled(-1), ss7admin(0), monitor(1), 
                        sccpOperator(2), mtpOperator(3) }
    MAX-ACCESS      read-create
    STATUS          current
    DESCRIPTION     
            "This field displays the Name of the profile. Edit to assign the user a different profile."
    ::= { ptuppUserEntry 2 }

ptuppUserUserProfilesIndex OBJECT-TYPE
    SYNTAX          Integer32 (-2147483648..2147483647)
    MAX-ACCESS      not-accessible
    STATUS          current
    DESCRIPTION     
            "This is the index of the parent type for this object.
             This parent type is UserProfiles."
    ::= { ptuppUserEntry 242 }

ptuppUserProfileIndex OBJECT-TYPE
    SYNTAX          Integer32 (-2147483648..2147483647)
    MAX-ACCESS      not-accessible
    STATUS          current
    DESCRIPTION     
            "This is the index of the parent type for this object.
             This parent type is Profile."
    ::= { ptuppUserEntry 243 }

ptuppUserParentOID OBJECT-TYPE
    SYNTAX          OBJECT IDENTIFIER
    MAX-ACCESS      read-create
    STATUS          current
    DESCRIPTION     
            "The OID of the parent object for this instance"
    ::= { ptuppUserEntry 253 }

ptuppUserRowStatus OBJECT-TYPE
    SYNTAX          RowStatus
    MAX-ACCESS      read-create
    STATUS          current
    DESCRIPTION     
            "The row status for the uppUser table"
    ::= { ptuppUserEntry 254 }

ptuppUserIndex OBJECT-TYPE
    SYNTAX          Integer32 (-2147483648..2147483647)
    MAX-ACCESS      not-accessible
    STATUS          current
    DESCRIPTION     
            "The row number for the uppUser table"
    ::= { ptuppUserEntry 255 }

ptuppRADIUS OBJECT IDENTIFIER
    ::= { ptConnGroup 1024 }

ptuppRADIUSTable OBJECT-TYPE
    SYNTAX          SEQUENCE OF PtuppRADIUSEntry
    MAX-ACCESS      not-accessible
    STATUS          current
    DESCRIPTION     
            "No description supplied in the proxy config file."
    ::= { ptuppRADIUS 1 }

ptuppRADIUSEntry OBJECT-TYPE
    SYNTAX          PtuppRADIUSEntry
    MAX-ACCESS      not-accessible
    STATUS          current
    DESCRIPTION     
            "A sequence of uppRADIUS attributes."
    INDEX           { ptConnGroupIndex, ptuppRADIUSIndex }
    ::= { ptuppRADIUSTable 1 }

PtuppRADIUSEntry ::=
    SEQUENCE {
        ptuppRADIUSStatus               INTEGER,
        ptuppRADIUSActions              INTEGER,
        ptuppRADIUSParentOID            OBJECT IDENTIFIER,
        ptuppRADIUSRowStatus            RowStatus,
        ptuppRADIUSIndex                Integer32
    }

ptuppRADIUSStatus OBJECT-TYPE
    SYNTAX          INTEGER { disabled(0), enabled(1) }
    MAX-ACCESS      read-only
    STATUS          current
    DESCRIPTION     
            "Current status of RADIUS support (ENABLED/DISABLED)."
    ::= { ptuppRADIUSEntry 1 }

ptuppRADIUSActions OBJECT-TYPE
    SYNTAX          INTEGER { enable(1), disable(2) }
    MAX-ACCESS      read-create
    STATUS          current
    DESCRIPTION     
            "The OID of all possible actions for this instance"
    ::= { ptuppRADIUSEntry 252 }

ptuppRADIUSParentOID OBJECT-TYPE
    SYNTAX          OBJECT IDENTIFIER
    MAX-ACCESS      read-create
    STATUS          current
    DESCRIPTION     
            "The OID of the parent object for this instance"
    ::= { ptuppRADIUSEntry 253 }

ptuppRADIUSRowStatus OBJECT-TYPE
    SYNTAX          RowStatus
    MAX-ACCESS      read-create
    STATUS          current
    DESCRIPTION     
            "The row status for the uppRADIUS table"
    ::= { ptuppRADIUSEntry 254 }

ptuppRADIUSIndex OBJECT-TYPE
    SYNTAX          Integer32 (-2147483648..2147483647)
    MAX-ACCESS      not-accessible
    STATUS          current
    DESCRIPTION     
            "The row number for the uppRADIUS table"
    ::= { ptuppRADIUSEntry 255 }

ptuppRADIUSServer OBJECT IDENTIFIER
    ::= { ptuppRADIUS 1025 }

ptuppRADIUSServerTable OBJECT-TYPE
    SYNTAX          SEQUENCE OF PtuppRADIUSServerEntry
    MAX-ACCESS      not-accessible
    STATUS          current
    DESCRIPTION     
            "No description supplied in the proxy config file."
    ::= { ptuppRADIUSServer 1 }

ptuppRADIUSServerEntry OBJECT-TYPE
    SYNTAX          PtuppRADIUSServerEntry
    MAX-ACCESS      not-accessible
    STATUS          current
    DESCRIPTION     
            "A sequence of uppRADIUSServer attributes."
    INDEX           { ptConnGroupIndex, ptuppRADIUSServerRADIUSIndex, 
                      ptuppRADIUSServerIndex }
    ::= { ptuppRADIUSServerTable 1 }

PtuppRADIUSServerEntry ::=
    SEQUENCE {
        ptuppRADIUSServerState          INTEGER,
        ptuppRADIUSServerAddress        DisplayString,
        ptuppRADIUSServerSecret         DisplayString,
        ptuppRADIUSServerTimeout        Integer32,
        ptuppRADIUSServerRADIUSIndex    Integer32,
        ptuppRADIUSServerActions        INTEGER,
        ptuppRADIUSServerParentOID      OBJECT IDENTIFIER,
        ptuppRADIUSServerRowStatus      RowStatus,
        ptuppRADIUSServerIndex          Integer32
    }

ptuppRADIUSServerState OBJECT-TYPE
    SYNTAX          INTEGER { unused(0), available(1), unavailable(2) }
    MAX-ACCESS      read-only
    STATUS          current
    DESCRIPTION     
            "The current state of this RADIUS server. \nUNUSED: This server has never been needed, so no information is available. \nAVAILABLE: This server responded to its most recent request. \nUNAVAILABLE: This server failed to respond to its most recent request."
    ::= { ptuppRADIUSServerEntry 1 }

ptuppRADIUSServerAddress OBJECT-TYPE
    SYNTAX          DisplayString (SIZE(0..255))
    MAX-ACCESS      read-only
    STATUS          current
    DESCRIPTION     
            "The location of the RADIUS server. \nCan be a hostname or IP address, with optional \ntrailing :port. The default RADIUS port is used if \nno port is specified. DNS is not supported, so \nall hostnames used must be added to /etc/hosts."
    ::= { ptuppRADIUSServerEntry 2 }

ptuppRADIUSServerSecret OBJECT-TYPE
    SYNTAX          DisplayString (SIZE(0..255))
    MAX-ACCESS      read-only
    STATUS          current
    DESCRIPTION     
            "The shared secret key of the RADIUS server."
    ::= { ptuppRADIUSServerEntry 3 }

ptuppRADIUSServerTimeout OBJECT-TYPE
    SYNTAX          Integer32 (-2147483648..2147483647)
    MAX-ACCESS      read-create
    STATUS          current
    DESCRIPTION     
            "How long to wait for a response (in seconds) from the server."
    ::= { ptuppRADIUSServerEntry 4 }

ptuppRADIUSServerRADIUSIndex OBJECT-TYPE
    SYNTAX          Integer32 (-2147483648..2147483647)
    MAX-ACCESS      not-accessible
    STATUS          current
    DESCRIPTION     
            "This is the index of the parent type for this object.
             This parent type is RADIUS."
    ::= { ptuppRADIUSServerEntry 242 }

ptuppRADIUSServerActions OBJECT-TYPE
    SYNTAX          INTEGER { moveUp(1), moveDown(2) }
    MAX-ACCESS      read-create
    STATUS          current
    DESCRIPTION     
            "The OID of all possible actions for this instance"
    ::= { ptuppRADIUSServerEntry 252 }

ptuppRADIUSServerParentOID OBJECT-TYPE
    SYNTAX          OBJECT IDENTIFIER
    MAX-ACCESS      read-create
    STATUS          current
    DESCRIPTION     
            "The OID of the parent object for this instance"
    ::= { ptuppRADIUSServerEntry 253 }

ptuppRADIUSServerRowStatus OBJECT-TYPE
    SYNTAX          RowStatus
    MAX-ACCESS      read-create
    STATUS          current
    DESCRIPTION     
            "The row status for the uppRADIUSServer table"
    ::= { ptuppRADIUSServerEntry 254 }

ptuppRADIUSServerIndex OBJECT-TYPE
    SYNTAX          Integer32 (-2147483648..2147483647)
    MAX-ACCESS      not-accessible
    STATUS          current
    DESCRIPTION     
            "The row number for the uppRADIUSServer table"
    ::= { ptuppRADIUSServerEntry 255 }

ptIOHWIOManager OBJECT IDENTIFIER
    ::= { ptConnGroup 1081 }

ptIOHWIOManagerTable OBJECT-TYPE
    SYNTAX          SEQUENCE OF PtIOHWIOManagerEntry
    MAX-ACCESS      not-accessible
    STATUS          current
    DESCRIPTION     
            "No description supplied in the proxy config file."
    ::= { ptIOHWIOManager 1 }

ptIOHWIOManagerEntry OBJECT-TYPE
    SYNTAX          PtIOHWIOManagerEntry
    MAX-ACCESS      not-accessible
    STATUS          current
    DESCRIPTION     
            "A sequence of IOHWIOManager attributes."
    INDEX           { ptConnGroupIndex, ptIOHWIOManagerIndex }
    ::= { ptIOHWIOManagerTable 1 }

PtIOHWIOManagerEntry ::=
    SEQUENCE {
        ptIOHWIOManagerSlotNumber       Integer32,
        ptIOHWIOManagerHostName         DisplayString,
        ptIOHWIOManagerSerialNumber     DisplayString,
        ptIOHWIOManagerRMSHostIP        DisplayString,
        ptIOHWIOManagerTDMCardPhysicalSlot  DisplayString,
        ptIOHWIOManagerCardType         INTEGER,
        ptIOHWIOManagerFeature          INTEGER,
        ptIOHWIOManagerErrors           INTEGER,
        ptIOHWIOManagerProvisioning     INTEGER,
        ptIOHWIOManagerMaxLSL           Integer32,
        ptIOHWIOManagerMaxHSLAnnexA     Integer32,
        ptIOHWIOManagerMaxHSLATM        Integer32,
        ptIOHWIOManagerLSLSupport       INTEGER,
        ptIOHWIOManagerHSLAnnexASupport INTEGER,
        ptIOHWIOManagerHSLATMSupport    INTEGER,
        ptIOHWIOManagerSelectConfiguration  INTEGER,
        ptIOHWIOManagerRestartRequired  INTEGER,
        ptIOHWIOManagerProtocolVariant  INTEGER,
        ptIOHWIOManagerActions          INTEGER,
        ptIOHWIOManagerParentOID        OBJECT IDENTIFIER,
        ptIOHWIOManagerRowStatus        RowStatus,
        ptIOHWIOManagerIndex            Integer32
    }

ptIOHWIOManagerSlotNumber OBJECT-TYPE
    SYNTAX          Integer32 (-2147483648..2147483647)
    MAX-ACCESS      read-only
    STATUS          current
    DESCRIPTION     
            "Location of the board in the chassis."
    ::= { ptIOHWIOManagerEntry 1 }

ptIOHWIOManagerHostName OBJECT-TYPE
    SYNTAX          DisplayString (SIZE(0..255))
    MAX-ACCESS      read-only
    STATUS          current
    DESCRIPTION     
            "Host name of this board."
    ::= { ptIOHWIOManagerEntry 2 }

ptIOHWIOManagerSerialNumber OBJECT-TYPE
    SYNTAX          DisplayString (SIZE(0..255))
    MAX-ACCESS      read-only
    STATUS          current
    DESCRIPTION     
            "Serial number of this board."
    ::= { ptIOHWIOManagerEntry 3 }

ptIOHWIOManagerRMSHostIP OBJECT-TYPE
    SYNTAX          DisplayString (SIZE(0..255))
    MAX-ACCESS      read-only
    STATUS          current
    DESCRIPTION     
            "IP Address of the hosting RMS Server. Optional attribute only applicable for TDMs on DSC SWe. Hidden on other platforms."
    ::= { ptIOHWIOManagerEntry 4 }

ptIOHWIOManagerTDMCardPhysicalSlot OBJECT-TYPE
    SYNTAX          DisplayString (SIZE(0..255))
    MAX-ACCESS      read-only
    STATUS          current
    DESCRIPTION     
            "Location of the TDM card within the RMS Server chassis. Optional attribute only applicable for TDMs on DSC SWe. Hidden on other platforms."
    ::= { ptIOHWIOManagerEntry 5 }

ptIOHWIOManagerCardType OBJECT-TYPE
    SYNTAX          INTEGER { cpc388(0), cpc358(1), cpc308(2), cpc324(3), 
                        cpc308a(4), amc304(5), amc308(6), amc318(7), 
                        amc348(8), pce382(9) }
    MAX-ACCESS      read-only
    STATUS          current
    DESCRIPTION     
            "Hardware model name for the board."
    ::= { ptIOHWIOManagerEntry 13 }

ptIOHWIOManagerFeature OBJECT-TYPE
    SYNTAX          INTEGER { notLogged(0), logged(1), overridden(2) }
    MAX-ACCESS      read-create
    STATUS          current
    DESCRIPTION     
            "Overall log control must be LOGGED to receive any logs."
    ::= { ptIOHWIOManagerEntry 15 }

ptIOHWIOManagerErrors OBJECT-TYPE
    SYNTAX          INTEGER { notLogged(0), logged(1), overridden(2) }
    MAX-ACCESS      read-create
    STATUS          current
    DESCRIPTION     
            "Logging of errored function calls to board API or library functions. Values: LOGGED, NOT_LOGGED. Value OVERRIDDEN indicates the debug FEATURE is NOT_LOGGED."
    ::= { ptIOHWIOManagerEntry 16 }

ptIOHWIOManagerProvisioning OBJECT-TYPE
    SYNTAX          INTEGER { notLogged(0), logged(1), overridden(2) }
    MAX-ACCESS      read-create
    STATUS          current
    DESCRIPTION     
            "Explanatory logs regarding user input. Values: LOGGED, NOT_LOGGED. Value OVERRIDDEN indicates the debug FEATURE is NOT_LOGGED."
    ::= { ptIOHWIOManagerEntry 17 }

ptIOHWIOManagerMaxLSL OBJECT-TYPE
    SYNTAX          Integer32 (-2147483648..2147483647)
    MAX-ACCESS      read-only
    STATUS          current
    DESCRIPTION     
            "Current max number of channelized low speed TDM channels"
    ::= { ptIOHWIOManagerEntry 22 }

ptIOHWIOManagerMaxHSLAnnexA OBJECT-TYPE
    SYNTAX          Integer32 (-2147483648..2147483647)
    MAX-ACCESS      read-only
    STATUS          current
    DESCRIPTION     
            "Current max number of AnnexA or unchannelized high speed TDM channels"
    ::= { ptIOHWIOManagerEntry 23 }

ptIOHWIOManagerMaxHSLATM OBJECT-TYPE
    SYNTAX          Integer32 (-2147483648..2147483647)
    MAX-ACCESS      read-only
    STATUS          current
    DESCRIPTION     
            "Current max number of ATM channels."
    ::= { ptIOHWIOManagerEntry 24 }

ptIOHWIOManagerLSLSupport OBJECT-TYPE
    SYNTAX          INTEGER { disabled(0), enabled(1) }
    MAX-ACCESS      read-only
    STATUS          current
    DESCRIPTION     
            "Indicated whether support for the link type is available on the installed hardware."
    ::= { ptIOHWIOManagerEntry 30 }

ptIOHWIOManagerHSLAnnexASupport OBJECT-TYPE
    SYNTAX          INTEGER { disabled(0), enabled(1) }
    MAX-ACCESS      read-only
    STATUS          current
    DESCRIPTION     
            "Indicated whether support for the link type is available on the installed hardware."
    ::= { ptIOHWIOManagerEntry 31 }

ptIOHWIOManagerHSLATMSupport OBJECT-TYPE
    SYNTAX          INTEGER { disabled(0), enabled(1) }
    MAX-ACCESS      read-only
    STATUS          current
    DESCRIPTION     
            "Indicated whether support for the link type is available on the installed hardware."
    ::= { ptIOHWIOManagerEntry 32 }

ptIOHWIOManagerSelectConfiguration OBJECT-TYPE
    SYNTAX          INTEGER { channels12800(0), channels6420(1), 
                        channels040(2), channels6404(3), channels024(4), 
                        channels008(5) }
    MAX-ACCESS      read-create
    STATUS          current
    DESCRIPTION     
            "Select the channel capabilities, in order: \n low speed TDM - channelized - (LSL), \n high speed TDM - unchannelized, Q.703 Annnex A - (HSL AnnexA), \n high speed ATM - ATM SAAL NNI - (HSL ATM). \nThis defines internal resource distribution. This slot must be restarted for the selection to take effect."
    ::= { ptIOHWIOManagerEntry 60 }

ptIOHWIOManagerRestartRequired OBJECT-TYPE
    SYNTAX          INTEGER { no(0), yes(1) }
    MAX-ACCESS      read-only
    STATUS          current
    DESCRIPTION     
            "Is a card restart required in order to have the selected configuration? Changing the Select Configuration requires a restart of this card for the new values to take effect."
    ::= { ptIOHWIOManagerEntry 61 }

ptIOHWIOManagerProtocolVariant OBJECT-TYPE
    SYNTAX          INTEGER { ansiItu(1), japan(2) }
    MAX-ACCESS      read-create
    STATUS          current
    DESCRIPTION     
            "Variant for low speed protocol. Either of ANSI-ITU or JAPAN. The application must be restarted for the selection to take effect."
    ::= { ptIOHWIOManagerEntry 62 }

ptIOHWIOManagerActions OBJECT-TYPE
    SYNTAX          INTEGER { restoreDebugDefaults(1) }
    MAX-ACCESS      read-create
    STATUS          current
    DESCRIPTION     
            "The OID of all possible actions for this instance"
    ::= { ptIOHWIOManagerEntry 252 }

ptIOHWIOManagerParentOID OBJECT-TYPE
    SYNTAX          OBJECT IDENTIFIER
    MAX-ACCESS      read-create
    STATUS          current
    DESCRIPTION     
            "The OID of the parent object for this instance"
    ::= { ptIOHWIOManagerEntry 253 }

ptIOHWIOManagerRowStatus OBJECT-TYPE
    SYNTAX          RowStatus
    MAX-ACCESS      read-create
    STATUS          current
    DESCRIPTION     
            "The row status for the IOHWIOManager table"
    ::= { ptIOHWIOManagerEntry 254 }

ptIOHWIOManagerIndex OBJECT-TYPE
    SYNTAX          Integer32 (-2147483648..2147483647)
    MAX-ACCESS      not-accessible
    STATUS          current
    DESCRIPTION     
            "The row number for the IOHWIOManager table"
    ::= { ptIOHWIOManagerEntry 255 }

ptIOHWLSLChannels OBJECT IDENTIFIER
    ::= { ptIOHWIOManager 1082 }

ptIOHWLSLChannelsTable OBJECT-TYPE
    SYNTAX          SEQUENCE OF PtIOHWLSLChannelsEntry
    MAX-ACCESS      not-accessible
    STATUS          current
    DESCRIPTION     
            "No description supplied in the proxy config file."
    ::= { ptIOHWLSLChannels 1 }

ptIOHWLSLChannelsEntry OBJECT-TYPE
    SYNTAX          PtIOHWLSLChannelsEntry
    MAX-ACCESS      not-accessible
    STATUS          current
    DESCRIPTION     
            "A sequence of IOHWLSLChannels attributes."
    INDEX           { ptConnGroupIndex, ptIOHWLSLChannelsIOManagerIndex, 
                      ptIOHWLSLChannelsIndex }
    ::= { ptIOHWLSLChannelsTable 1 }

PtIOHWLSLChannelsEntry ::=
    SEQUENCE {
        ptIOHWLSLChannelsState          INTEGER,
        ptIOHWLSLChannelsLicense        INTEGER,
        ptIOHWLSLChannelsUseRepeatFISU  INTEGER,
        ptIOHWLSLChannelsIOManagerIndex Integer32,
        ptIOHWLSLChannelsActions        INTEGER,
        ptIOHWLSLChannelsParentOID      OBJECT IDENTIFIER,
        ptIOHWLSLChannelsRowStatus      RowStatus,
        ptIOHWLSLChannelsIndex          Integer32
    }

ptIOHWLSLChannelsState OBJECT-TYPE
    SYNTAX          INTEGER { activated(0), deactivated(1), failed(2) }
    MAX-ACCESS      read-only
    STATUS          current
    DESCRIPTION     
            "Link Manager state"
    ::= { ptIOHWLSLChannelsEntry 4 }

ptIOHWLSLChannelsLicense OBJECT-TYPE
    SYNTAX          INTEGER { unlicensed(0), disconnected(1), 
                        licensed(2), unknown(3) }
    MAX-ACCESS      read-only
    STATUS          current
    DESCRIPTION     
            "TDM license state: Licensed, Unlicensed, Disconnected"
    ::= { ptIOHWLSLChannelsEntry 18 }

ptIOHWLSLChannelsUseRepeatFISU OBJECT-TYPE
    SYNTAX          INTEGER { disabled(0), enabled(1) }
    MAX-ACCESS      read-create
    STATUS          current
    DESCRIPTION     
            "To be used only when link failures occur in the absence of clock faults and miss-configuration. Increases FISUs on the line but decreases performance."
    ::= { ptIOHWLSLChannelsEntry 60 }

ptIOHWLSLChannelsIOManagerIndex OBJECT-TYPE
    SYNTAX          Integer32 (-2147483648..2147483647)
    MAX-ACCESS      not-accessible
    STATUS          current
    DESCRIPTION     
            "This is the index of the parent type for this object.
             This parent type is IOManager."
    ::= { ptIOHWLSLChannelsEntry 242 }

ptIOHWLSLChannelsActions OBJECT-TYPE
    SYNTAX          INTEGER { activate(1), deactivate(2) }
    MAX-ACCESS      read-create
    STATUS          current
    DESCRIPTION     
            "The OID of all possible actions for this instance"
    ::= { ptIOHWLSLChannelsEntry 252 }

ptIOHWLSLChannelsParentOID OBJECT-TYPE
    SYNTAX          OBJECT IDENTIFIER
    MAX-ACCESS      read-create
    STATUS          current
    DESCRIPTION     
            "The OID of the parent object for this instance"
    ::= { ptIOHWLSLChannelsEntry 253 }

ptIOHWLSLChannelsRowStatus OBJECT-TYPE
    SYNTAX          RowStatus
    MAX-ACCESS      read-create
    STATUS          current
    DESCRIPTION     
            "The row status for the IOHWLSLChannels table"
    ::= { ptIOHWLSLChannelsEntry 254 }

ptIOHWLSLChannelsIndex OBJECT-TYPE
    SYNTAX          Integer32 (-2147483648..2147483647)
    MAX-ACCESS      not-accessible
    STATUS          current
    DESCRIPTION     
            "The row number for the IOHWLSLChannels table"
    ::= { ptIOHWLSLChannelsEntry 255 }

ptIOHWLSLChannel OBJECT IDENTIFIER
    ::= { ptIOHWLSLChannels 1099 }

ptIOHWLSLChannelTable OBJECT-TYPE
    SYNTAX          SEQUENCE OF PtIOHWLSLChannelEntry
    MAX-ACCESS      not-accessible
    STATUS          current
    DESCRIPTION     
            "No description supplied in the proxy config file."
    ::= { ptIOHWLSLChannel 1 }

ptIOHWLSLChannelEntry OBJECT-TYPE
    SYNTAX          PtIOHWLSLChannelEntry
    MAX-ACCESS      not-accessible
    STATUS          current
    DESCRIPTION     
            "A sequence of IOHWLSLChannel attributes."
    INDEX           { ptConnGroupIndex, ptIOHWLSLChannelIOManagerIndex, 
                      ptIOHWLSLChannelLSLChannelsIndex, 
                      ptIOHWLSLChannelIndex }
    ::= { ptIOHWLSLChannelTable 1 }

PtIOHWLSLChannelEntry ::=
    SEQUENCE {
        ptIOHWLSLChannelChannelNumber   Integer32,
        ptIOHWLSLChannelPort            INTEGER,
        ptIOHWLSLChannelTimeSlot        INTEGER,
        ptIOHWLSLChannelBaudRate        INTEGER,
        ptIOHWLSLChannelLoopbackMode    INTEGER,
        ptIOHWLSLChannelMTP3API         INTEGER,
        ptIOHWLSLChannelLSSU            INTEGER,
        ptIOHWLSLChannelFISUAndMSU      INTEGER,
        ptIOHWLSLChannelCLLI            DisplayString,
        ptIOHWLSLChannelSupportDebug    DisplayString,
        ptIOHWLSLChannelL3Use           INTEGER,
        ptIOHWLSLChannelIOManagerIndex  Integer32,
        ptIOHWLSLChannelLSLChannelsIndex Integer32,
        ptIOHWLSLChannelParentOID       OBJECT IDENTIFIER,
        ptIOHWLSLChannelRowStatus       RowStatus,
        ptIOHWLSLChannelIndex           Integer32
    }

ptIOHWLSLChannelChannelNumber OBJECT-TYPE
    SYNTAX          Integer32 (-2147483648..2147483647)
    MAX-ACCESS      read-only
    STATUS          current
    DESCRIPTION     
            "The number of the Signaling Channel being mapped"
    ::= { ptIOHWLSLChannelEntry 1 }

ptIOHWLSLChannelPort OBJECT-TYPE
    SYNTAX          INTEGER { port0(0), port1(1), port2(2), port3(3), 
                        port4(4), port5(5), port6(6), port7(7), 
                        monitorPort(8), notConfigured(9), port8(10) }
    MAX-ACCESS      read-create
    STATUS          current
    DESCRIPTION     
            "The number of the I/O port with the physical connection to the link"
    ::= { ptIOHWLSLChannelEntry 2 }

ptIOHWLSLChannelTimeSlot OBJECT-TYPE
    SYNTAX          INTEGER { notConfigured(0) }
    MAX-ACCESS      read-create
    STATUS          current
    DESCRIPTION     
            "Timeslot on the link (1-24 T1, 1-31 E1)"
    ::= { ptIOHWLSLChannelEntry 3 }

ptIOHWLSLChannelBaudRate OBJECT-TYPE
    SYNTAX          INTEGER { ds064k(0), ds0a56k(1), baud48k(2), 
                        baud48kRev(3), baudTtc48k(4) }
    MAX-ACCESS      read-create
    STATUS          current
    DESCRIPTION     
            "Baud rate for the timeslot. 64K uses all 8 bits. 56K uses 7 of 8 bits and discards the LSB. 48K uses 6 of 8 bits and discards the 2 LSBs. 48K_REV uses 6 of 8 bits and discards the two MSBs. TTC_48K uses 6 of 8 bits and discards the LSB and MSB."
    ::= { ptIOHWLSLChannelEntry 4 }

ptIOHWLSLChannelLoopbackMode OBJECT-TYPE
    SYNTAX          INTEGER { disabled(0), enabled(1) }
    MAX-ACCESS      read-create
    STATUS          current
    DESCRIPTION     
            "Redirects incoming data on port and timeslot back to sender (Remote end L2 alignment may be achieved). ENABLED or DISABLED"
    ::= { ptIOHWLSLChannelEntry 6 }

ptIOHWLSLChannelMTP3API OBJECT-TYPE
    SYNTAX          INTEGER { notLogged(0), logged(1), overridden(2) }
    MAX-ACCESS      read-only
    STATUS          current
    DESCRIPTION     
            "Log MTP3 API related information. Set this value at MTP3. Values: LOGGED, NOT_LOGGED. Value OVERRIDDEN indicates the debug FEATURE is NOT_LOGGED."
    ::= { ptIOHWLSLChannelEntry 8 }

ptIOHWLSLChannelLSSU OBJECT-TYPE
    SYNTAX          INTEGER { notLogged(0), logged(1), overridden(2) }
    MAX-ACCESS      read-only
    STATUS          current
    DESCRIPTION     
            "Log LSSU receipt and state changes. Set this value at MTP3. Values: LOGGED, NOT_LOGGED. Value OVERRIDDEN indicates the debug FEATURE is NOT_LOGGED."
    ::= { ptIOHWLSLChannelEntry 9 }

ptIOHWLSLChannelFISUAndMSU OBJECT-TYPE
    SYNTAX          INTEGER { notLogged(0), logged(1), overridden(2) }
    MAX-ACCESS      read-only
    STATUS          current
    DESCRIPTION     
            "Log Sequence Numbers information. Set this value at MTP3. Values: LOGGED, NOT_LOGGED. Value OVERRIDDEN indicates the debug FEATURE is NOT_LOGGED."
    ::= { ptIOHWLSLChannelEntry 10 }

ptIOHWLSLChannelCLLI OBJECT-TYPE
    SYNTAX          DisplayString (SIZE(0..255))
    MAX-ACCESS      read-create
    STATUS          current
    DESCRIPTION     
            "Common Language Location Identifier string for this channel."
    ::= { ptIOHWLSLChannelEntry 11 }

ptIOHWLSLChannelSupportDebug OBJECT-TYPE
    SYNTAX          DisplayString (SIZE(0..255))
    MAX-ACCESS      read-only
    STATUS          current
    DESCRIPTION     
            "Information for debug support."
    ::= { ptIOHWLSLChannelEntry 20 }

ptIOHWLSLChannelL3Use OBJECT-TYPE
    SYNTAX          INTEGER { inUse(-1), available(0) }
    MAX-ACCESS      read-only
    STATUS          current
    DESCRIPTION     
            "State of channel availability for mtp3 use (assigned number or AVAILABLE)"
    ::= { ptIOHWLSLChannelEntry 28 }

ptIOHWLSLChannelIOManagerIndex OBJECT-TYPE
    SYNTAX          Integer32 (-2147483648..2147483647)
    MAX-ACCESS      not-accessible
    STATUS          current
    DESCRIPTION     
            "This is the index of the parent type for this object.
             This parent type is IOManager."
    ::= { ptIOHWLSLChannelEntry 242 }

ptIOHWLSLChannelLSLChannelsIndex OBJECT-TYPE
    SYNTAX          Integer32 (-2147483648..2147483647)
    MAX-ACCESS      not-accessible
    STATUS          current
    DESCRIPTION     
            "This is the index of the parent type for this object.
             This parent type is LSLChannels."
    ::= { ptIOHWLSLChannelEntry 243 }

ptIOHWLSLChannelParentOID OBJECT-TYPE
    SYNTAX          OBJECT IDENTIFIER
    MAX-ACCESS      read-create
    STATUS          current
    DESCRIPTION     
            "The OID of the parent object for this instance"
    ::= { ptIOHWLSLChannelEntry 253 }

ptIOHWLSLChannelRowStatus OBJECT-TYPE
    SYNTAX          RowStatus
    MAX-ACCESS      read-create
    STATUS          current
    DESCRIPTION     
            "The row status for the IOHWLSLChannel table"
    ::= { ptIOHWLSLChannelEntry 254 }

ptIOHWLSLChannelIndex OBJECT-TYPE
    SYNTAX          Integer32 (-2147483648..2147483647)
    MAX-ACCESS      not-accessible
    STATUS          current
    DESCRIPTION     
            "The row number for the IOHWLSLChannel table"
    ::= { ptIOHWLSLChannelEntry 255 }

ptIOHWLSLH110Channel OBJECT IDENTIFIER
    ::= { ptIOHWLSLChannels 1100 }

ptIOHWLSLH110ChannelTable OBJECT-TYPE
    SYNTAX          SEQUENCE OF PtIOHWLSLH110ChannelEntry
    MAX-ACCESS      not-accessible
    STATUS          current
    DESCRIPTION     
            "No description supplied in the proxy config file."
    ::= { ptIOHWLSLH110Channel 1 }

ptIOHWLSLH110ChannelEntry OBJECT-TYPE
    SYNTAX          PtIOHWLSLH110ChannelEntry
    MAX-ACCESS      not-accessible
    STATUS          current
    DESCRIPTION     
            "A sequence of IOHWLSLH110Channel attributes."
    INDEX           { ptConnGroupIndex, 
                      ptIOHWLSLH110ChannelIOManagerIndex, 
                      ptIOHWLSLH110ChannelLSLChannelsIndex, 
                      ptIOHWLSLH110ChannelIndex }
    ::= { ptIOHWLSLH110ChannelTable 1 }

PtIOHWLSLH110ChannelEntry ::=
    SEQUENCE {
        ptIOHWLSLH110ChannelChannelNumber Integer32,
        ptIOHWLSLH110ChannelBaudRate    INTEGER,
        ptIOHWLSLH110ChannelCTBusTimeSlotRx   INTEGER,
        ptIOHWLSLH110ChannelCTBusTimeSlotTx   INTEGER,
        ptIOHWLSLH110ChannelLoopbackMode INTEGER,
        ptIOHWLSLH110ChannelCLLI        DisplayString,
        ptIOHWLSLH110ChannelSupportDebug DisplayString,
        ptIOHWLSLH110ChannelL3Use       INTEGER,
        ptIOHWLSLH110ChannelMTP3API     INTEGER,
        ptIOHWLSLH110ChannelLSSU        INTEGER,
        ptIOHWLSLH110ChannelFISUAndMSU  INTEGER,
        ptIOHWLSLH110ChannelIOManagerIndex  Integer32,
        ptIOHWLSLH110ChannelLSLChannelsIndex    Integer32,
        ptIOHWLSLH110ChannelParentOID   OBJECT IDENTIFIER,
        ptIOHWLSLH110ChannelRowStatus   RowStatus,
        ptIOHWLSLH110ChannelIndex       Integer32
    }

ptIOHWLSLH110ChannelChannelNumber OBJECT-TYPE
    SYNTAX          Integer32 (-2147483648..2147483647)
    MAX-ACCESS      read-only
    STATUS          current
    DESCRIPTION     
            "The number of the Signaling Channel being mapped"
    ::= { ptIOHWLSLH110ChannelEntry 1 }

ptIOHWLSLH110ChannelBaudRate OBJECT-TYPE
    SYNTAX          INTEGER { ds064k(0), ds0a56k(1), baud48k(2), 
                        baud48kRev(3), baudTtc48k(4) }
    MAX-ACCESS      read-create
    STATUS          current
    DESCRIPTION     
            "Baud rate for the timeslot. 64K uses all 8 bits. 56K uses 7 of 8 bits and discards the LSB. 48K uses 6 of 8 bits and discards the 2 LSBs. 48K_REV uses 6 of 8 bits and discards the two MSBs. TTC_48K uses 6 of 8 bits and discards the LSB and MSB."
    ::= { ptIOHWLSLH110ChannelEntry 6 }

ptIOHWLSLH110ChannelCTBusTimeSlotRx OBJECT-TYPE
    SYNTAX          INTEGER { notConfigured(0) }
    MAX-ACCESS      read-create
    STATUS          current
    DESCRIPTION     
            "Receive Timeslot on the CTBus (1-4096)"
    ::= { ptIOHWLSLH110ChannelEntry 8 }

ptIOHWLSLH110ChannelCTBusTimeSlotTx OBJECT-TYPE
    SYNTAX          INTEGER { notConfigured(0) }
    MAX-ACCESS      read-create
    STATUS          current
    DESCRIPTION     
            "Transmit Timeslot on the CTBus (1-4096)"
    ::= { ptIOHWLSLH110ChannelEntry 9 }

ptIOHWLSLH110ChannelLoopbackMode OBJECT-TYPE
    SYNTAX          INTEGER { disabled(0), enabled(1) }
    MAX-ACCESS      read-create
    STATUS          current
    DESCRIPTION     
            "Redirects incoming data on Tx timeslot back to Rx timeslot (Remote end L2 alignment may be achieved). ENABLED or DISABLED"
    ::= { ptIOHWLSLH110ChannelEntry 10 }

ptIOHWLSLH110ChannelCLLI OBJECT-TYPE
    SYNTAX          DisplayString (SIZE(0..255))
    MAX-ACCESS      read-create
    STATUS          current
    DESCRIPTION     
            "Common Language Location Identifier string for this channel."
    ::= { ptIOHWLSLH110ChannelEntry 14 }

ptIOHWLSLH110ChannelSupportDebug OBJECT-TYPE
    SYNTAX          DisplayString (SIZE(0..255))
    MAX-ACCESS      read-only
    STATUS          current
    DESCRIPTION     
            "Information for debug support."
    ::= { ptIOHWLSLH110ChannelEntry 20 }

ptIOHWLSLH110ChannelL3Use OBJECT-TYPE
    SYNTAX          INTEGER { inUse(-1), available(0) }
    MAX-ACCESS      read-only
    STATUS          current
    DESCRIPTION     
            "State of channel availability for mtp3 use (assigned number or AVAILABLE)"
    ::= { ptIOHWLSLH110ChannelEntry 28 }

ptIOHWLSLH110ChannelMTP3API OBJECT-TYPE
    SYNTAX          INTEGER { notLogged(0), logged(1), overridden(2) }
    MAX-ACCESS      read-only
    STATUS          current
    DESCRIPTION     
            "Log MTP3 API related information. Set this value at MTP3. Values: LOGGED, NOT_LOGGED. Value OVERRIDDEN indicates the debug FEATURE is NOT_LOGGED."
    ::= { ptIOHWLSLH110ChannelEntry 30 }

ptIOHWLSLH110ChannelLSSU OBJECT-TYPE
    SYNTAX          INTEGER { notLogged(0), logged(1), overridden(2) }
    MAX-ACCESS      read-only
    STATUS          current
    DESCRIPTION     
            "Log LSSU receipt and state changes. Set this value at MTP3. Values: LOGGED, NOT_LOGGED. Value OVERRIDDEN indicates the debug FEATURE is NOT_LOGGED."
    ::= { ptIOHWLSLH110ChannelEntry 31 }

ptIOHWLSLH110ChannelFISUAndMSU OBJECT-TYPE
    SYNTAX          INTEGER { notLogged(0), logged(1), overridden(2) }
    MAX-ACCESS      read-only
    STATUS          current
    DESCRIPTION     
            "Log Sequence Numbers information. Set this value at MTP3. Values: LOGGED, NOT_LOGGED. Value OVERRIDDEN indicates the debug FEATURE is NOT_LOGGED."
    ::= { ptIOHWLSLH110ChannelEntry 32 }

ptIOHWLSLH110ChannelIOManagerIndex OBJECT-TYPE
    SYNTAX          Integer32 (-2147483648..2147483647)
    MAX-ACCESS      not-accessible
    STATUS          current
    DESCRIPTION     
            "This is the index of the parent type for this object.
             This parent type is IOManager."
    ::= { ptIOHWLSLH110ChannelEntry 242 }

ptIOHWLSLH110ChannelLSLChannelsIndex OBJECT-TYPE
    SYNTAX          Integer32 (-2147483648..2147483647)
    MAX-ACCESS      not-accessible
    STATUS          current
    DESCRIPTION     
            "This is the index of the parent type for this object.
             This parent type is LSLChannels."
    ::= { ptIOHWLSLH110ChannelEntry 243 }

ptIOHWLSLH110ChannelParentOID OBJECT-TYPE
    SYNTAX          OBJECT IDENTIFIER
    MAX-ACCESS      read-create
    STATUS          current
    DESCRIPTION     
            "The OID of the parent object for this instance"
    ::= { ptIOHWLSLH110ChannelEntry 253 }

ptIOHWLSLH110ChannelRowStatus OBJECT-TYPE
    SYNTAX          RowStatus
    MAX-ACCESS      read-create
    STATUS          current
    DESCRIPTION     
            "The row status for the IOHWLSLH110Channel table"
    ::= { ptIOHWLSLH110ChannelEntry 254 }

ptIOHWLSLH110ChannelIndex OBJECT-TYPE
    SYNTAX          Integer32 (-2147483648..2147483647)
    MAX-ACCESS      not-accessible
    STATUS          current
    DESCRIPTION     
            "The row number for the IOHWLSLH110Channel table"
    ::= { ptIOHWLSLH110ChannelEntry 255 }

ptIOHWMTP2Link OBJECT IDENTIFIER
    ::= { ptIOHWLSLChannels 1101 }

ptIOHWMTP2LinkTable OBJECT-TYPE
    SYNTAX          SEQUENCE OF PtIOHWMTP2LinkEntry
    MAX-ACCESS      not-accessible
    STATUS          current
    DESCRIPTION     
            "No description supplied in the proxy config file."
    ::= { ptIOHWMTP2Link 1 }

ptIOHWMTP2LinkEntry OBJECT-TYPE
    SYNTAX          PtIOHWMTP2LinkEntry
    MAX-ACCESS      not-accessible
    STATUS          current
    DESCRIPTION     
            "A sequence of IOHWMTP2Link attributes."
    INDEX           { ptConnGroupIndex, ptIOHWMTP2LinkIOManagerIndex, 
                      ptIOHWMTP2LinkLSLChannelsIndex, 
                      ptIOHWMTP2LinkIndex }
    ::= { ptIOHWMTP2LinkTable 1 }

PtIOHWMTP2LinkEntry ::=
    SEQUENCE {
        ptIOHWMTP2LinkLinkNumber        Integer32,
        ptIOHWMTP2LinkLinkStatus        INTEGER,
        ptIOHWMTP2LinkCongestionLevel   Integer32,
        ptIOHWMTP2LinkProtocol          INTEGER,
        ptIOHWMTP2LinkAlignmentType     INTEGER,
        ptIOHWMTP2LinkErrorCorrection   INTEGER,
        ptIOHWMTP2LinkCongestionLevel1Onset   Integer32,
        ptIOHWMTP2LinkCongestionLevel2Onset   Integer32,
        ptIOHWMTP2LinkCongestionLevel3Onset   Integer32,
        ptIOHWMTP2LinkCongestionLevel1Abate   Integer32,
        ptIOHWMTP2LinkCongestionLevel2Abate   Integer32,
        ptIOHWMTP2LinkCongestionLevel3Abate   Integer32,
        ptIOHWMTP2LinkSUERMThreshold    Integer32,
        ptIOHWMTP2LinkNormalAERMThreshold Integer32,
        ptIOHWMTP2LinkEmergencyAERMThreshold    Integer32,
        ptIOHWMTP2LinkT1                Integer32,
        ptIOHWMTP2LinkT2                Integer32,
        ptIOHWMTP2LinkT3                Integer32,
        ptIOHWMTP2LinkT4n               Integer32,
        ptIOHWMTP2LinkT4e               Integer32,
        ptIOHWMTP2LinkT5                Integer32,
        ptIOHWMTP2LinkT6                Integer32,
        ptIOHWMTP2LinkT7                Integer32,
        ptIOHWMTP2LinkStatisticsReporting INTEGER,
        ptIOHWMTP2LinkReportingInterval Integer32,
        ptIOHWMTP2LinkTxErlang          DisplayString,
        ptIOHWMTP2LinkRxErlang          DisplayString,
        ptIOHWMTP2LinkMSUsTransmitted   Integer32,
        ptIOHWMTP2LinkMSUsReceived      Integer32,
        ptIOHWMTP2LinkMSUsRetransmitted Integer32,
        ptIOHWMTP2LinkFIBInversions     Integer32,
        ptIOHWMTP2LinkBIBInversions     Integer32,
        ptIOHWMTP2LinkRxErrors          Integer32,
        ptIOHWMTP2LinkRxOverflows       Integer32,
        ptIOHWMTP2LinkNumberOfMSUToSend Integer32,
        ptIOHWMTP2LinkSizeOfMSUToTx     Integer32,
        ptIOHWMTP2LinkN1                Integer32,
        ptIOHWMTP2LinkN2                Integer32,
        ptIOHWMTP2LinkLinkType          INTEGER,
        ptIOHWMTP2LinkL3LinkNumber      Integer32,
        ptIOHWMTP2LinkIOManagerIndex    Integer32,
        ptIOHWMTP2LinkLSLChannelsIndex  Integer32,
        ptIOHWMTP2LinkActions           INTEGER,
        ptIOHWMTP2LinkParentOID         OBJECT IDENTIFIER,
        ptIOHWMTP2LinkRowStatus         RowStatus,
        ptIOHWMTP2LinkIndex             Integer32
    }

ptIOHWMTP2LinkLinkNumber OBJECT-TYPE
    SYNTAX          Integer32 (-2147483648..2147483647)
    MAX-ACCESS      read-only
    STATUS          current
    DESCRIPTION     
            ""
    ::= { ptIOHWMTP2LinkEntry 1 }

ptIOHWMTP2LinkLinkStatus OBJECT-TYPE
    SYNTAX          INTEGER { disabled(0), outOfService(1), aligning(2), 
                        alignedReady(3), alignedNotReady(4), 
                        inService(5), processorOutage(6) }
    MAX-ACCESS      read-only
    STATUS          current
    DESCRIPTION     
            ""
    ::= { ptIOHWMTP2LinkEntry 2 }

ptIOHWMTP2LinkCongestionLevel OBJECT-TYPE
    SYNTAX          Integer32 (-2147483648..2147483647)
    MAX-ACCESS      read-only
    STATUS          current
    DESCRIPTION     
            ""
    ::= { ptIOHWMTP2LinkEntry 3 }

ptIOHWMTP2LinkProtocol OBJECT-TYPE
    SYNTAX          INTEGER { ansi(0), itu(1), japan(2) }
    MAX-ACCESS      read-create
    STATUS          current
    DESCRIPTION     
            ""
    ::= { ptIOHWMTP2LinkEntry 4 }

ptIOHWMTP2LinkAlignmentType OBJECT-TYPE
    SYNTAX          INTEGER { normal(0), emergency(1) }
    MAX-ACCESS      read-create
    STATUS          current
    DESCRIPTION     
            ""
    ::= { ptIOHWMTP2LinkEntry 5 }

ptIOHWMTP2LinkErrorCorrection OBJECT-TYPE
    SYNTAX          INTEGER { basic(0), pcr(1) }
    MAX-ACCESS      read-create
    STATUS          current
    DESCRIPTION     
            ""
    ::= { ptIOHWMTP2LinkEntry 6 }

ptIOHWMTP2LinkCongestionLevel1Onset OBJECT-TYPE
    SYNTAX          Integer32 (-2147483648..2147483647)
    MAX-ACCESS      read-create
    STATUS          current
    DESCRIPTION     
            ""
    ::= { ptIOHWMTP2LinkEntry 7 }

ptIOHWMTP2LinkCongestionLevel2Onset OBJECT-TYPE
    SYNTAX          Integer32 (-2147483648..2147483647)
    MAX-ACCESS      read-create
    STATUS          current
    DESCRIPTION     
            ""
    ::= { ptIOHWMTP2LinkEntry 8 }

ptIOHWMTP2LinkCongestionLevel3Onset OBJECT-TYPE
    SYNTAX          Integer32 (-2147483648..2147483647)
    MAX-ACCESS      read-create
    STATUS          current
    DESCRIPTION     
            ""
    ::= { ptIOHWMTP2LinkEntry 9 }

ptIOHWMTP2LinkCongestionLevel1Abate OBJECT-TYPE
    SYNTAX          Integer32 (-2147483648..2147483647)
    MAX-ACCESS      read-create
    STATUS          current
    DESCRIPTION     
            ""
    ::= { ptIOHWMTP2LinkEntry 10 }

ptIOHWMTP2LinkCongestionLevel2Abate OBJECT-TYPE
    SYNTAX          Integer32 (-2147483648..2147483647)
    MAX-ACCESS      read-create
    STATUS          current
    DESCRIPTION     
            ""
    ::= { ptIOHWMTP2LinkEntry 11 }

ptIOHWMTP2LinkCongestionLevel3Abate OBJECT-TYPE
    SYNTAX          Integer32 (-2147483648..2147483647)
    MAX-ACCESS      read-create
    STATUS          current
    DESCRIPTION     
            ""
    ::= { ptIOHWMTP2LinkEntry 12 }

ptIOHWMTP2LinkSUERMThreshold OBJECT-TYPE
    SYNTAX          Integer32 (-2147483648..2147483647)
    MAX-ACCESS      read-create
    STATUS          current
    DESCRIPTION     
            ""
    ::= { ptIOHWMTP2LinkEntry 14 }

ptIOHWMTP2LinkNormalAERMThreshold OBJECT-TYPE
    SYNTAX          Integer32 (-2147483648..2147483647)
    MAX-ACCESS      read-create
    STATUS          current
    DESCRIPTION     
            ""
    ::= { ptIOHWMTP2LinkEntry 15 }

ptIOHWMTP2LinkEmergencyAERMThreshold OBJECT-TYPE
    SYNTAX          Integer32 (-2147483648..2147483647)
    MAX-ACCESS      read-create
    STATUS          current
    DESCRIPTION     
            ""
    ::= { ptIOHWMTP2LinkEntry 16 }

ptIOHWMTP2LinkT1 OBJECT-TYPE
    SYNTAX          Integer32 (-2147483648..2147483647)
    MAX-ACCESS      read-create
    STATUS          current
    DESCRIPTION     
            ""
    ::= { ptIOHWMTP2LinkEntry 17 }

ptIOHWMTP2LinkT2 OBJECT-TYPE
    SYNTAX          Integer32 (-2147483648..2147483647)
    MAX-ACCESS      read-create
    STATUS          current
    DESCRIPTION     
            ""
    ::= { ptIOHWMTP2LinkEntry 18 }

ptIOHWMTP2LinkT3 OBJECT-TYPE
    SYNTAX          Integer32 (-2147483648..2147483647)
    MAX-ACCESS      read-create
    STATUS          current
    DESCRIPTION     
            ""
    ::= { ptIOHWMTP2LinkEntry 19 }

ptIOHWMTP2LinkT4n OBJECT-TYPE
    SYNTAX          Integer32 (-2147483648..2147483647)
    MAX-ACCESS      read-create
    STATUS          current
    DESCRIPTION     
            ""
    ::= { ptIOHWMTP2LinkEntry 20 }

ptIOHWMTP2LinkT4e OBJECT-TYPE
    SYNTAX          Integer32 (-2147483648..2147483647)
    MAX-ACCESS      read-create
    STATUS          current
    DESCRIPTION     
            ""
    ::= { ptIOHWMTP2LinkEntry 21 }

ptIOHWMTP2LinkT5 OBJECT-TYPE
    SYNTAX          Integer32 (-2147483648..2147483647)
    MAX-ACCESS      read-create
    STATUS          current
    DESCRIPTION     
            ""
    ::= { ptIOHWMTP2LinkEntry 22 }

ptIOHWMTP2LinkT6 OBJECT-TYPE
    SYNTAX          Integer32 (-2147483648..2147483647)
    MAX-ACCESS      read-create
    STATUS          current
    DESCRIPTION     
            ""
    ::= { ptIOHWMTP2LinkEntry 23 }

ptIOHWMTP2LinkT7 OBJECT-TYPE
    SYNTAX          Integer32 (-2147483648..2147483647)
    MAX-ACCESS      read-create
    STATUS          current
    DESCRIPTION     
            ""
    ::= { ptIOHWMTP2LinkEntry 24 }

ptIOHWMTP2LinkStatisticsReporting OBJECT-TYPE
    SYNTAX          INTEGER { disabled(0), enabled(1) }
    MAX-ACCESS      read-create
    STATUS          current
    DESCRIPTION     
            ""
    ::= { ptIOHWMTP2LinkEntry 25 }

ptIOHWMTP2LinkReportingInterval OBJECT-TYPE
    SYNTAX          Integer32 (-2147483648..2147483647)
    MAX-ACCESS      read-create
    STATUS          current
    DESCRIPTION     
            ""
    ::= { ptIOHWMTP2LinkEntry 26 }

ptIOHWMTP2LinkTxErlang OBJECT-TYPE
    SYNTAX          DisplayString (SIZE(0..255))
    MAX-ACCESS      read-only
    STATUS          current
    DESCRIPTION     
            "No description supplied in the proxy config file."
    ::= { ptIOHWMTP2LinkEntry 27 }

ptIOHWMTP2LinkRxErlang OBJECT-TYPE
    SYNTAX          DisplayString (SIZE(0..255))
    MAX-ACCESS      read-only
    STATUS          current
    DESCRIPTION     
            "No description supplied in the proxy config file."
    ::= { ptIOHWMTP2LinkEntry 28 }

ptIOHWMTP2LinkMSUsTransmitted OBJECT-TYPE
    SYNTAX          Integer32 (-2147483648..2147483647)
    MAX-ACCESS      read-only
    STATUS          current
    DESCRIPTION     
            "No description supplied in the proxy config file."
    ::= { ptIOHWMTP2LinkEntry 29 }

ptIOHWMTP2LinkMSUsReceived OBJECT-TYPE
    SYNTAX          Integer32 (-2147483648..2147483647)
    MAX-ACCESS      read-only
    STATUS          current
    DESCRIPTION     
            "No description supplied in the proxy config file."
    ::= { ptIOHWMTP2LinkEntry 30 }

ptIOHWMTP2LinkMSUsRetransmitted OBJECT-TYPE
    SYNTAX          Integer32 (-2147483648..2147483647)
    MAX-ACCESS      read-only
    STATUS          current
    DESCRIPTION     
            "No description supplied in the proxy config file."
    ::= { ptIOHWMTP2LinkEntry 31 }

ptIOHWMTP2LinkFIBInversions OBJECT-TYPE
    SYNTAX          Integer32 (-2147483648..2147483647)
    MAX-ACCESS      read-only
    STATUS          current
    DESCRIPTION     
            "No description supplied in the proxy config file."
    ::= { ptIOHWMTP2LinkEntry 32 }

ptIOHWMTP2LinkBIBInversions OBJECT-TYPE
    SYNTAX          Integer32 (-2147483648..2147483647)
    MAX-ACCESS      read-only
    STATUS          current
    DESCRIPTION     
            "No description supplied in the proxy config file."
    ::= { ptIOHWMTP2LinkEntry 33 }

ptIOHWMTP2LinkRxErrors OBJECT-TYPE
    SYNTAX          Integer32 (-2147483648..2147483647)
    MAX-ACCESS      read-only
    STATUS          current
    DESCRIPTION     
            "No description supplied in the proxy config file."
    ::= { ptIOHWMTP2LinkEntry 34 }

ptIOHWMTP2LinkRxOverflows OBJECT-TYPE
    SYNTAX          Integer32 (-2147483648..2147483647)
    MAX-ACCESS      read-only
    STATUS          current
    DESCRIPTION     
            "No description supplied in the proxy config file."
    ::= { ptIOHWMTP2LinkEntry 35 }

ptIOHWMTP2LinkNumberOfMSUToSend OBJECT-TYPE
    SYNTAX          Integer32 (-2147483648..2147483647)
    MAX-ACCESS      read-create
    STATUS          current
    DESCRIPTION     
            ""
    ::= { ptIOHWMTP2LinkEntry 36 }

ptIOHWMTP2LinkSizeOfMSUToTx OBJECT-TYPE
    SYNTAX          Integer32 (-2147483648..2147483647)
    MAX-ACCESS      read-create
    STATUS          current
    DESCRIPTION     
            ""
    ::= { ptIOHWMTP2LinkEntry 37 }

ptIOHWMTP2LinkN1 OBJECT-TYPE
    SYNTAX          Integer32 (-2147483648..2147483647)
    MAX-ACCESS      read-create
    STATUS          current
    DESCRIPTION     
            ""
    ::= { ptIOHWMTP2LinkEntry 38 }

ptIOHWMTP2LinkN2 OBJECT-TYPE
    SYNTAX          Integer32 (-2147483648..2147483647)
    MAX-ACCESS      read-create
    STATUS          current
    DESCRIPTION     
            ""
    ::= { ptIOHWMTP2LinkEntry 39 }

ptIOHWMTP2LinkLinkType OBJECT-TYPE
    SYNTAX          INTEGER { lowSpeed56k(0), lowSpeed64k(1), 
                        highSpeed15m(2), highSpeed20m(3), lowSpeed48k(4), 
                        lowSpeed48kRev(5), lowSpeedTtc48k(6) }
    MAX-ACCESS      read-only
    STATUS          current
    DESCRIPTION     
            ""
    ::= { ptIOHWMTP2LinkEntry 40 }

ptIOHWMTP2LinkL3LinkNumber OBJECT-TYPE
    SYNTAX          Integer32 (-2147483648..2147483647)
    MAX-ACCESS      read-only
    STATUS          current
    DESCRIPTION     
            ""
    ::= { ptIOHWMTP2LinkEntry 45 }

ptIOHWMTP2LinkIOManagerIndex OBJECT-TYPE
    SYNTAX          Integer32 (-2147483648..2147483647)
    MAX-ACCESS      not-accessible
    STATUS          current
    DESCRIPTION     
            "This is the index of the parent type for this object.
             This parent type is IOManager."
    ::= { ptIOHWMTP2LinkEntry 242 }

ptIOHWMTP2LinkLSLChannelsIndex OBJECT-TYPE
    SYNTAX          Integer32 (-2147483648..2147483647)
    MAX-ACCESS      not-accessible
    STATUS          current
    DESCRIPTION     
            "This is the index of the parent type for this object.
             This parent type is LSLChannels."
    ::= { ptIOHWMTP2LinkEntry 243 }

ptIOHWMTP2LinkActions OBJECT-TYPE
    SYNTAX          INTEGER { start(1), stop(2), enable(3), disable(4), 
                        setEmergency(5), clearEmergency(6), setSIB(7), 
                        clearSIB(8), setLPO(9), clearLPO(10), 
                        sendMSU(11) }
    MAX-ACCESS      read-create
    STATUS          current
    DESCRIPTION     
            "The OID of all possible actions for this instance"
    ::= { ptIOHWMTP2LinkEntry 252 }

ptIOHWMTP2LinkParentOID OBJECT-TYPE
    SYNTAX          OBJECT IDENTIFIER
    MAX-ACCESS      read-create
    STATUS          current
    DESCRIPTION     
            "The OID of the parent object for this instance"
    ::= { ptIOHWMTP2LinkEntry 253 }

ptIOHWMTP2LinkRowStatus OBJECT-TYPE
    SYNTAX          RowStatus
    MAX-ACCESS      read-create
    STATUS          current
    DESCRIPTION     
            "The row status for the IOHWMTP2Link table"
    ::= { ptIOHWMTP2LinkEntry 254 }

ptIOHWMTP2LinkIndex OBJECT-TYPE
    SYNTAX          Integer32 (-2147483648..2147483647)
    MAX-ACCESS      not-accessible
    STATUS          current
    DESCRIPTION     
            "The row number for the IOHWMTP2Link table"
    ::= { ptIOHWMTP2LinkEntry 255 }

ptIOHWHSLAnnexAChannels OBJECT IDENTIFIER
    ::= { ptIOHWIOManager 1083 }

ptIOHWHSLAnnexAChannelsTable OBJECT-TYPE
    SYNTAX          SEQUENCE OF PtIOHWHSLAnnexAChannelsEntry
    MAX-ACCESS      not-accessible
    STATUS          current
    DESCRIPTION     
            "No description supplied in the proxy config file."
    ::= { ptIOHWHSLAnnexAChannels 1 }

ptIOHWHSLAnnexAChannelsEntry OBJECT-TYPE
    SYNTAX          PtIOHWHSLAnnexAChannelsEntry
    MAX-ACCESS      not-accessible
    STATUS          current
    DESCRIPTION     
            "A sequence of IOHWHSLAnnexAChannels attributes."
    INDEX           { ptConnGroupIndex, 
                      ptIOHWHSLAnnexAChannelsIOManagerIndex, 
                      ptIOHWHSLAnnexAChannelsIndex }
    ::= { ptIOHWHSLAnnexAChannelsTable 1 }

PtIOHWHSLAnnexAChannelsEntry ::=
    SEQUENCE {
        ptIOHWHSLAnnexAChannelsState    INTEGER,
        ptIOHWHSLAnnexAChannelsLicense  INTEGER,
        ptIOHWHSLAnnexAChannelsUseRepeatFISU    INTEGER,
        ptIOHWHSLAnnexAChannelsIOManagerIndex     Integer32,
        ptIOHWHSLAnnexAChannelsActions  INTEGER,
        ptIOHWHSLAnnexAChannelsParentOID OBJECT IDENTIFIER,
        ptIOHWHSLAnnexAChannelsRowStatus RowStatus,
        ptIOHWHSLAnnexAChannelsIndex    Integer32
    }

ptIOHWHSLAnnexAChannelsState OBJECT-TYPE
    SYNTAX          INTEGER { activated(0), deactivated(1), failed(2) }
    MAX-ACCESS      read-only
    STATUS          current
    DESCRIPTION     
            "Link Manager state"
    ::= { ptIOHWHSLAnnexAChannelsEntry 4 }

ptIOHWHSLAnnexAChannelsLicense OBJECT-TYPE
    SYNTAX          INTEGER { unlicensed(0), disconnected(1), 
                        licensed(2), unknown(3) }
    MAX-ACCESS      read-only
    STATUS          current
    DESCRIPTION     
            "TDM license state: Licensed, Unlicensed, Disconnected"
    ::= { ptIOHWHSLAnnexAChannelsEntry 18 }

ptIOHWHSLAnnexAChannelsUseRepeatFISU OBJECT-TYPE
    SYNTAX          INTEGER { disabled(0), enabled(1) }
    MAX-ACCESS      read-create
    STATUS          current
    DESCRIPTION     
            "To be used only when link failures occur in the absence of clock faults and miss-configuration. Increases FISUs on the line but decreases performance."
    ::= { ptIOHWHSLAnnexAChannelsEntry 60 }

ptIOHWHSLAnnexAChannelsIOManagerIndex OBJECT-TYPE
    SYNTAX          Integer32 (-2147483648..2147483647)
    MAX-ACCESS      not-accessible
    STATUS          current
    DESCRIPTION     
            "This is the index of the parent type for this object.
             This parent type is IOManager."
    ::= { ptIOHWHSLAnnexAChannelsEntry 242 }

ptIOHWHSLAnnexAChannelsActions OBJECT-TYPE
    SYNTAX          INTEGER { activate(1), deactivate(2) }
    MAX-ACCESS      read-create
    STATUS          current
    DESCRIPTION     
            "The OID of all possible actions for this instance"
    ::= { ptIOHWHSLAnnexAChannelsEntry 252 }

ptIOHWHSLAnnexAChannelsParentOID OBJECT-TYPE
    SYNTAX          OBJECT IDENTIFIER
    MAX-ACCESS      read-create
    STATUS          current
    DESCRIPTION     
            "The OID of the parent object for this instance"
    ::= { ptIOHWHSLAnnexAChannelsEntry 253 }

ptIOHWHSLAnnexAChannelsRowStatus OBJECT-TYPE
    SYNTAX          RowStatus
    MAX-ACCESS      read-create
    STATUS          current
    DESCRIPTION     
            "The row status for the IOHWHSLAnnexAChannels table"
    ::= { ptIOHWHSLAnnexAChannelsEntry 254 }

ptIOHWHSLAnnexAChannelsIndex OBJECT-TYPE
    SYNTAX          Integer32 (-2147483648..2147483647)
    MAX-ACCESS      not-accessible
    STATUS          current
    DESCRIPTION     
            "The row number for the IOHWHSLAnnexAChannels table"
    ::= { ptIOHWHSLAnnexAChannelsEntry 255 }

ptIOHWHSLAnnexAChannel OBJECT IDENTIFIER
    ::= { ptIOHWHSLAnnexAChannels 1098 }

ptIOHWHSLAnnexAChannelTable OBJECT-TYPE
    SYNTAX          SEQUENCE OF PtIOHWHSLAnnexAChannelEntry
    MAX-ACCESS      not-accessible
    STATUS          current
    DESCRIPTION     
            "No description supplied in the proxy config file."
    ::= { ptIOHWHSLAnnexAChannel 1 }

ptIOHWHSLAnnexAChannelEntry OBJECT-TYPE
    SYNTAX          PtIOHWHSLAnnexAChannelEntry
    MAX-ACCESS      not-accessible
    STATUS          current
    DESCRIPTION     
            "A sequence of IOHWHSLAnnexAChannel attributes."
    INDEX           { ptConnGroupIndex, 
                      ptIOHWHSLAnnexAChannelIOManagerIndex, 
                      ptIOHWHSLAnnexAChannelHSLAnnexAChannelsIndex, 
                      ptIOHWHSLAnnexAChannelIndex }
    ::= { ptIOHWHSLAnnexAChannelTable 1 }

PtIOHWHSLAnnexAChannelEntry ::=
    SEQUENCE {
        ptIOHWHSLAnnexAChannelChannelNumber   Integer32,
        ptIOHWHSLAnnexAChannelPort      INTEGER,
        ptIOHWHSLAnnexAChannelBaudRate  INTEGER,
        ptIOHWHSLAnnexAChannelMTP3API   INTEGER,
        ptIOHWHSLAnnexAChannelLSSU      INTEGER,
        ptIOHWHSLAnnexAChannelFISUAndMSU INTEGER,
        ptIOHWHSLAnnexAChannelCLLI      DisplayString,
        ptIOHWHSLAnnexAChannelSupportDebug  DisplayString,
        ptIOHWHSLAnnexAChannelL3Use     INTEGER,
        ptIOHWHSLAnnexAChannelSequenceNumberBits        INTEGER,
        ptIOHWHSLAnnexAChannelIOManagerIndex    Integer32,
        ptIOHWHSLAnnexAChannelHSLAnnexAChannelsIndex            Integer32,
        ptIOHWHSLAnnexAChannelParentOID OBJECT IDENTIFIER,
        ptIOHWHSLAnnexAChannelRowStatus RowStatus,
        ptIOHWHSLAnnexAChannelIndex     Integer32
    }

ptIOHWHSLAnnexAChannelChannelNumber OBJECT-TYPE
    SYNTAX          Integer32 (-2147483648..2147483647)
    MAX-ACCESS      read-only
    STATUS          current
    DESCRIPTION     
            "Channel number"
    ::= { ptIOHWHSLAnnexAChannelEntry 1 }

ptIOHWHSLAnnexAChannelPort OBJECT-TYPE
    SYNTAX          INTEGER { port0(0), port1(1), port2(2), port3(3), 
                        port4(4), port5(5), port6(6), port7(7), 
                        monitorPort(8), notConfigured(9), port8(10) }
    MAX-ACCESS      read-create
    STATUS          current
    DESCRIPTION     
            "Port number"
    ::= { ptIOHWHSLAnnexAChannelEntry 2 }

ptIOHWHSLAnnexAChannelBaudRate OBJECT-TYPE
    SYNTAX          INTEGER { baud15m(0), baud20m(1) }
    MAX-ACCESS      read-only
    STATUS          current
    DESCRIPTION     
            "Baud rate: T1 link requires 1.5M while E1 uses 2.0M. Autoconfigured on port selection"
    ::= { ptIOHWHSLAnnexAChannelEntry 3 }

ptIOHWHSLAnnexAChannelMTP3API OBJECT-TYPE
    SYNTAX          INTEGER { notLogged(0), logged(1), overridden(2) }
    MAX-ACCESS      read-only
    STATUS          current
    DESCRIPTION     
            "Log MTP3 API related information. Set this value at MTP3. Values: LOGGED, NOT_LOGGED. Value OVERRIDDEN indicates the debug FEATURE is NOT_LOGGED."
    ::= { ptIOHWHSLAnnexAChannelEntry 8 }

ptIOHWHSLAnnexAChannelLSSU OBJECT-TYPE
    SYNTAX          INTEGER { notLogged(0), logged(1), overridden(2) }
    MAX-ACCESS      read-only
    STATUS          current
    DESCRIPTION     
            "Log LSSU receipt and state changes. Set this value at MTP3. Values: LOGGED, NOT_LOGGED. Value OVERRIDDEN indicates the debug FEATURE is NOT_LOGGED."
    ::= { ptIOHWHSLAnnexAChannelEntry 9 }

ptIOHWHSLAnnexAChannelFISUAndMSU OBJECT-TYPE
    SYNTAX          INTEGER { notLogged(0), logged(1), overridden(2) }
    MAX-ACCESS      read-only
    STATUS          current
    DESCRIPTION     
            "Log Sequence Numbers information. Set this value at MTP3. Values: LOGGED, NOT_LOGGED. Value OVERRIDDEN indicates the debug FEATURE is NOT_LOGGED."
    ::= { ptIOHWHSLAnnexAChannelEntry 10 }

ptIOHWHSLAnnexAChannelCLLI OBJECT-TYPE
    SYNTAX          DisplayString (SIZE(0..255))
    MAX-ACCESS      read-create
    STATUS          current
    DESCRIPTION     
            "Common Language Location Identifier string for this channel."
    ::= { ptIOHWHSLAnnexAChannelEntry 11 }

ptIOHWHSLAnnexAChannelSupportDebug OBJECT-TYPE
    SYNTAX          DisplayString (SIZE(0..255))
    MAX-ACCESS      read-only
    STATUS          current
    DESCRIPTION     
            "Information for debug support."
    ::= { ptIOHWHSLAnnexAChannelEntry 20 }

ptIOHWHSLAnnexAChannelL3Use OBJECT-TYPE
    SYNTAX          INTEGER { inUse(-1), available(0) }
    MAX-ACCESS      read-only
    STATUS          current
    DESCRIPTION     
            "State of channel availability for mtp3 use (assigned number or AVAILABLE)"
    ::= { ptIOHWHSLAnnexAChannelEntry 28 }

ptIOHWHSLAnnexAChannelSequenceNumberBits OBJECT-TYPE
    SYNTAX          INTEGER { standard(12) }
    MAX-ACCESS      read-create
    STATUS          current
    DESCRIPTION     
            "Number of sequence number bits used for the sliding window size. Reasonable values are 7-12, 12 is standard. The FSN/BSN field is 12 bits. Set before configuring channels - changes may cause link failure."
    ::= { ptIOHWHSLAnnexAChannelEntry 70 }

ptIOHWHSLAnnexAChannelIOManagerIndex OBJECT-TYPE
    SYNTAX          Integer32 (-2147483648..2147483647)
    MAX-ACCESS      not-accessible
    STATUS          current
    DESCRIPTION     
            "This is the index of the parent type for this object.
             This parent type is IOManager."
    ::= { ptIOHWHSLAnnexAChannelEntry 242 }

ptIOHWHSLAnnexAChannelHSLAnnexAChannelsIndex OBJECT-TYPE
    SYNTAX          Integer32 (-2147483648..2147483647)
    MAX-ACCESS      not-accessible
    STATUS          current
    DESCRIPTION     
            "This is the index of the parent type for this object.
             This parent type is HSLAnnexAChannels."
    ::= { ptIOHWHSLAnnexAChannelEntry 243 }

ptIOHWHSLAnnexAChannelParentOID OBJECT-TYPE
    SYNTAX          OBJECT IDENTIFIER
    MAX-ACCESS      read-create
    STATUS          current
    DESCRIPTION     
            "The OID of the parent object for this instance"
    ::= { ptIOHWHSLAnnexAChannelEntry 253 }

ptIOHWHSLAnnexAChannelRowStatus OBJECT-TYPE
    SYNTAX          RowStatus
    MAX-ACCESS      read-create
    STATUS          current
    DESCRIPTION     
            "The row status for the IOHWHSLAnnexAChannel table"
    ::= { ptIOHWHSLAnnexAChannelEntry 254 }

ptIOHWHSLAnnexAChannelIndex OBJECT-TYPE
    SYNTAX          Integer32 (-2147483648..2147483647)
    MAX-ACCESS      not-accessible
    STATUS          current
    DESCRIPTION     
            "The row number for the IOHWHSLAnnexAChannel table"
    ::= { ptIOHWHSLAnnexAChannelEntry 255 }

ptIOHWHSLATMChannels OBJECT IDENTIFIER
    ::= { ptIOHWIOManager 1084 }

ptIOHWHSLATMChannelsTable OBJECT-TYPE
    SYNTAX          SEQUENCE OF PtIOHWHSLATMChannelsEntry
    MAX-ACCESS      not-accessible
    STATUS          current
    DESCRIPTION     
            "No description supplied in the proxy config file."
    ::= { ptIOHWHSLATMChannels 1 }

ptIOHWHSLATMChannelsEntry OBJECT-TYPE
    SYNTAX          PtIOHWHSLATMChannelsEntry
    MAX-ACCESS      not-accessible
    STATUS          current
    DESCRIPTION     
            "A sequence of IOHWHSLATMChannels attributes."
    INDEX           { ptConnGroupIndex, 
                      ptIOHWHSLATMChannelsIOManagerIndex, 
                      ptIOHWHSLATMChannelsIndex }
    ::= { ptIOHWHSLATMChannelsTable 1 }

PtIOHWHSLATMChannelsEntry ::=
    SEQUENCE {
        ptIOHWHSLATMChannelsVPIMask     Integer32,
        ptIOHWHSLATMChannelsVCIMask     Integer32,
        ptIOHWHSLATMChannelsState       INTEGER,
        ptIOHWHSLATMChannelsLicense     INTEGER,
        ptIOHWHSLATMChannelsIOManagerIndex  Integer32,
        ptIOHWHSLATMChannelsActions     INTEGER,
        ptIOHWHSLATMChannelsParentOID   OBJECT IDENTIFIER,
        ptIOHWHSLATMChannelsRowStatus   RowStatus,
        ptIOHWHSLATMChannelsIndex       Integer32
    }

ptIOHWHSLATMChannelsVPIMask OBJECT-TYPE
    SYNTAX          Integer32 (-2147483648..2147483647)
    MAX-ACCESS      read-create
    STATUS          current
    DESCRIPTION     
            "Bit mask (in decimal) that determines the valid VPI range for a link. A maximum of 4 out of 8 bits can be used. Valid options are 0 to 240. For example, mask 15 is 00001111 in binary, which gives a range of 0 to 15 for VPI. The maximum is 11110000 (240 decimal)."
    ::= { ptIOHWHSLATMChannelsEntry 2 }

ptIOHWHSLATMChannelsVCIMask OBJECT-TYPE
    SYNTAX          Integer32 (-2147483648..2147483647)
    MAX-ACCESS      read-create
    STATUS          current
    DESCRIPTION     
            "Bit mask (in decimal) that determines the valid VCI range for a link. A maximum of 10 out of 16 bits can be used. Valid options are 0 to 65472. For example, mask 15 is 00001111 in binary, which gives a range of 0 to 15 for VPI. The maximum is 1111111111000000 (65472 decimal)."
    ::= { ptIOHWHSLATMChannelsEntry 3 }

ptIOHWHSLATMChannelsState OBJECT-TYPE
    SYNTAX          INTEGER { activated(0), deactivated(1), failed(2) }
    MAX-ACCESS      read-only
    STATUS          current
    DESCRIPTION     
            "Link manager state. State of FAILED indicates setup fault."
    ::= { ptIOHWHSLATMChannelsEntry 4 }

ptIOHWHSLATMChannelsLicense OBJECT-TYPE
    SYNTAX          INTEGER { unlicensed(0), disconnected(1), 
                        licensed(2), unknown(3) }
    MAX-ACCESS      read-only
    STATUS          current
    DESCRIPTION     
            "ATM license state: Licensed, Unlicensed, Disconnected"
    ::= { ptIOHWHSLATMChannelsEntry 18 }

ptIOHWHSLATMChannelsIOManagerIndex OBJECT-TYPE
    SYNTAX          Integer32 (-2147483648..2147483647)
    MAX-ACCESS      not-accessible
    STATUS          current
    DESCRIPTION     
            "This is the index of the parent type for this object.
             This parent type is IOManager."
    ::= { ptIOHWHSLATMChannelsEntry 242 }

ptIOHWHSLATMChannelsActions OBJECT-TYPE
    SYNTAX          INTEGER { activate(1), deactivate(2) }
    MAX-ACCESS      read-create
    STATUS          current
    DESCRIPTION     
            "The OID of all possible actions for this instance"
    ::= { ptIOHWHSLATMChannelsEntry 252 }

ptIOHWHSLATMChannelsParentOID OBJECT-TYPE
    SYNTAX          OBJECT IDENTIFIER
    MAX-ACCESS      read-create
    STATUS          current
    DESCRIPTION     
            "The OID of the parent object for this instance"
    ::= { ptIOHWHSLATMChannelsEntry 253 }

ptIOHWHSLATMChannelsRowStatus OBJECT-TYPE
    SYNTAX          RowStatus
    MAX-ACCESS      read-create
    STATUS          current
    DESCRIPTION     
            "The row status for the IOHWHSLATMChannels table"
    ::= { ptIOHWHSLATMChannelsEntry 254 }

ptIOHWHSLATMChannelsIndex OBJECT-TYPE
    SYNTAX          Integer32 (-2147483648..2147483647)
    MAX-ACCESS      not-accessible
    STATUS          current
    DESCRIPTION     
            "The row number for the IOHWHSLATMChannels table"
    ::= { ptIOHWHSLATMChannelsEntry 255 }

ptIOHWHSLATMChannel OBJECT IDENTIFIER
    ::= { ptIOHWHSLATMChannels 1102 }

ptIOHWHSLATMChannelTable OBJECT-TYPE
    SYNTAX          SEQUENCE OF PtIOHWHSLATMChannelEntry
    MAX-ACCESS      not-accessible
    STATUS          current
    DESCRIPTION     
            "No description supplied in the proxy config file."
    ::= { ptIOHWHSLATMChannel 1 }

ptIOHWHSLATMChannelEntry OBJECT-TYPE
    SYNTAX          PtIOHWHSLATMChannelEntry
    MAX-ACCESS      not-accessible
    STATUS          current
    DESCRIPTION     
            "A sequence of IOHWHSLATMChannel attributes."
    INDEX           { ptConnGroupIndex, 
                      ptIOHWHSLATMChannelIOManagerIndex, 
                      ptIOHWHSLATMChannelHSLATMChannelsIndex, 
                      ptIOHWHSLATMChannelIndex }
    ::= { ptIOHWHSLATMChannelTable 1 }

PtIOHWHSLATMChannelEntry ::=
    SEQUENCE {
        ptIOHWHSLATMChannelChannelNumber Integer32,
        ptIOHWHSLATMChannelCLLI         DisplayString,
        ptIOHWHSLATMChannelPort         INTEGER,
        ptIOHWHSLATMChannelChannelState INTEGER,
        ptIOHWHSLATMChannelVPI          Integer32,
        ptIOHWHSLATMChannelVCI          Integer32,
        ptIOHWHSLATMChannelScrambling   INTEGER,
        ptIOHWHSLATMChannelHECPolynomial INTEGER,
        ptIOHWHSLATMChannelHECVerification  INTEGER,
        ptIOHWHSLATMChannelQualityOfService   INTEGER,
        ptIOHWHSLATMChannelT1           Integer32,
        ptIOHWHSLATMChannelT2           Integer32,
        ptIOHWHSLATMChannelT3           Integer32,
        ptIOHWHSLATMChannelAlignment    INTEGER,
        ptIOHWHSLATMChannelN1           Integer32,
        ptIOHWHSLATMChannelCongestionLevel1Onset        Integer32,
        ptIOHWHSLATMChannelCongestionLevel2Onset        Integer32,
        ptIOHWHSLATMChannelCongestionLevel3Onset        Integer32,
        ptIOHWHSLATMChannelCongestionLevel1Abate        Integer32,
        ptIOHWHSLATMChannelCongestionLevel2Abate        Integer32,
        ptIOHWHSLATMChannelCongestionLevel3Abate        Integer32,
        ptIOHWHSLATMChannelL3Use        INTEGER,
        ptIOHWHSLATMChannelDebug        DisplayString,
        ptIOHWHSLATMChannelManagement   INTEGER,
        ptIOHWHSLATMChannelSSCFMessages INTEGER,
        ptIOHWHSLATMChannelSSCOPMessages INTEGER,
        ptIOHWHSLATMChannelPDUs         INTEGER,
        ptIOHWHSLATMChannelIOManagerIndex Integer32,
        ptIOHWHSLATMChannelHSLATMChannelsIndex      Integer32,
        ptIOHWHSLATMChannelActions      INTEGER,
        ptIOHWHSLATMChannelParentOID    OBJECT IDENTIFIER,
        ptIOHWHSLATMChannelRowStatus    RowStatus,
        ptIOHWHSLATMChannelIndex        Integer32
    }

ptIOHWHSLATMChannelChannelNumber OBJECT-TYPE
    SYNTAX          Integer32 (-2147483648..2147483647)
    MAX-ACCESS      read-only
    STATUS          current
    DESCRIPTION     
            "Number that is used in communication with Level 3"
    ::= { ptIOHWHSLATMChannelEntry 1 }

ptIOHWHSLATMChannelCLLI OBJECT-TYPE
    SYNTAX          DisplayString (SIZE(0..255))
    MAX-ACCESS      read-create
    STATUS          current
    DESCRIPTION     
            "Common Language Location Identifier string for this channel."
    ::= { ptIOHWHSLATMChannelEntry 2 }

ptIOHWHSLATMChannelPort OBJECT-TYPE
    SYNTAX          INTEGER { port0(0), port1(1), port2(2), port3(3), 
                        port4(4), port5(5), port6(6), port7(7), 
                        monitorPort(8), notConfigured(9), port8(10) }
    MAX-ACCESS      read-only
    STATUS          current
    DESCRIPTION     
            "The number of the I/O port with the physical connection to the link"
    ::= { ptIOHWHSLATMChannelEntry 3 }

ptIOHWHSLATMChannelChannelState OBJECT-TYPE
    SYNTAX          INTEGER { activated(0), deactivated(1), failed(2) }
    MAX-ACCESS      read-only
    STATUS          current
    DESCRIPTION     
            "Link Manager state"
    ::= { ptIOHWHSLATMChannelEntry 4 }

ptIOHWHSLATMChannelVPI OBJECT-TYPE
    SYNTAX          Integer32 (-2147483648..2147483647)
    MAX-ACCESS      read-create
    STATUS          current
    DESCRIPTION     
            "Virtual path identifier (0-255)"
    ::= { ptIOHWHSLATMChannelEntry 7 }

ptIOHWHSLATMChannelVCI OBJECT-TYPE
    SYNTAX          Integer32 (-2147483648..2147483647)
    MAX-ACCESS      read-create
    STATUS          current
    DESCRIPTION     
            "Virtual channel identifier (0-65535)"
    ::= { ptIOHWHSLATMChannelEntry 8 }

ptIOHWHSLATMChannelScrambling OBJECT-TYPE
    SYNTAX          INTEGER { disabled(0), enabled(1) }
    MAX-ACCESS      read-create
    STATUS          current
    DESCRIPTION     
            "Scrambling of the payload part of the ATM cell"
    ::= { ptIOHWHSLATMChannelEntry 9 }

ptIOHWHSLATMChannelHECPolynomial OBJECT-TYPE
    SYNTAX          INTEGER { disabled(0), enabled(1) }
    MAX-ACCESS      read-create
    STATUS          current
    DESCRIPTION     
            "Also called coset, HEC ATM polynomial option used in HEC calculation"
    ::= { ptIOHWHSLATMChannelEntry 10 }

ptIOHWHSLATMChannelHECVerification OBJECT-TYPE
    SYNTAX          INTEGER { filter(0), correct(1) }
    MAX-ACCESS      read-create
    STATUS          current
    DESCRIPTION     
            "Filter or correct cells received with invalid HEC"
    ::= { ptIOHWHSLATMChannelEntry 11 }

ptIOHWHSLATMChannelQualityOfService OBJECT-TYPE
    SYNTAX          INTEGER { cbr(0), rtVbr(1), nrtVbr(2), ubr(3) }
    MAX-ACCESS      read-create
    STATUS          current
    DESCRIPTION     
            "Constant, rt-aVerage, nrt-aVerage, Unspecified"
    ::= { ptIOHWHSLATMChannelEntry 12 }

ptIOHWHSLATMChannelT1 OBJECT-TYPE
    SYNTAX          Integer32 (-2147483648..2147483647)
    MAX-ACCESS      read-create
    STATUS          current
    DESCRIPTION     
            "T1 Timer. Time in ms between link release and re-establishment during alignment"
    ::= { ptIOHWHSLATMChannelEntry 13 }

ptIOHWHSLATMChannelT2 OBJECT-TYPE
    SYNTAX          Integer32 (-2147483648..2147483647)
    MAX-ACCESS      read-create
    STATUS          current
    DESCRIPTION     
            "T2 Timer. Time in ms that SSCF will attempt link alignment"
    ::= { ptIOHWHSLATMChannelEntry 14 }

ptIOHWHSLATMChannelT3 OBJECT-TYPE
    SYNTAX          Integer32 (-2147483648..2147483647)
    MAX-ACCESS      read-create
    STATUS          current
    DESCRIPTION     
            "T3 Timer. Time in ms between proving PDUs"
    ::= { ptIOHWHSLATMChannelEntry 15 }

ptIOHWHSLATMChannelAlignment OBJECT-TYPE
    SYNTAX          INTEGER { normal(0), emergency(1) }
    MAX-ACCESS      read-create
    STATUS          current
    DESCRIPTION     
            "Alignment type"
    ::= { ptIOHWHSLATMChannelEntry 16 }

ptIOHWHSLATMChannelN1 OBJECT-TYPE
    SYNTAX          Integer32 (-2147483648..2147483647)
    MAX-ACCESS      read-create
    STATUS          current
    DESCRIPTION     
            "Number of PDUs sent during normal proving"
    ::= { ptIOHWHSLATMChannelEntry 17 }

ptIOHWHSLATMChannelCongestionLevel1Onset OBJECT-TYPE
    SYNTAX          Integer32 (-2147483648..2147483647)
    MAX-ACCESS      read-create
    STATUS          current
    DESCRIPTION     
            "Onset of level 1 congestion for ANSI and Onset of congestion for ITU. In ITU any congestion level will trigger notice to L3."
    ::= { ptIOHWHSLATMChannelEntry 18 }

ptIOHWHSLATMChannelCongestionLevel2Onset OBJECT-TYPE
    SYNTAX          Integer32 (-2147483648..2147483647)
    MAX-ACCESS      read-create
    STATUS          current
    DESCRIPTION     
            "Onset of level 2 congestion for ANSI. In ITU any congestion level will trigger notice to L3."
    ::= { ptIOHWHSLATMChannelEntry 19 }

ptIOHWHSLATMChannelCongestionLevel3Onset OBJECT-TYPE
    SYNTAX          Integer32 (-2147483648..2147483647)
    MAX-ACCESS      read-create
    STATUS          current
    DESCRIPTION     
            "Onset of level 3 congestion for ANSI. In ITU any congestion level will trigger notice to L3."
    ::= { ptIOHWHSLATMChannelEntry 20 }

ptIOHWHSLATMChannelCongestionLevel1Abate OBJECT-TYPE
    SYNTAX          Integer32 (-2147483648..2147483647)
    MAX-ACCESS      read-create
    STATUS          current
    DESCRIPTION     
            "Level 1 congestion abatement for ANSI and congestion abatement for ITU. In ITU the lowest abatement the clear notice trigger for L3."
    ::= { ptIOHWHSLATMChannelEntry 21 }

ptIOHWHSLATMChannelCongestionLevel2Abate OBJECT-TYPE
    SYNTAX          Integer32 (-2147483648..2147483647)
    MAX-ACCESS      read-create
    STATUS          current
    DESCRIPTION     
            "Level 2 congestion abatement for ANSI. In ITU the lowest abatement the clear notice trigger for L3."
    ::= { ptIOHWHSLATMChannelEntry 22 }

ptIOHWHSLATMChannelCongestionLevel3Abate OBJECT-TYPE
    SYNTAX          Integer32 (-2147483648..2147483647)
    MAX-ACCESS      read-create
    STATUS          current
    DESCRIPTION     
            "Level 3 congestion abatement for ANSI. In ITU the lowest abatement the clear notice trigger for L3."
    ::= { ptIOHWHSLATMChannelEntry 23 }

ptIOHWHSLATMChannelL3Use OBJECT-TYPE
    SYNTAX          INTEGER { inUse(-1), available(0) }
    MAX-ACCESS      read-only
    STATUS          current
    DESCRIPTION     
            "Either the assigned Server Process number or AVAILABLE if not registered."
    ::= { ptIOHWHSLATMChannelEntry 28 }

ptIOHWHSLATMChannelDebug OBJECT-TYPE
    SYNTAX          DisplayString (SIZE(0..255))
    MAX-ACCESS      read-only
    STATUS          current
    DESCRIPTION     
            "Information for support purposes."
    ::= { ptIOHWHSLATMChannelEntry 29 }

ptIOHWHSLATMChannelManagement OBJECT-TYPE
    SYNTAX          INTEGER { notLogged(0), logged(1), overridden(2) }
    MAX-ACCESS      read-create
    STATUS          current
    DESCRIPTION     
            "Minimal logging - mostly exchanges with level 3."
    ::= { ptIOHWHSLATMChannelEntry 30 }

ptIOHWHSLATMChannelSSCFMessages OBJECT-TYPE
    SYNTAX          INTEGER { notLogged(0), logged(1), overridden(2) }
    MAX-ACCESS      read-create
    STATUS          current
    DESCRIPTION     
            "High level state transitions. Few logs during normal operations."
    ::= { ptIOHWHSLATMChannelEntry 31 }

ptIOHWHSLATMChannelSSCOPMessages OBJECT-TYPE
    SYNTAX          INTEGER { notLogged(0), logged(1), overridden(2) }
    MAX-ACCESS      read-create
    STATUS          current
    DESCRIPTION     
            "Verbose logging of protocol events. Not for production environment."
    ::= { ptIOHWHSLATMChannelEntry 32 }

ptIOHWHSLATMChannelPDUs OBJECT-TYPE
    SYNTAX          INTEGER { notLogged(0), logged(1), overridden(2) }
    MAX-ACCESS      read-create
    STATUS          current
    DESCRIPTION     
            "Very verbose logging or each message. Not for production environment."
    ::= { ptIOHWHSLATMChannelEntry 33 }

ptIOHWHSLATMChannelIOManagerIndex OBJECT-TYPE
    SYNTAX          Integer32 (-2147483648..2147483647)
    MAX-ACCESS      not-accessible
    STATUS          current
    DESCRIPTION     
            "This is the index of the parent type for this object.
             This parent type is IOManager."
    ::= { ptIOHWHSLATMChannelEntry 242 }

ptIOHWHSLATMChannelHSLATMChannelsIndex OBJECT-TYPE
    SYNTAX          Integer32 (-2147483648..2147483647)
    MAX-ACCESS      not-accessible
    STATUS          current
    DESCRIPTION     
            "This is the index of the parent type for this object.
             This parent type is HSLATMChannels."
    ::= { ptIOHWHSLATMChannelEntry 243 }

ptIOHWHSLATMChannelActions OBJECT-TYPE
    SYNTAX          INTEGER { activate(1), deactivate(2) }
    MAX-ACCESS      read-create
    STATUS          current
    DESCRIPTION     
            "The OID of all possible actions for this instance"
    ::= { ptIOHWHSLATMChannelEntry 252 }

ptIOHWHSLATMChannelParentOID OBJECT-TYPE
    SYNTAX          OBJECT IDENTIFIER
    MAX-ACCESS      read-create
    STATUS          current
    DESCRIPTION     
            "The OID of the parent object for this instance"
    ::= { ptIOHWHSLATMChannelEntry 253 }

ptIOHWHSLATMChannelRowStatus OBJECT-TYPE
    SYNTAX          RowStatus
    MAX-ACCESS      read-create
    STATUS          current
    DESCRIPTION     
            "The row status for the IOHWHSLATMChannel table"
    ::= { ptIOHWHSLATMChannelEntry 254 }

ptIOHWHSLATMChannelIndex OBJECT-TYPE
    SYNTAX          Integer32 (-2147483648..2147483647)
    MAX-ACCESS      not-accessible
    STATUS          current
    DESCRIPTION     
            "The row number for the IOHWHSLATMChannel table"
    ::= { ptIOHWHSLATMChannelEntry 255 }

ptIOHWHSLATMChannelDEBUG OBJECT IDENTIFIER
    ::= { ptIOHWHSLATMChannel 1103 }

ptIOHWHSLATMChannelDEBUGTable OBJECT-TYPE
    SYNTAX          SEQUENCE OF PtIOHWHSLATMChannelDEBUGEntry
    MAX-ACCESS      not-accessible
    STATUS          current
    DESCRIPTION     
            "No description supplied in the proxy config file."
    ::= { ptIOHWHSLATMChannelDEBUG 1 }

ptIOHWHSLATMChannelDEBUGEntry OBJECT-TYPE
    SYNTAX          PtIOHWHSLATMChannelDEBUGEntry
    MAX-ACCESS      not-accessible
    STATUS          current
    DESCRIPTION     
            "A sequence of IOHWHSLATMChannelDEBUG attributes."
    INDEX           { ptConnGroupIndex, 
                      ptIOHWHSLATMChannelDEBUGIOManagerIndex, 
                      ptIOHWHSLATMChannelDEBUGHSLATMChannelsIndex, 
                      ptIOHWHSLATMChannelDEBUGHSLATMChannelIndex, 
                      ptIOHWHSLATMChannelDEBUGIndex }
    ::= { ptIOHWHSLATMChannelDEBUGTable 1 }

PtIOHWHSLATMChannelDEBUGEntry ::=
    SEQUENCE {
        ptIOHWHSLATMChannelDEBUGSSCOPState  DisplayString,
        ptIOHWHSLATMChannelDEBUGSSCFState DisplayString,
        ptIOHWHSLATMChannelDEBUGIOManagerIndex      Integer32,
        ptIOHWHSLATMChannelDEBUGHSLATMChannelsIndex           Integer32,
        ptIOHWHSLATMChannelDEBUGHSLATMChannelIndex          Integer32,
        ptIOHWHSLATMChannelDEBUGActions INTEGER,
        ptIOHWHSLATMChannelDEBUGParentOID OBJECT IDENTIFIER,
        ptIOHWHSLATMChannelDEBUGRowStatus RowStatus,
        ptIOHWHSLATMChannelDEBUGIndex   Integer32
    }

ptIOHWHSLATMChannelDEBUGSSCOPState OBJECT-TYPE
    SYNTAX          DisplayString (SIZE(0..255))
    MAX-ACCESS      read-only
    STATUS          current
    DESCRIPTION     
            "."
    ::= { ptIOHWHSLATMChannelDEBUGEntry 1 }

ptIOHWHSLATMChannelDEBUGSSCFState OBJECT-TYPE
    SYNTAX          DisplayString (SIZE(0..255))
    MAX-ACCESS      read-only
    STATUS          current
    DESCRIPTION     
            "."
    ::= { ptIOHWHSLATMChannelDEBUGEntry 2 }

ptIOHWHSLATMChannelDEBUGIOManagerIndex OBJECT-TYPE
    SYNTAX          Integer32 (-2147483648..2147483647)
    MAX-ACCESS      not-accessible
    STATUS          current
    DESCRIPTION     
            "This is the index of the parent type for this object.
             This parent type is IOManager."
    ::= { ptIOHWHSLATMChannelDEBUGEntry 242 }

ptIOHWHSLATMChannelDEBUGHSLATMChannelsIndex OBJECT-TYPE
    SYNTAX          Integer32 (-2147483648..2147483647)
    MAX-ACCESS      not-accessible
    STATUS          current
    DESCRIPTION     
            "This is the index of the parent type for this object.
             This parent type is HSLATMChannels."
    ::= { ptIOHWHSLATMChannelDEBUGEntry 243 }

ptIOHWHSLATMChannelDEBUGHSLATMChannelIndex OBJECT-TYPE
    SYNTAX          Integer32 (-2147483648..2147483647)
    MAX-ACCESS      not-accessible
    STATUS          current
    DESCRIPTION     
            "This is the index of the parent type for this object.
             This parent type is HSLATMChannel."
    ::= { ptIOHWHSLATMChannelDEBUGEntry 244 }

ptIOHWHSLATMChannelDEBUGActions OBJECT-TYPE
    SYNTAX          INTEGER { startLink(1), stopLink(2) }
    MAX-ACCESS      read-create
    STATUS          current
    DESCRIPTION     
            "The OID of all possible actions for this instance"
    ::= { ptIOHWHSLATMChannelDEBUGEntry 252 }

ptIOHWHSLATMChannelDEBUGParentOID OBJECT-TYPE
    SYNTAX          OBJECT IDENTIFIER
    MAX-ACCESS      read-create
    STATUS          current
    DESCRIPTION     
            "The OID of the parent object for this instance"
    ::= { ptIOHWHSLATMChannelDEBUGEntry 253 }

ptIOHWHSLATMChannelDEBUGRowStatus OBJECT-TYPE
    SYNTAX          RowStatus
    MAX-ACCESS      read-create
    STATUS          current
    DESCRIPTION     
            "The row status for the IOHWHSLATMChannelDEBUG table"
    ::= { ptIOHWHSLATMChannelDEBUGEntry 254 }

ptIOHWHSLATMChannelDEBUGIndex OBJECT-TYPE
    SYNTAX          Integer32 (-2147483648..2147483647)
    MAX-ACCESS      not-accessible
    STATUS          current
    DESCRIPTION     
            "The row number for the IOHWHSLATMChannelDEBUG table"
    ::= { ptIOHWHSLATMChannelDEBUGEntry 255 }

ptIOHWSerialChannels OBJECT IDENTIFIER
    ::= { ptIOHWIOManager 1085 }

ptIOHWSerialChannelsTable OBJECT-TYPE
    SYNTAX          SEQUENCE OF PtIOHWSerialChannelsEntry
    MAX-ACCESS      not-accessible
    STATUS          current
    DESCRIPTION     
            "No description supplied in the proxy config file."
    ::= { ptIOHWSerialChannels 1 }

ptIOHWSerialChannelsEntry OBJECT-TYPE
    SYNTAX          PtIOHWSerialChannelsEntry
    MAX-ACCESS      not-accessible
    STATUS          current
    DESCRIPTION     
            "A sequence of IOHWSerialChannels attributes."
    INDEX           { ptConnGroupIndex, 
                      ptIOHWSerialChannelsIOManagerIndex, 
                      ptIOHWSerialChannelsIndex }
    ::= { ptIOHWSerialChannelsTable 1 }

PtIOHWSerialChannelsEntry ::=
    SEQUENCE {
        ptIOHWSerialChannelsIOManagerIndex  Integer32,
        ptIOHWSerialChannelsParentOID   OBJECT IDENTIFIER,
        ptIOHWSerialChannelsRowStatus   RowStatus,
        ptIOHWSerialChannelsIndex       Integer32
    }

ptIOHWSerialChannelsIOManagerIndex OBJECT-TYPE
    SYNTAX          Integer32 (-2147483648..2147483647)
    MAX-ACCESS      not-accessible
    STATUS          current
    DESCRIPTION     
            "This is the index of the parent type for this object.
             This parent type is IOManager."
    ::= { ptIOHWSerialChannelsEntry 242 }

ptIOHWSerialChannelsParentOID OBJECT-TYPE
    SYNTAX          OBJECT IDENTIFIER
    MAX-ACCESS      read-create
    STATUS          current
    DESCRIPTION     
            "The OID of the parent object for this instance"
    ::= { ptIOHWSerialChannelsEntry 253 }

ptIOHWSerialChannelsRowStatus OBJECT-TYPE
    SYNTAX          RowStatus
    MAX-ACCESS      read-create
    STATUS          current
    DESCRIPTION     
            "The row status for the IOHWSerialChannels table"
    ::= { ptIOHWSerialChannelsEntry 254 }

ptIOHWSerialChannelsIndex OBJECT-TYPE
    SYNTAX          Integer32 (-2147483648..2147483647)
    MAX-ACCESS      not-accessible
    STATUS          current
    DESCRIPTION     
            "The row number for the IOHWSerialChannels table"
    ::= { ptIOHWSerialChannelsEntry 255 }

ptIOHWSerialChannel OBJECT IDENTIFIER
    ::= { ptIOHWSerialChannels 1104 }

ptIOHWSerialChannelTable OBJECT-TYPE
    SYNTAX          SEQUENCE OF PtIOHWSerialChannelEntry
    MAX-ACCESS      not-accessible
    STATUS          current
    DESCRIPTION     
            "No description supplied in the proxy config file."
    ::= { ptIOHWSerialChannel 1 }

ptIOHWSerialChannelEntry OBJECT-TYPE
    SYNTAX          PtIOHWSerialChannelEntry
    MAX-ACCESS      not-accessible
    STATUS          current
    DESCRIPTION     
            "A sequence of IOHWSerialChannel attributes."
    INDEX           { ptConnGroupIndex, 
                      ptIOHWSerialChannelIOManagerIndex, 
                      ptIOHWSerialChannelSerialChannelsIndex, 
                      ptIOHWSerialChannelIndex }
    ::= { ptIOHWSerialChannelTable 1 }

PtIOHWSerialChannelEntry ::=
    SEQUENCE {
        ptIOHWSerialChannelIOManagerIndex Integer32,
        ptIOHWSerialChannelSerialChannelsIndex      Integer32,
        ptIOHWSerialChannelParentOID    OBJECT IDENTIFIER,
        ptIOHWSerialChannelRowStatus    RowStatus,
        ptIOHWSerialChannelIndex        Integer32
    }

ptIOHWSerialChannelIOManagerIndex OBJECT-TYPE
    SYNTAX          Integer32 (-2147483648..2147483647)
    MAX-ACCESS      not-accessible
    STATUS          current
    DESCRIPTION     
            "This is the index of the parent type for this object.
             This parent type is IOManager."
    ::= { ptIOHWSerialChannelEntry 242 }

ptIOHWSerialChannelSerialChannelsIndex OBJECT-TYPE
    SYNTAX          Integer32 (-2147483648..2147483647)
    MAX-ACCESS      not-accessible
    STATUS          current
    DESCRIPTION     
            "This is the index of the parent type for this object.
             This parent type is SerialChannels."
    ::= { ptIOHWSerialChannelEntry 243 }

ptIOHWSerialChannelParentOID OBJECT-TYPE
    SYNTAX          OBJECT IDENTIFIER
    MAX-ACCESS      read-create
    STATUS          current
    DESCRIPTION     
            "The OID of the parent object for this instance"
    ::= { ptIOHWSerialChannelEntry 253 }

ptIOHWSerialChannelRowStatus OBJECT-TYPE
    SYNTAX          RowStatus
    MAX-ACCESS      read-create
    STATUS          current
    DESCRIPTION     
            "The row status for the IOHWSerialChannel table"
    ::= { ptIOHWSerialChannelEntry 254 }

ptIOHWSerialChannelIndex OBJECT-TYPE
    SYNTAX          Integer32 (-2147483648..2147483647)
    MAX-ACCESS      not-accessible
    STATUS          current
    DESCRIPTION     
            "The row number for the IOHWSerialChannel table"
    ::= { ptIOHWSerialChannelEntry 255 }

ptIOHWPortClocking OBJECT IDENTIFIER
    ::= { ptIOHWIOManager 1088 }

ptIOHWPortClockingTable OBJECT-TYPE
    SYNTAX          SEQUENCE OF PtIOHWPortClockingEntry
    MAX-ACCESS      not-accessible
    STATUS          current
    DESCRIPTION     
            "No description supplied in the proxy config file."
    ::= { ptIOHWPortClocking 1 }

ptIOHWPortClockingEntry OBJECT-TYPE
    SYNTAX          PtIOHWPortClockingEntry
    MAX-ACCESS      not-accessible
    STATUS          current
    DESCRIPTION     
            "A sequence of IOHWPortClocking attributes."
    INDEX           { ptConnGroupIndex, ptIOHWPortClockingIOManagerIndex, 
                      ptIOHWPortClockingIndex }
    ::= { ptIOHWPortClockingTable 1 }

PtIOHWPortClockingEntry ::=
    SEQUENCE {
        ptIOHWPortClockingPerPortClocking INTEGER,
        ptIOHWPortClockingPrimaryClockSource    INTEGER,
        ptIOHWPortClockingSecondaryClockSource      INTEGER,
        ptIOHWPortClockingCurrentClockSource    INTEGER,
        ptIOHWPortClockingClockMode     INTEGER,
        ptIOHWPortClockingIOManagerIndex Integer32,
        ptIOHWPortClockingParentOID     OBJECT IDENTIFIER,
        ptIOHWPortClockingRowStatus     RowStatus,
        ptIOHWPortClockingIndex         Integer32
    }

ptIOHWPortClockingPerPortClocking OBJECT-TYPE
    SYNTAX          INTEGER { disabled(0), enabled(1) }
    MAX-ACCESS      read-only
    STATUS          current
    DESCRIPTION     
            "If ENABLED all ports can be configured to maintain separate clocking sources, otherwise there is a single clocking source for all ports. (hardware dependent)"
    ::= { ptIOHWPortClockingEntry 41 }

ptIOHWPortClockingPrimaryClockSource OBJECT-TYPE
    SYNTAX          INTEGER { none(0), internal(1), port0(2), port1(3), 
                        port2(4), port3(5), port4(6), port5(7), port6(8), 
                        port7(9), monitorPort(10), clockA(11), 
                        clockB(12), port8(13), telcoA(14), telcoB(15) }
    MAX-ACCESS      read-create
    STATUS          current
    DESCRIPTION     
            "Primary Clock source"
    ::= { ptIOHWPortClockingEntry 42 }

ptIOHWPortClockingSecondaryClockSource OBJECT-TYPE
    SYNTAX          INTEGER { none(0), internal(1), port0(2), port1(3), 
                        port2(4), port3(5), port4(6), port5(7), port6(8), 
                        port7(9), monitorPort(10), clockA(11), 
                        clockB(12), port8(13), telcoA(14), telcoB(15) }
    MAX-ACCESS      read-create
    STATUS          current
    DESCRIPTION     
            "Secondary Clock source"
    ::= { ptIOHWPortClockingEntry 43 }

ptIOHWPortClockingCurrentClockSource OBJECT-TYPE
    SYNTAX          INTEGER { none(0), internal(1), port0(2), port1(3), 
                        port2(4), port3(5), port4(6), port5(7), port6(8), 
                        port7(9), monitorPort(10), clockA(11), 
                        clockB(12), port8(13), telcoA(14), telcoB(15) }
    MAX-ACCESS      read-only
    STATUS          current
    DESCRIPTION     
            "Current clock source"
    ::= { ptIOHWPortClockingEntry 44 }

ptIOHWPortClockingClockMode OBJECT-TYPE
    SYNTAX          INTEGER { standAlone(3), slave(0), masterA(1), 
                        masterB(2), masterTelcoA(4), masterTelcoB(5) }
    MAX-ACCESS      read-create
    STATUS          current
    DESCRIPTION     
            "Clock mode for H110 enabled devices"
    ::= { ptIOHWPortClockingEntry 45 }

ptIOHWPortClockingIOManagerIndex OBJECT-TYPE
    SYNTAX          Integer32 (-2147483648..2147483647)
    MAX-ACCESS      not-accessible
    STATUS          current
    DESCRIPTION     
            "This is the index of the parent type for this object.
             This parent type is IOManager."
    ::= { ptIOHWPortClockingEntry 242 }

ptIOHWPortClockingParentOID OBJECT-TYPE
    SYNTAX          OBJECT IDENTIFIER
    MAX-ACCESS      read-create
    STATUS          current
    DESCRIPTION     
            "The OID of the parent object for this instance"
    ::= { ptIOHWPortClockingEntry 253 }

ptIOHWPortClockingRowStatus OBJECT-TYPE
    SYNTAX          RowStatus
    MAX-ACCESS      read-create
    STATUS          current
    DESCRIPTION     
            "The row status for the IOHWPortClocking table"
    ::= { ptIOHWPortClockingEntry 254 }

ptIOHWPortClockingIndex OBJECT-TYPE
    SYNTAX          Integer32 (-2147483648..2147483647)
    MAX-ACCESS      not-accessible
    STATUS          current
    DESCRIPTION     
            "The row number for the IOHWPortClocking table"
    ::= { ptIOHWPortClockingEntry 255 }

ptIOHWPort OBJECT IDENTIFIER
    ::= { ptIOHWIOManager 1089 }

ptIOHWPortTable OBJECT-TYPE
    SYNTAX          SEQUENCE OF PtIOHWPortEntry
    MAX-ACCESS      not-accessible
    STATUS          current
    DESCRIPTION     
            "No description supplied in the proxy config file."
    ::= { ptIOHWPort 1 }

ptIOHWPortEntry OBJECT-TYPE
    SYNTAX          PtIOHWPortEntry
    MAX-ACCESS      not-accessible
    STATUS          current
    DESCRIPTION     
            "A sequence of IOHWPort attributes."
    INDEX           { ptConnGroupIndex, ptIOHWPortIOManagerIndex, 
                      ptIOHWPortIndex }
    ::= { ptIOHWPortTable 1 }

PtIOHWPortEntry ::=
    SEQUENCE {
        ptIOHWPortPortNumber            INTEGER,
        ptIOHWPortInterfaceType         INTEGER,
        ptIOHWPortEncoding              INTEGER,
        ptIOHWPortLineLength            INTEGER,
        ptIOHWPortFacilityDataLink      INTEGER,
        ptIOHWPortAlarmSquelch          INTEGER,
        ptIOHWPortAlarmEgress           INTEGER,
        ptIOHWPortLoopbackMode          INTEGER,
        ptIOHWPortFramingStatus         INTEGER,
        ptIOHWPortNoAlarm               INTEGER,
        ptIOHWPortRemoteRxLOF           INTEGER,
        ptIOHWPortRemoteTxLOF           INTEGER,
        ptIOHWPortRxAIS                 INTEGER,
        ptIOHWPortTxAIS                 INTEGER,
        ptIOHWPortLossOfFrame           INTEGER,
        ptIOHWPortLossOfSynchronization INTEGER,
        ptIOHWPortLoopbackState         INTEGER,
        ptIOHWPortT16AIS                INTEGER,
        ptIOHWPortRemoteRxLOMF          INTEGER,
        ptIOHWPortRemoteTxLOMF          INTEGER,
        ptIOHWPortRxTestCode            INTEGER,
        ptIOHWPortOtherFailure          INTEGER,
        ptIOHWPortUnavailableSignalState INTEGER,
        ptIOHWPortNetEquipmentOOS       INTEGER,
        ptIOHWPortRxPayloadAIS          INTEGER,
        ptIOHWPortPerformanceThreshold  INTEGER,
        ptIOHWPortNoLoopback            INTEGER,
        ptIOHWPortRemotePayloadLoopback INTEGER,
        ptIOHWPortRemoteLineLoopback    INTEGER,
        ptIOHWPortLocalLineLoopback     INTEGER,
        ptIOHWPortFarEndPayloadLoopback INTEGER,
        ptIOHWPortFarEndLineLoopback    INTEGER,
        ptIOHWPortCurrentGain           Integer32,
        ptIOHWPortCurrentAttenuation    Integer32,
        ptIOHWPortStatistics            INTEGER,
        ptIOHWPortClockSource           INTEGER,
        ptIOHWPortStatusAlarms          INTEGER,
        ptIOHWPortFarEndLoopbackType    INTEGER,
        ptIOHWPortFarEndLoopbackActivationTime      Integer32,
        ptIOHWPortFarEndLoopbackDeactivationTime        Integer32,
        ptIOHWPortBERTPattern           INTEGER,
        ptIOHWPortPRBSDetectionTimer    Integer32,
        ptIOHWPortBERTDuration          Integer32,
        ptIOHWPortBERTStatus            DisplayString,
        ptIOHWPortBERTResult            DisplayString,
        ptIOHWPortPRBSSyncSeconds       Integer32,
        ptIOHWPortPRBSLostSeconds       Integer32,
        ptIOHWPortPRBSBitErrors         Integer32,
        ptIOHWPortPRBSErrorInstances    Integer32,
        ptIOHWPortIOManagerIndex        Integer32,
        ptIOHWPortActions               INTEGER,
        ptIOHWPortParentOID             OBJECT IDENTIFIER,
        ptIOHWPortRowStatus             RowStatus,
        ptIOHWPortIndex                 Integer32
    }

ptIOHWPortPortNumber OBJECT-TYPE
    SYNTAX          INTEGER { port0(0), port1(1), port2(2), port3(3), 
                        port4(4), port5(5), port6(6), port7(7), 
                        monitorPort(8), notConfigured(9), port8(10) }
    MAX-ACCESS      read-only
    STATUS          current
    DESCRIPTION     
            "Port number as indicated on physical device."
    ::= { ptIOHWPortEntry 1 }

ptIOHWPortInterfaceType OBJECT-TYPE
    SYNTAX          INTEGER { j1(0), t1Esf(1), t1D4(2), e1(3), e1Crc4(4) }
    MAX-ACCESS      read-create
    STATUS          current
    DESCRIPTION     
            "Interface type for the port (J1, T1_ESF, T1_D4, E1, E1_CRC4)"
    ::= { ptIOHWPortEntry 2 }

ptIOHWPortEncoding OBJECT-TYPE
    SYNTAX          INTEGER { b8zs(0), hdb3(1), ami(2) }
    MAX-ACCESS      read-create
    STATUS          current
    DESCRIPTION     
            "Line Encoding mode (B8ZS, HDB3, AMI)"
    ::= { ptIOHWPortEntry 3 }

ptIOHWPortLineLength OBJECT-TYPE
    SYNTAX          INTEGER { e175OhmShorthaul(0), e1120OhmShorthaul(1), 
                        e175OhmLonghaul(2), e1120OhmLonghaul(3), 
                        t1Shorthaul0133ft(4), t1Shorthaul133266ft(5), 
                        t1Shorthaul266399ft(6), t1Shorthaul399533ft(7), 
                        t1Shorthaul533655ft(8), t1Longhaul0db(9), 
                        t1Longhaul7db(10), t1Longhaul15db(11), 
                        t1Longhaul22db(12), j1Shorthaul(13), 
                        j1Longhaul(14) }
    MAX-ACCESS      read-create
    STATUS          current
    DESCRIPTION     
            "Transmit buildout for interface type."
    ::= { ptIOHWPortEntry 4 }

ptIOHWPortFacilityDataLink OBJECT-TYPE
    SYNTAX          INTEGER { disabled(0), enabled(1) }
    MAX-ACCESS      read-create
    STATUS          current
    DESCRIPTION     
            "Facility DataLink (FDL) is only applicable for T1_ESF interface type"
    ::= { ptIOHWPortEntry 7 }

ptIOHWPortAlarmSquelch OBJECT-TYPE
    SYNTAX          INTEGER { disabled(0), enabled(1) }
    MAX-ACCESS      read-create
    STATUS          current
    DESCRIPTION     
            "Stop responding to received alarms"
    ::= { ptIOHWPortEntry 8 }

ptIOHWPortAlarmEgress OBJECT-TYPE
    SYNTAX          INTEGER { rai(0), ais(1) }
    MAX-ACCESS      read-create
    STATUS          current
    DESCRIPTION     
            "Type of alarm to transmit on reception of AIS (red alarm) (RAI, AIS)"
    ::= { ptIOHWPortEntry 9 }

ptIOHWPortLoopbackMode OBJECT-TYPE
    SYNTAX          INTEGER { disabled(0), remotePayload(1), 
                        remoteLine(2), localLine(3) }
    MAX-ACCESS      read-create
    STATUS          current
    DESCRIPTION     
            "Loopback mode (DISABLED, REMOTE_PAYLOAD, REMOTE_LINE, LOCAL_LINE)"
    ::= { ptIOHWPortEntry 10 }

ptIOHWPortFramingStatus OBJECT-TYPE
    SYNTAX          INTEGER { na(0), nosync(1), sync(2) }
    MAX-ACCESS      read-only
    STATUS          current
    DESCRIPTION     
            "Framing Status (SYNC, NOSYNC)"
    ::= { ptIOHWPortEntry 11 }

ptIOHWPortNoAlarm OBJECT-TYPE
    SYNTAX          INTEGER { clear(0), set(1), na(3) }
    MAX-ACCESS      read-only
    STATUS          current
    DESCRIPTION     
            "None of the defined alarms are present"
    ::= { ptIOHWPortEntry 12 }

ptIOHWPortRemoteRxLOF OBJECT-TYPE
    SYNTAX          INTEGER { clear(0), set(1), na(3) }
    MAX-ACCESS      read-only
    STATUS          current
    DESCRIPTION     
            "Remote Receiver Loss of Frame"
    ::= { ptIOHWPortEntry 13 }

ptIOHWPortRemoteTxLOF OBJECT-TYPE
    SYNTAX          INTEGER { clear(0), set(1), na(3) }
    MAX-ACCESS      read-only
    STATUS          current
    DESCRIPTION     
            "Remote Transmitter Loss of Frame"
    ::= { ptIOHWPortEntry 14 }

ptIOHWPortRxAIS OBJECT-TYPE
    SYNTAX          INTEGER { clear(0), set(1), na(3) }
    MAX-ACCESS      read-only
    STATUS          current
    DESCRIPTION     
            "Receiver Alarm Indication Signal"
    ::= { ptIOHWPortEntry 15 }

ptIOHWPortTxAIS OBJECT-TYPE
    SYNTAX          INTEGER { clear(0), set(1), na(3) }
    MAX-ACCESS      read-only
    STATUS          current
    DESCRIPTION     
            "Transmitter Alarm Indication Signal"
    ::= { ptIOHWPortEntry 16 }

ptIOHWPortLossOfFrame OBJECT-TYPE
    SYNTAX          INTEGER { clear(0), set(1), na(3) }
    MAX-ACCESS      read-only
    STATUS          current
    DESCRIPTION     
            "Local Loss of Frame"
    ::= { ptIOHWPortEntry 17 }

ptIOHWPortLossOfSynchronization OBJECT-TYPE
    SYNTAX          INTEGER { clear(0), set(1), na(3) }
    MAX-ACCESS      read-only
    STATUS          current
    DESCRIPTION     
            "Local Loss of Synchronization"
    ::= { ptIOHWPortEntry 18 }

ptIOHWPortLoopbackState OBJECT-TYPE
    SYNTAX          INTEGER { clear(0), set(1), na(3) }
    MAX-ACCESS      read-only
    STATUS          current
    DESCRIPTION     
            "Loopback State On/Off"
    ::= { ptIOHWPortEntry 19 }

ptIOHWPortT16AIS OBJECT-TYPE
    SYNTAX          INTEGER { clear(0), set(1), na(3) }
    MAX-ACCESS      read-only
    STATUS          current
    DESCRIPTION     
            "Timeslot 16 AIS Clear/Set"
    ::= { ptIOHWPortEntry 20 }

ptIOHWPortRemoteRxLOMF OBJECT-TYPE
    SYNTAX          INTEGER { clear(0), set(1), na(3) }
    MAX-ACCESS      read-only
    STATUS          current
    DESCRIPTION     
            "Remote Receiver Loss of Multiframe"
    ::= { ptIOHWPortEntry 21 }

ptIOHWPortRemoteTxLOMF OBJECT-TYPE
    SYNTAX          INTEGER { clear(0), set(1), na(3) }
    MAX-ACCESS      read-only
    STATUS          current
    DESCRIPTION     
            "Remote Transmitter Loss of Multiframe"
    ::= { ptIOHWPortEntry 22 }

ptIOHWPortRxTestCode OBJECT-TYPE
    SYNTAX          INTEGER { clear(0), set(1), na(3) }
    MAX-ACCESS      read-only
    STATUS          current
    DESCRIPTION     
            "Receiver Test Code On/Off"
    ::= { ptIOHWPortEntry 23 }

ptIOHWPortOtherFailure OBJECT-TYPE
    SYNTAX          INTEGER { clear(0), set(1), na(3) }
    MAX-ACCESS      read-only
    STATUS          current
    DESCRIPTION     
            "Other Failure Detected"
    ::= { ptIOHWPortEntry 24 }

ptIOHWPortUnavailableSignalState OBJECT-TYPE
    SYNTAX          INTEGER { clear(0), set(1), na(3) }
    MAX-ACCESS      read-only
    STATUS          current
    DESCRIPTION     
            "Unavailable Signal State"
    ::= { ptIOHWPortEntry 25 }

ptIOHWPortNetEquipmentOOS OBJECT-TYPE
    SYNTAX          INTEGER { clear(0), set(1), na(3) }
    MAX-ACCESS      read-only
    STATUS          current
    DESCRIPTION     
            "Network Equipment Out Of Service"
    ::= { ptIOHWPortEntry 26 }

ptIOHWPortRxPayloadAIS OBJECT-TYPE
    SYNTAX          INTEGER { clear(0), set(1), na(3) }
    MAX-ACCESS      read-only
    STATUS          current
    DESCRIPTION     
            "Receiver Payload Alarm Indication Signal"
    ::= { ptIOHWPortEntry 27 }

ptIOHWPortPerformanceThreshold OBJECT-TYPE
    SYNTAX          INTEGER { clear(0), set(1), na(3) }
    MAX-ACCESS      read-only
    STATUS          current
    DESCRIPTION     
            "Performance Threshold"
    ::= { ptIOHWPortEntry 28 }

ptIOHWPortNoLoopback OBJECT-TYPE
    SYNTAX          INTEGER { clear(0), set(1), na(3) }
    MAX-ACCESS      read-only
    STATUS          current
    DESCRIPTION     
            "None of the defined Loopback types are present"
    ::= { ptIOHWPortEntry 29 }

ptIOHWPortRemotePayloadLoopback OBJECT-TYPE
    SYNTAX          INTEGER { clear(0), set(1), na(3) }
    MAX-ACCESS      read-only
    STATUS          current
    DESCRIPTION     
            "Remote Payload Loopback Status"
    ::= { ptIOHWPortEntry 30 }

ptIOHWPortRemoteLineLoopback OBJECT-TYPE
    SYNTAX          INTEGER { clear(0), set(1), na(3) }
    MAX-ACCESS      read-only
    STATUS          current
    DESCRIPTION     
            "Remote Line Loopback Status"
    ::= { ptIOHWPortEntry 31 }

ptIOHWPortLocalLineLoopback OBJECT-TYPE
    SYNTAX          INTEGER { clear(0), set(1), na(3) }
    MAX-ACCESS      read-only
    STATUS          current
    DESCRIPTION     
            "Local Line Loopback Status"
    ::= { ptIOHWPortEntry 32 }

ptIOHWPortFarEndPayloadLoopback OBJECT-TYPE
    SYNTAX          INTEGER { clear(0), set(1), na(3) }
    MAX-ACCESS      read-only
    STATUS          current
    DESCRIPTION     
            "Far End Payload Loopback Status"
    ::= { ptIOHWPortEntry 33 }

ptIOHWPortFarEndLineLoopback OBJECT-TYPE
    SYNTAX          INTEGER { clear(0), set(1), na(3) }
    MAX-ACCESS      read-only
    STATUS          current
    DESCRIPTION     
            "Far End Line Loopback"
    ::= { ptIOHWPortEntry 34 }

ptIOHWPortCurrentGain OBJECT-TYPE
    SYNTAX          Integer32 (-2147483648..2147483647)
    MAX-ACCESS      read-only
    STATUS          current
    DESCRIPTION     
            "The current gain settings in dbs"
    ::= { ptIOHWPortEntry 35 }

ptIOHWPortCurrentAttenuation OBJECT-TYPE
    SYNTAX          Integer32 (-2147483648..2147483647)
    MAX-ACCESS      read-only
    STATUS          current
    DESCRIPTION     
            "The current attenuation in dbs"
    ::= { ptIOHWPortEntry 36 }

ptIOHWPortStatistics OBJECT-TYPE
    SYNTAX          INTEGER { notLogged(0), logged(1), overridden(2) }
    MAX-ACCESS      read-create
    STATUS          current
    DESCRIPTION     
            "Log port statistics to the debug log every 15 minutes."
    ::= { ptIOHWPortEntry 40 }

ptIOHWPortClockSource OBJECT-TYPE
    SYNTAX          INTEGER { through(0), recovered(1) }
    MAX-ACCESS      read-create
    STATUS          current
    DESCRIPTION     
            "Port specific clock source. THROUGH clocking uses on board clock. RECOVERED clocking loops the received clock back out. Availability is hardware dependent."
    ::= { ptIOHWPortEntry 42 }

ptIOHWPortStatusAlarms OBJECT-TYPE
    SYNTAX          INTEGER { disabled(0), enabled(1) }
    MAX-ACCESS      read-create
    STATUS          current
    DESCRIPTION     
            "When enabled MTP2 will alarm on major and critical port status events. Only one critical and one major alarm is raised per port regardless of the number of current critical and major events. These traps are displayed in the dash board and sent to SNMP trap hosts."
    ::= { ptIOHWPortEntry 43 }

ptIOHWPortFarEndLoopbackType OBJECT-TYPE
    SYNTAX          INTEGER { none(0), line(1), payload(2) }
    MAX-ACCESS      read-create
    STATUS          current
    DESCRIPTION     
            "This attribute determines the type of loopback code to send to the far end. \nTransmission of loopback code is only supported for T1. \nPAYLOAD loopback code is only available if Facility Data Link is ENABLED. \nThe default value for T1 is LINE, NONE otherwise."
    ::= { ptIOHWPortEntry 45 }

ptIOHWPortFarEndLoopbackActivationTime OBJECT-TYPE
    SYNTAX          Integer32 (-2147483648..2147483647)
    MAX-ACCESS      read-create
    STATUS          current
    DESCRIPTION     
            "The amount of time to transmit the loopback activation code. \nThis attribute has no effect if Loopback Type is NONE. \nIf Facility Data Link is ENABLED for T1 ESF, the timer value is in milliseconds and valid values are 40 to 1000 ms. The default value is 100 ms. \nIf Facility Data Link is DISABLED, the timer value is in seconds and valid values are 5 to 10 sec. The default value is 6 sec."
    ::= { ptIOHWPortEntry 46 }

ptIOHWPortFarEndLoopbackDeactivationTime OBJECT-TYPE
    SYNTAX          Integer32 (-2147483648..2147483647)
    MAX-ACCESS      read-create
    STATUS          current
    DESCRIPTION     
            "The amount of time to transmit the loopback deactivation code. \nThis attribute has no effect if Loopback Type is NONE. \nIf Facility Data Link is ENABLED for T1 ESF, the timer value is in milliseconds and valid values are 40 to 1000 ms. The default value is 100 ms. \nIf Facility Data Link is DISABLED, the timer value is in seconds and valid values are 5 to 10 sec. The default value is 6 sec."
    ::= { ptIOHWPortEntry 47 }

ptIOHWPortBERTPattern OBJECT-TYPE
    SYNTAX          INTEGER { userData(0), prbs215(1) }
    MAX-ACCESS      read-create
    STATUS          current
    DESCRIPTION     
            "The type of test data to use for BERT. \nUser Data will inhibit the generation and detection of PRBS test data. \nPRBS_2_15 will generate 2^15-1 PRBS, non-inverted for T1 and J1, inverted for E1. \nThe default value is PRBS_2_15."
    ::= { ptIOHWPortEntry 48 }

ptIOHWPortPRBSDetectionTimer OBJECT-TYPE
    SYNTAX          Integer32 (-2147483648..2147483647)
    MAX-ACCESS      read-create
    STATUS          current
    DESCRIPTION     
            "The time limit to wait for PRBS detection in the receive stream. \nThis attribute has no effect if BERT Pattern is User Data. \nValid values are 0 and 1 to 30 seconds. \nIf the value is 0, the timer is disabled and BERT Duration time begins immediately. \nThe default value is 5 seconds."
    ::= { ptIOHWPortEntry 49 }

ptIOHWPortBERTDuration OBJECT-TYPE
    SYNTAX          Integer32 (-2147483648..2147483647)
    MAX-ACCESS      read-create
    STATUS          current
    DESCRIPTION     
            "The length of time to perform BERT. \nThe time period begins when PRBS detection is confirmed. \nValid values are 0 and 5-3600 seconds. \nIf the value is 0, the timer is disabled and BERT runs indefinitely. \nThe default value is 10 seconds."
    ::= { ptIOHWPortEntry 50 }

ptIOHWPortBERTStatus OBJECT-TYPE
    SYNTAX          DisplayString (SIZE(0..255))
    MAX-ACCESS      read-only
    STATUS          current
    DESCRIPTION     
            "Displays state information on BERT state machines. \n========================== \nBERT indicates the overall BERT state machine initiated by the Start BERT action. \n* IDLE - The BERT state machine is not active. \n* SEND_ACT - BERT has asked LOOP to send loopback activation code. \n* WAIT_SYNC - BERT is waiting for PRBS to synchronize. \n* ACTIVE - The main testing cycle is in progress. \n* SEND_DEACT - BERT has asked LOOP to send loopback deactivation code. \n* BLOCKED - LOOP or PRBS has been activated independently of BERT. The Start BERT action is prohibited until LOOP and PRBS are both IDLE. \n========================== \nLOOP indicates the far end loopback state machine, initiated by the Send Loop Up, Send Loop Down actions, or indirectly by the Start BERT action. \n* IDLE - The LOOP state machine is not active. \n* SEND_ACT - LOOP is sending loopback activation code. \n* ACTIVE - LOOP expects that the far end is in loopback mode due to the sent activation code. \n* SEND_DEACT - LOOP is sending loopback deactivation code. \n========================== \nPRBS indicates the PRBS state machine, initiated by the Start PRBS action, or indirectly by the Start BERT action. \n* IDLE - The PRBS state machine is not active. \n* INIT - PRBS has been started and is in a 1 second debounce period to allow the hardware to synchronize. Errors are ignored during this time. \n* WAIT_SYNC - PRBS is waiting for synchronization. \n* ACTIVE_SYNC - PRBS is active in test mode, currently synchronized. \n* ACTIVE_LOST - PRBS is active in test mode, currently not synchronization. \n========================== \nNote that when any one of the state machine is not in IDLE state, port configuration attributes Framing, Encoding, and Facility Data Link are locked."
    ::= { ptIOHWPortEntry 51 }

ptIOHWPortBERTResult OBJECT-TYPE
    SYNTAX          DisplayString (SIZE(0..255))
    MAX-ACCESS      read-only
    STATUS          current
    DESCRIPTION     
            "Displays execution results on the last BERT action."
    ::= { ptIOHWPortEntry 52 }

ptIOHWPortPRBSSyncSeconds OBJECT-TYPE
    SYNTAX          Integer32 (-2147483648..2147483647)
    MAX-ACCESS      read-only
    STATUS          current
    DESCRIPTION     
            "Displays number of seconds where PRBS is synchronized during BERT. This indicates the amount of time the PRBS state machine is in the ACTIVE_SYNC state."
    ::= { ptIOHWPortEntry 53 }

ptIOHWPortPRBSLostSeconds OBJECT-TYPE
    SYNTAX          Integer32 (-2147483648..2147483647)
    MAX-ACCESS      read-only
    STATUS          current
    DESCRIPTION     
            "Displays number of seconds where PRBS is unsynchronized during BERT. This indicates the amount of time the PRBS state machine is in the ACTIVE_LOST state."
    ::= { ptIOHWPortEntry 54 }

ptIOHWPortPRBSBitErrors OBJECT-TYPE
    SYNTAX          Integer32 (-2147483648..2147483647)
    MAX-ACCESS      read-only
    STATUS          current
    DESCRIPTION     
            "Displays number of bit errors detection while running PRBS. Note that the number of error may be larger than actual, especially in cases of timing slips."
    ::= { ptIOHWPortEntry 55 }

ptIOHWPortPRBSErrorInstances OBJECT-TYPE
    SYNTAX          Integer32 (-2147483648..2147483647)
    MAX-ACCESS      read-only
    STATUS          current
    DESCRIPTION     
            "Displays number of instances where errors were detected while running PRBS. A regular increment of this value may indicate a TDM timing issue."
    ::= { ptIOHWPortEntry 56 }

ptIOHWPortIOManagerIndex OBJECT-TYPE
    SYNTAX          Integer32 (-2147483648..2147483647)
    MAX-ACCESS      not-accessible
    STATUS          current
    DESCRIPTION     
            "This is the index of the parent type for this object.
             This parent type is IOManager."
    ::= { ptIOHWPortEntry 242 }

ptIOHWPortActions OBJECT-TYPE
    SYNTAX          INTEGER { startBERT(1), stopBERT(2), sendLoopUp(3), 
                        sendLoopDown(4), startPRBS(5), stopPRBS(6) }
    MAX-ACCESS      read-create
    STATUS          current
    DESCRIPTION     
            "The OID of all possible actions for this instance"
    ::= { ptIOHWPortEntry 252 }

ptIOHWPortParentOID OBJECT-TYPE
    SYNTAX          OBJECT IDENTIFIER
    MAX-ACCESS      read-create
    STATUS          current
    DESCRIPTION     
            "The OID of the parent object for this instance"
    ::= { ptIOHWPortEntry 253 }

ptIOHWPortRowStatus OBJECT-TYPE
    SYNTAX          RowStatus
    MAX-ACCESS      read-create
    STATUS          current
    DESCRIPTION     
            "The row status for the IOHWPort table"
    ::= { ptIOHWPortEntry 254 }

ptIOHWPortIndex OBJECT-TYPE
    SYNTAX          Integer32 (-2147483648..2147483647)
    MAX-ACCESS      not-accessible
    STATUS          current
    DESCRIPTION     
            "The row number for the IOHWPort table"
    ::= { ptIOHWPortEntry 255 }

ptIOHWVoicePassThrough OBJECT IDENTIFIER
    ::= { ptIOHWIOManager 1090 }

ptIOHWVoicePassThroughTable OBJECT-TYPE
    SYNTAX          SEQUENCE OF PtIOHWVoicePassThroughEntry
    MAX-ACCESS      not-accessible
    STATUS          current
    DESCRIPTION     
            "No description supplied in the proxy config file."
    ::= { ptIOHWVoicePassThrough 1 }

ptIOHWVoicePassThroughEntry OBJECT-TYPE
    SYNTAX          PtIOHWVoicePassThroughEntry
    MAX-ACCESS      not-accessible
    STATUS          current
    DESCRIPTION     
            "A sequence of IOHWVoicePassThrough attributes."
    INDEX           { ptConnGroupIndex, 
                      ptIOHWVoicePassThroughIOManagerIndex, 
                      ptIOHWVoicePassThroughIndex }
    ::= { ptIOHWVoicePassThroughTable 1 }

PtIOHWVoicePassThroughEntry ::=
    SEQUENCE {
        ptIOHWVoicePassThroughIOManagerIndex    Integer32,
        ptIOHWVoicePassThroughActions   INTEGER,
        ptIOHWVoicePassThroughParentOID OBJECT IDENTIFIER,
        ptIOHWVoicePassThroughRowStatus RowStatus,
        ptIOHWVoicePassThroughIndex     Integer32
    }

ptIOHWVoicePassThroughIOManagerIndex OBJECT-TYPE
    SYNTAX          Integer32 (-2147483648..2147483647)
    MAX-ACCESS      not-accessible
    STATUS          current
    DESCRIPTION     
            "This is the index of the parent type for this object.
             This parent type is IOManager."
    ::= { ptIOHWVoicePassThroughEntry 242 }

ptIOHWVoicePassThroughActions OBJECT-TYPE
    SYNTAX          INTEGER { clearMappings(1) }
    MAX-ACCESS      read-create
    STATUS          current
    DESCRIPTION     
            "The OID of all possible actions for this instance"
    ::= { ptIOHWVoicePassThroughEntry 252 }

ptIOHWVoicePassThroughParentOID OBJECT-TYPE
    SYNTAX          OBJECT IDENTIFIER
    MAX-ACCESS      read-create
    STATUS          current
    DESCRIPTION     
            "The OID of the parent object for this instance"
    ::= { ptIOHWVoicePassThroughEntry 253 }

ptIOHWVoicePassThroughRowStatus OBJECT-TYPE
    SYNTAX          RowStatus
    MAX-ACCESS      read-create
    STATUS          current
    DESCRIPTION     
            "The row status for the IOHWVoicePassThrough table"
    ::= { ptIOHWVoicePassThroughEntry 254 }

ptIOHWVoicePassThroughIndex OBJECT-TYPE
    SYNTAX          Integer32 (-2147483648..2147483647)
    MAX-ACCESS      not-accessible
    STATUS          current
    DESCRIPTION     
            "The row number for the IOHWVoicePassThrough table"
    ::= { ptIOHWVoicePassThroughEntry 255 }

ptIOHWLocalPassThrough OBJECT IDENTIFIER
    ::= { ptIOHWVoicePassThrough 1105 }

ptIOHWLocalPassThroughTable OBJECT-TYPE
    SYNTAX          SEQUENCE OF PtIOHWLocalPassThroughEntry
    MAX-ACCESS      not-accessible
    STATUS          current
    DESCRIPTION     
            "No description supplied in the proxy config file."
    ::= { ptIOHWLocalPassThrough 1 }

ptIOHWLocalPassThroughEntry OBJECT-TYPE
    SYNTAX          PtIOHWLocalPassThroughEntry
    MAX-ACCESS      not-accessible
    STATUS          current
    DESCRIPTION     
            "A sequence of IOHWLocalPassThrough attributes."
    INDEX           { ptConnGroupIndex, 
                      ptIOHWLocalPassThroughIOManagerIndex, 
                      ptIOHWLocalPassThroughVoicePassThroughIndex, 
                      ptIOHWLocalPassThroughIndex }
    ::= { ptIOHWLocalPassThroughTable 1 }

PtIOHWLocalPassThroughEntry ::=
    SEQUENCE {
        ptIOHWLocalPassThroughPortA     INTEGER,
        ptIOHWLocalPassThroughTimeSlotA INTEGER,
        ptIOHWLocalPassThroughPortB     INTEGER,
        ptIOHWLocalPassThroughTimeSlotB INTEGER,
        ptIOHWLocalPassThroughInstanceID Integer32,
        ptIOHWLocalPassThroughIOManagerIndex    Integer32,
        ptIOHWLocalPassThroughVoicePassThroughIndex           Integer32,
        ptIOHWLocalPassThroughParentOID OBJECT IDENTIFIER,
        ptIOHWLocalPassThroughRowStatus RowStatus,
        ptIOHWLocalPassThroughIndex     Integer32
    }

ptIOHWLocalPassThroughPortA OBJECT-TYPE
    SYNTAX          INTEGER { port0(0), port1(1), port2(2), port3(3), 
                        port4(4), port5(5), port6(6), port7(7), 
                        monitorPort(8), notConfigured(9), port8(10) }
    MAX-ACCESS      read-create
    STATUS          current
    DESCRIPTION     
            "Port A receive/transmit"
    ::= { ptIOHWLocalPassThroughEntry 1 }

ptIOHWLocalPassThroughTimeSlotA OBJECT-TYPE
    SYNTAX          INTEGER { notConfigured(0) }
    MAX-ACCESS      read-create
    STATUS          current
    DESCRIPTION     
            "Time slot on port A"
    ::= { ptIOHWLocalPassThroughEntry 2 }

ptIOHWLocalPassThroughPortB OBJECT-TYPE
    SYNTAX          INTEGER { port0(0), port1(1), port2(2), port3(3), 
                        port4(4), port5(5), port6(6), port7(7), 
                        monitorPort(8), notConfigured(9), port8(10) }
    MAX-ACCESS      read-create
    STATUS          current
    DESCRIPTION     
            "Port B receive/transmit"
    ::= { ptIOHWLocalPassThroughEntry 3 }

ptIOHWLocalPassThroughTimeSlotB OBJECT-TYPE
    SYNTAX          INTEGER { notConfigured(0) }
    MAX-ACCESS      read-create
    STATUS          current
    DESCRIPTION     
            "Time slot on port B"
    ::= { ptIOHWLocalPassThroughEntry 4 }

ptIOHWLocalPassThroughInstanceID OBJECT-TYPE
    SYNTAX          Integer32 (-2147483648..2147483647)
    MAX-ACCESS      read-only
    STATUS          current
    DESCRIPTION     
            "Object instance number"
    ::= { ptIOHWLocalPassThroughEntry 5 }

ptIOHWLocalPassThroughIOManagerIndex OBJECT-TYPE
    SYNTAX          Integer32 (-2147483648..2147483647)
    MAX-ACCESS      not-accessible
    STATUS          current
    DESCRIPTION     
            "This is the index of the parent type for this object.
             This parent type is IOManager."
    ::= { ptIOHWLocalPassThroughEntry 242 }

ptIOHWLocalPassThroughVoicePassThroughIndex OBJECT-TYPE
    SYNTAX          Integer32 (-2147483648..2147483647)
    MAX-ACCESS      not-accessible
    STATUS          current
    DESCRIPTION     
            "This is the index of the parent type for this object.
             This parent type is VoicePassThrough."
    ::= { ptIOHWLocalPassThroughEntry 243 }

ptIOHWLocalPassThroughParentOID OBJECT-TYPE
    SYNTAX          OBJECT IDENTIFIER
    MAX-ACCESS      read-create
    STATUS          current
    DESCRIPTION     
            "The OID of the parent object for this instance"
    ::= { ptIOHWLocalPassThroughEntry 253 }

ptIOHWLocalPassThroughRowStatus OBJECT-TYPE
    SYNTAX          RowStatus
    MAX-ACCESS      read-create
    STATUS          current
    DESCRIPTION     
            "The row status for the IOHWLocalPassThrough table"
    ::= { ptIOHWLocalPassThroughEntry 254 }

ptIOHWLocalPassThroughIndex OBJECT-TYPE
    SYNTAX          Integer32 (-2147483648..2147483647)
    MAX-ACCESS      not-accessible
    STATUS          current
    DESCRIPTION     
            "The row number for the IOHWLocalPassThrough table"
    ::= { ptIOHWLocalPassThroughEntry 255 }

ptIOHWH110PassThrough OBJECT IDENTIFIER
    ::= { ptIOHWVoicePassThrough 1106 }

ptIOHWH110PassThroughTable OBJECT-TYPE
    SYNTAX          SEQUENCE OF PtIOHWH110PassThroughEntry
    MAX-ACCESS      not-accessible
    STATUS          current
    DESCRIPTION     
            "No description supplied in the proxy config file."
    ::= { ptIOHWH110PassThrough 1 }

ptIOHWH110PassThroughEntry OBJECT-TYPE
    SYNTAX          PtIOHWH110PassThroughEntry
    MAX-ACCESS      not-accessible
    STATUS          current
    DESCRIPTION     
            "A sequence of IOHWH110PassThrough attributes."
    INDEX           { ptConnGroupIndex, 
                      ptIOHWH110PassThroughIOManagerIndex, 
                      ptIOHWH110PassThroughVoicePassThroughIndex, 
                      ptIOHWH110PassThroughIndex }
    ::= { ptIOHWH110PassThroughTable 1 }

PtIOHWH110PassThroughEntry ::=
    SEQUENCE {
        ptIOHWH110PassThroughPortA      INTEGER,
        ptIOHWH110PassThroughTimeSlotA  INTEGER,
        ptIOHWH110PassThroughCTBusTimeSlotRx    INTEGER,
        ptIOHWH110PassThroughCTBusTimeSlotTx    INTEGER,
        ptIOHWH110PassThroughInstanceID Integer32,
        ptIOHWH110PassThroughIOManagerIndex   Integer32,
        ptIOHWH110PassThroughVoicePassThroughIndex          Integer32,
        ptIOHWH110PassThroughParentOID  OBJECT IDENTIFIER,
        ptIOHWH110PassThroughRowStatus  RowStatus,
        ptIOHWH110PassThroughIndex      Integer32
    }

ptIOHWH110PassThroughPortA OBJECT-TYPE
    SYNTAX          INTEGER { port0(0), port1(1), port2(2), port3(3), 
                        port4(4), port5(5), port6(6), port7(7), 
                        monitorPort(8), notConfigured(9), port8(10) }
    MAX-ACCESS      read-create
    STATUS          current
    DESCRIPTION     
            "Port A receive/transmit"
    ::= { ptIOHWH110PassThroughEntry 1 }

ptIOHWH110PassThroughTimeSlotA OBJECT-TYPE
    SYNTAX          INTEGER { notConfigured(0) }
    MAX-ACCESS      read-create
    STATUS          current
    DESCRIPTION     
            "Time slot on port A"
    ::= { ptIOHWH110PassThroughEntry 2 }

ptIOHWH110PassThroughCTBusTimeSlotRx OBJECT-TYPE
    SYNTAX          INTEGER { notConfigured(0) }
    MAX-ACCESS      read-create
    STATUS          current
    DESCRIPTION     
            "Receive timeslot on the CTBus (1-4096)"
    ::= { ptIOHWH110PassThroughEntry 7 }

ptIOHWH110PassThroughCTBusTimeSlotTx OBJECT-TYPE
    SYNTAX          INTEGER { notConfigured(0) }
    MAX-ACCESS      read-create
    STATUS          current
    DESCRIPTION     
            "Transmit timeslot on the CTBus (1-4096)"
    ::= { ptIOHWH110PassThroughEntry 8 }

ptIOHWH110PassThroughInstanceID OBJECT-TYPE
    SYNTAX          Integer32 (-2147483648..2147483647)
    MAX-ACCESS      read-only
    STATUS          current
    DESCRIPTION     
            "Object instance number"
    ::= { ptIOHWH110PassThroughEntry 10 }

ptIOHWH110PassThroughIOManagerIndex OBJECT-TYPE
    SYNTAX          Integer32 (-2147483648..2147483647)
    MAX-ACCESS      not-accessible
    STATUS          current
    DESCRIPTION     
            "This is the index of the parent type for this object.
             This parent type is IOManager."
    ::= { ptIOHWH110PassThroughEntry 242 }

ptIOHWH110PassThroughVoicePassThroughIndex OBJECT-TYPE
    SYNTAX          Integer32 (-2147483648..2147483647)
    MAX-ACCESS      not-accessible
    STATUS          current
    DESCRIPTION     
            "This is the index of the parent type for this object.
             This parent type is VoicePassThrough."
    ::= { ptIOHWH110PassThroughEntry 243 }

ptIOHWH110PassThroughParentOID OBJECT-TYPE
    SYNTAX          OBJECT IDENTIFIER
    MAX-ACCESS      read-create
    STATUS          current
    DESCRIPTION     
            "The OID of the parent object for this instance"
    ::= { ptIOHWH110PassThroughEntry 253 }

ptIOHWH110PassThroughRowStatus OBJECT-TYPE
    SYNTAX          RowStatus
    MAX-ACCESS      read-create
    STATUS          current
    DESCRIPTION     
            "The row status for the IOHWH110PassThrough table"
    ::= { ptIOHWH110PassThroughEntry 254 }

ptIOHWH110PassThroughIndex OBJECT-TYPE
    SYNTAX          Integer32 (-2147483648..2147483647)
    MAX-ACCESS      not-accessible
    STATUS          current
    DESCRIPTION     
            "The row number for the IOHWH110PassThrough table"
    ::= { ptIOHWH110PassThroughEntry 255 }

ptIOHWSCTPServer OBJECT IDENTIFIER
    ::= { ptIOHWIOManager 1092 }

ptIOHWSCTPServerTable OBJECT-TYPE
    SYNTAX          SEQUENCE OF PtIOHWSCTPServerEntry
    MAX-ACCESS      not-accessible
    STATUS          current
    DESCRIPTION     
            "No description supplied in the proxy config file."
    ::= { ptIOHWSCTPServer 1 }

ptIOHWSCTPServerEntry OBJECT-TYPE
    SYNTAX          PtIOHWSCTPServerEntry
    MAX-ACCESS      not-accessible
    STATUS          current
    DESCRIPTION     
            "A sequence of IOHWSCTPServer attributes."
    INDEX           { ptConnGroupIndex, ptIOHWSCTPServerIOManagerIndex, 
                      ptIOHWSCTPServerIndex }
    ::= { ptIOHWSCTPServerTable 1 }

PtIOHWSCTPServerEntry ::=
    SEQUENCE {
        ptIOHWSCTPServerListeningPort   Integer32,
        ptIOHWSCTPServerPrimaryIP       DisplayString,
        ptIOHWSCTPServerSecondaryIP     DisplayString,
        ptIOHWSCTPServerNumberOfAssoc   Integer32,
        ptIOHWSCTPServerDebugLevel      Integer32,
        ptIOHWSCTPServerHeartBeat       INTEGER,
        ptIOHWSCTPServerHeartBeatInterval Integer32,
        ptIOHWSCTPServerRTOInitial      Integer32,
        ptIOHWSCTPServerRTOMinimum      Integer32,
        ptIOHWSCTPServerRTOMaximum      Integer32,
        ptIOHWSCTPServerMaximumPathRetrans  Integer32,
        ptIOHWSCTPServerMaximumAssocRetrans   Integer32,
        ptIOHWSCTPServerBundling        INTEGER,
        ptIOHWSCTPServerBundlingTO      Integer32,
        ptIOHWSCTPServerDelayedAckTO    Integer32,
        ptIOHWSCTPServerFastRetransThreshold    Integer32,
        ptIOHWSCTPServerChecksum        INTEGER,
        ptIOHWSCTPServerProtocol        INTEGER,
        ptIOHWSCTPServerIOManagerIndex  Integer32,
        ptIOHWSCTPServerParentOID       OBJECT IDENTIFIER,
        ptIOHWSCTPServerRowStatus       RowStatus,
        ptIOHWSCTPServerIndex           Integer32
    }

ptIOHWSCTPServerListeningPort OBJECT-TYPE
    SYNTAX          Integer32 (1024..2147483647)
    MAX-ACCESS      read-only
    STATUS          current
    DESCRIPTION     
            "Port on which SCTP Server listens"
    ::= { ptIOHWSCTPServerEntry 1 }

ptIOHWSCTPServerPrimaryIP OBJECT-TYPE
    SYNTAX          DisplayString (SIZE(0..255))
    MAX-ACCESS      read-create
    STATUS          current
    DESCRIPTION     
            "Primary IP path to listen on"
    ::= { ptIOHWSCTPServerEntry 2 }

ptIOHWSCTPServerSecondaryIP OBJECT-TYPE
    SYNTAX          DisplayString (SIZE(0..255))
    MAX-ACCESS      read-create
    STATUS          current
    DESCRIPTION     
            "Secondary IP path to listen on"
    ::= { ptIOHWSCTPServerEntry 3 }

ptIOHWSCTPServerNumberOfAssoc OBJECT-TYPE
    SYNTAX          Integer32 (0..2147483647)
    MAX-ACCESS      read-only
    STATUS          current
    DESCRIPTION     
            "Number of associations to this server"
    ::= { ptIOHWSCTPServerEntry 4 }

ptIOHWSCTPServerDebugLevel OBJECT-TYPE
    SYNTAX          Integer32 (0..5)
    MAX-ACCESS      read-create
    STATUS          current
    DESCRIPTION     
            "Default Debug level (0-5) of SCTP associations and SCTP Server (0=none, 1=min, 5=max)"
    ::= { ptIOHWSCTPServerEntry 5 }

ptIOHWSCTPServerHeartBeat OBJECT-TYPE
    SYNTAX          INTEGER { disabled(0), enabled(1) }
    MAX-ACCESS      read-create
    STATUS          current
    DESCRIPTION     
            "Heartbeat: periodic sending of test message"
    ::= { ptIOHWSCTPServerEntry 6 }

ptIOHWSCTPServerHeartBeatInterval OBJECT-TYPE
    SYNTAX          Integer32 (0..2147483647)
    MAX-ACCESS      read-create
    STATUS          current
    DESCRIPTION     
            "Time between heartbeat messages (ms)"
    ::= { ptIOHWSCTPServerEntry 7 }

ptIOHWSCTPServerRTOInitial OBJECT-TYPE
    SYNTAX          Integer32 (0..2147483647)
    MAX-ACCESS      read-create
    STATUS          current
    DESCRIPTION     
            "Initial Retransmission Timeout interval when connecting to a remote node"
    ::= { ptIOHWSCTPServerEntry 8 }

ptIOHWSCTPServerRTOMinimum OBJECT-TYPE
    SYNTAX          Integer32 (0..2147483647)
    MAX-ACCESS      read-create
    STATUS          current
    DESCRIPTION     
            "Minimum Retransmission Timeout interval when communicating to a remote node"
    ::= { ptIOHWSCTPServerEntry 9 }

ptIOHWSCTPServerRTOMaximum OBJECT-TYPE
    SYNTAX          Integer32 (0..2147483647)
    MAX-ACCESS      read-create
    STATUS          current
    DESCRIPTION     
            "Maximum Retransmission Timeout interval when communicating to a remote node"
    ::= { ptIOHWSCTPServerEntry 10 }

ptIOHWSCTPServerMaximumPathRetrans OBJECT-TYPE
    SYNTAX          Integer32 (0..2147483647)
    MAX-ACCESS      read-create
    STATUS          current
    DESCRIPTION     
            "Number of failed retransmission attempts over current transmission path before deeming the path as unavailable and selecting a different transmission path"
    ::= { ptIOHWSCTPServerEntry 11 }

ptIOHWSCTPServerMaximumAssocRetrans OBJECT-TYPE
    SYNTAX          Integer32 (0..2147483647)
    MAX-ACCESS      read-create
    STATUS          current
    DESCRIPTION     
            "Number of failed retransmission attempts over all transmission paths before deeming the remote node as unavailable"
    ::= { ptIOHWSCTPServerEntry 12 }

ptIOHWSCTPServerBundling OBJECT-TYPE
    SYNTAX          INTEGER { disabled(0), enabled(1) }
    MAX-ACCESS      read-create
    STATUS          current
    DESCRIPTION     
            "Bundling of messages into larger packets when possible"
    ::= { ptIOHWSCTPServerEntry 13 }

ptIOHWSCTPServerBundlingTO OBJECT-TYPE
    SYNTAX          Integer32 (0..2147483647)
    MAX-ACCESS      read-create
    STATUS          current
    DESCRIPTION     
            "Length of time messages are queued before bundled into larger packets and transmitted, if bundling is enabled (ms)"
    ::= { ptIOHWSCTPServerEntry 14 }

ptIOHWSCTPServerDelayedAckTO OBJECT-TYPE
    SYNTAX          Integer32 (0..2147483647)
    MAX-ACCESS      read-create
    STATUS          current
    DESCRIPTION     
            "Length of time to delay acknowledgements to received data"
    ::= { ptIOHWSCTPServerEntry 15 }

ptIOHWSCTPServerFastRetransThreshold OBJECT-TYPE
    SYNTAX          Integer32 (0..2147483647)
    MAX-ACCESS      read-create
    STATUS          current
    DESCRIPTION     
            "Number of times a packet can be reported as missing before resending packets using the Fast-Retransmit algorithm"
    ::= { ptIOHWSCTPServerEntry 16 }

ptIOHWSCTPServerChecksum OBJECT-TYPE
    SYNTAX          INTEGER { crc32(0), adler32(1), none(2), probe(3) }
    MAX-ACCESS      read-create
    STATUS          current
    DESCRIPTION     
            "Checksum algorithm to be used (CRC32, ADLER32, NONE)"
    ::= { ptIOHWSCTPServerEntry 17 }

ptIOHWSCTPServerProtocol OBJECT-TYPE
    SYNTAX          INTEGER { tdm(0), atm(1), all(2) }
    MAX-ACCESS      read-only
    STATUS          current
    DESCRIPTION     
            "Which protocols the connections to this server support"
    ::= { ptIOHWSCTPServerEntry 80 }

ptIOHWSCTPServerIOManagerIndex OBJECT-TYPE
    SYNTAX          Integer32 (-2147483648..2147483647)
    MAX-ACCESS      not-accessible
    STATUS          current
    DESCRIPTION     
            "This is the index of the parent type for this object.
             This parent type is IOManager."
    ::= { ptIOHWSCTPServerEntry 242 }

ptIOHWSCTPServerParentOID OBJECT-TYPE
    SYNTAX          OBJECT IDENTIFIER
    MAX-ACCESS      read-create
    STATUS          current
    DESCRIPTION     
            "The OID of the parent object for this instance"
    ::= { ptIOHWSCTPServerEntry 253 }

ptIOHWSCTPServerRowStatus OBJECT-TYPE
    SYNTAX          RowStatus
    MAX-ACCESS      read-create
    STATUS          current
    DESCRIPTION     
            "The row status for the IOHWSCTPServer table"
    ::= { ptIOHWSCTPServerEntry 254 }

ptIOHWSCTPServerIndex OBJECT-TYPE
    SYNTAX          Integer32 (-2147483648..2147483647)
    MAX-ACCESS      not-accessible
    STATUS          current
    DESCRIPTION     
            "The row number for the IOHWSCTPServer table"
    ::= { ptIOHWSCTPServerEntry 255 }

ptIOHWSCTPAssociation OBJECT IDENTIFIER
    ::= { ptIOHWSCTPServer 1108 }

ptIOHWSCTPAssociationTable OBJECT-TYPE
    SYNTAX          SEQUENCE OF PtIOHWSCTPAssociationEntry
    MAX-ACCESS      not-accessible
    STATUS          current
    DESCRIPTION     
            "No description supplied in the proxy config file."
    ::= { ptIOHWSCTPAssociation 1 }

ptIOHWSCTPAssociationEntry OBJECT-TYPE
    SYNTAX          PtIOHWSCTPAssociationEntry
    MAX-ACCESS      not-accessible
    STATUS          current
    DESCRIPTION     
            "A sequence of IOHWSCTPAssociation attributes."
    INDEX           { ptConnGroupIndex, 
                      ptIOHWSCTPAssociationIOManagerIndex, 
                      ptIOHWSCTPAssociationSCTPServerIndex, 
                      ptIOHWSCTPAssociationIndex }
    ::= { ptIOHWSCTPAssociationTable 1 }

PtIOHWSCTPAssociationEntry ::=
    SEQUENCE {
        ptIOHWSCTPAssociationAssociationNumber      Integer32,
        ptIOHWSCTPAssociationRemoteIP1  DisplayString,
        ptIOHWSCTPAssociationRemoteIP2  DisplayString,
        ptIOHWSCTPAssociationAssociationStatus      INTEGER,
        ptIOHWSCTPAssociationDebugLevel Integer32,
        ptIOHWSCTPAssociationRemotePort Integer32,
        ptIOHWSCTPAssociationASPID      Integer32,
        ptIOHWSCTPAssociationIOManagerIndex   Integer32,
        ptIOHWSCTPAssociationSCTPServerIndex    Integer32,
        ptIOHWSCTPAssociationParentOID  OBJECT IDENTIFIER,
        ptIOHWSCTPAssociationRowStatus  RowStatus,
        ptIOHWSCTPAssociationIndex      Integer32
    }

ptIOHWSCTPAssociationAssociationNumber OBJECT-TYPE
    SYNTAX          Integer32 (0..2147483647)
    MAX-ACCESS      read-only
    STATUS          current
    DESCRIPTION     
            "Number assigned to this SCTP Association"
    ::= { ptIOHWSCTPAssociationEntry 1 }

ptIOHWSCTPAssociationRemoteIP1 OBJECT-TYPE
    SYNTAX          DisplayString (SIZE(0..255))
    MAX-ACCESS      read-only
    STATUS          current
    DESCRIPTION     
            "Remote IP No.1 of this association"
    ::= { ptIOHWSCTPAssociationEntry 2 }

ptIOHWSCTPAssociationRemoteIP2 OBJECT-TYPE
    SYNTAX          DisplayString (SIZE(0..255))
    MAX-ACCESS      read-only
    STATUS          current
    DESCRIPTION     
            "Remote IP No.2 of this association"
    ::= { ptIOHWSCTPAssociationEntry 3 }

ptIOHWSCTPAssociationAssociationStatus OBJECT-TYPE
    SYNTAX          INTEGER { closed(0), connecting(1), established(2), 
                        deactivated(3) }
    MAX-ACCESS      read-only
    STATUS          current
    DESCRIPTION     
            "Current status of this association"
    ::= { ptIOHWSCTPAssociationEntry 4 }

ptIOHWSCTPAssociationDebugLevel OBJECT-TYPE
    SYNTAX          Integer32 (0..5)
    MAX-ACCESS      read-create
    STATUS          current
    DESCRIPTION     
            "Debug level (0-5) of this SCTP association (0=none, 1=min, 5=max)"
    ::= { ptIOHWSCTPAssociationEntry 5 }

ptIOHWSCTPAssociationRemotePort OBJECT-TYPE
    SYNTAX          Integer32 (-2147483648..2147483647)
    MAX-ACCESS      read-only
    STATUS          current
    DESCRIPTION     
            "Remote port number used for this association"
    ::= { ptIOHWSCTPAssociationEntry 6 }

ptIOHWSCTPAssociationASPID OBJECT-TYPE
    SYNTAX          Integer32 (-2147483648..2147483647)
    MAX-ACCESS      read-only
    STATUS          current
    DESCRIPTION     
            "Object instance number"
    ::= { ptIOHWSCTPAssociationEntry 10 }

ptIOHWSCTPAssociationIOManagerIndex OBJECT-TYPE
    SYNTAX          Integer32 (-2147483648..2147483647)
    MAX-ACCESS      not-accessible
    STATUS          current
    DESCRIPTION     
            "This is the index of the parent type for this object.
             This parent type is IOManager."
    ::= { ptIOHWSCTPAssociationEntry 242 }

ptIOHWSCTPAssociationSCTPServerIndex OBJECT-TYPE
    SYNTAX          Integer32 (-2147483648..2147483647)
    MAX-ACCESS      not-accessible
    STATUS          current
    DESCRIPTION     
            "This is the index of the parent type for this object.
             This parent type is SCTPServer."
    ::= { ptIOHWSCTPAssociationEntry 243 }

ptIOHWSCTPAssociationParentOID OBJECT-TYPE
    SYNTAX          OBJECT IDENTIFIER
    MAX-ACCESS      read-create
    STATUS          current
    DESCRIPTION     
            "The OID of the parent object for this instance"
    ::= { ptIOHWSCTPAssociationEntry 253 }

ptIOHWSCTPAssociationRowStatus OBJECT-TYPE
    SYNTAX          RowStatus
    MAX-ACCESS      read-create
    STATUS          current
    DESCRIPTION     
            "The row status for the IOHWSCTPAssociation table"
    ::= { ptIOHWSCTPAssociationEntry 254 }

ptIOHWSCTPAssociationIndex OBJECT-TYPE
    SYNTAX          Integer32 (-2147483648..2147483647)
    MAX-ACCESS      not-accessible
    STATUS          current
    DESCRIPTION     
            "The row number for the IOHWSCTPAssociation table"
    ::= { ptIOHWSCTPAssociationEntry 255 }

ptIOHWTIPCServer OBJECT IDENTIFIER
    ::= { ptIOHWIOManager 1093 }

ptIOHWTIPCServerTable OBJECT-TYPE
    SYNTAX          SEQUENCE OF PtIOHWTIPCServerEntry
    MAX-ACCESS      not-accessible
    STATUS          current
    DESCRIPTION     
            "No description supplied in the proxy config file."
    ::= { ptIOHWTIPCServer 1 }

ptIOHWTIPCServerEntry OBJECT-TYPE
    SYNTAX          PtIOHWTIPCServerEntry
    MAX-ACCESS      not-accessible
    STATUS          current
    DESCRIPTION     
            "A sequence of IOHWTIPCServer attributes."
    INDEX           { ptConnGroupIndex, ptIOHWTIPCServerIOManagerIndex, 
                      ptIOHWTIPCServerIndex }
    ::= { ptIOHWTIPCServerTable 1 }

PtIOHWTIPCServerEntry ::=
    SEQUENCE {
        ptIOHWTIPCServerServiceType     Integer32,
        ptIOHWTIPCServerServiceInstance Integer32,
        ptIOHWTIPCServerNumberOfASP     Integer32,
        ptIOHWTIPCServerProtocol        INTEGER,
        ptIOHWTIPCServerIOManagerIndex  Integer32,
        ptIOHWTIPCServerParentOID       OBJECT IDENTIFIER,
        ptIOHWTIPCServerRowStatus       RowStatus,
        ptIOHWTIPCServerIndex           Integer32
    }

ptIOHWTIPCServerServiceType OBJECT-TYPE
    SYNTAX          Integer32 (-2147483648..2147483647)
    MAX-ACCESS      read-only
    STATUS          current
    DESCRIPTION     
            "TIPC service type number"
    ::= { ptIOHWTIPCServerEntry 1 }

ptIOHWTIPCServerServiceInstance OBJECT-TYPE
    SYNTAX          Integer32 (-2147483648..2147483647)
    MAX-ACCESS      read-only
    STATUS          current
    DESCRIPTION     
            "TIPC service instance number"
    ::= { ptIOHWTIPCServerEntry 2 }

ptIOHWTIPCServerNumberOfASP OBJECT-TYPE
    SYNTAX          Integer32 (0..2147483647)
    MAX-ACCESS      read-only
    STATUS          current
    DESCRIPTION     
            "Number of associations spawned by this server"
    ::= { ptIOHWTIPCServerEntry 6 }

ptIOHWTIPCServerProtocol OBJECT-TYPE
    SYNTAX          INTEGER { tdm(0), atm(1), all(2) }
    MAX-ACCESS      read-only
    STATUS          current
    DESCRIPTION     
            "Which protocols the connections to this server will support"
    ::= { ptIOHWTIPCServerEntry 80 }

ptIOHWTIPCServerIOManagerIndex OBJECT-TYPE
    SYNTAX          Integer32 (-2147483648..2147483647)
    MAX-ACCESS      not-accessible
    STATUS          current
    DESCRIPTION     
            "This is the index of the parent type for this object.
             This parent type is IOManager."
    ::= { ptIOHWTIPCServerEntry 242 }

ptIOHWTIPCServerParentOID OBJECT-TYPE
    SYNTAX          OBJECT IDENTIFIER
    MAX-ACCESS      read-create
    STATUS          current
    DESCRIPTION     
            "The OID of the parent object for this instance"
    ::= { ptIOHWTIPCServerEntry 253 }

ptIOHWTIPCServerRowStatus OBJECT-TYPE
    SYNTAX          RowStatus
    MAX-ACCESS      read-create
    STATUS          current
    DESCRIPTION     
            "The row status for the IOHWTIPCServer table"
    ::= { ptIOHWTIPCServerEntry 254 }

ptIOHWTIPCServerIndex OBJECT-TYPE
    SYNTAX          Integer32 (-2147483648..2147483647)
    MAX-ACCESS      not-accessible
    STATUS          current
    DESCRIPTION     
            "The row number for the IOHWTIPCServer table"
    ::= { ptIOHWTIPCServerEntry 255 }

ptIOHWTIPCServerProcess OBJECT IDENTIFIER
    ::= { ptIOHWTIPCServer 1109 }

ptIOHWTIPCServerProcessTable OBJECT-TYPE
    SYNTAX          SEQUENCE OF PtIOHWTIPCServerProcessEntry
    MAX-ACCESS      not-accessible
    STATUS          current
    DESCRIPTION     
            "No description supplied in the proxy config file."
    ::= { ptIOHWTIPCServerProcess 1 }

ptIOHWTIPCServerProcessEntry OBJECT-TYPE
    SYNTAX          PtIOHWTIPCServerProcessEntry
    MAX-ACCESS      not-accessible
    STATUS          current
    DESCRIPTION     
            "A sequence of IOHWTIPCServerProcess attributes."
    INDEX           { ptConnGroupIndex, 
                      ptIOHWTIPCServerProcessIOManagerIndex, 
                      ptIOHWTIPCServerProcessTIPCServerIndex, 
                      ptIOHWTIPCServerProcessIndex }
    ::= { ptIOHWTIPCServerProcessTable 1 }

PtIOHWTIPCServerProcessEntry ::=
    SEQUENCE {
        ptIOHWTIPCServerProcessASPID    Integer32,
        ptIOHWTIPCServerProcessIOManagerIndex     Integer32,
        ptIOHWTIPCServerProcessTIPCServerIndex      Integer32,
        ptIOHWTIPCServerProcessParentOID OBJECT IDENTIFIER,
        ptIOHWTIPCServerProcessRowStatus RowStatus,
        ptIOHWTIPCServerProcessIndex    Integer32
    }

ptIOHWTIPCServerProcessASPID OBJECT-TYPE
    SYNTAX          Integer32 (-2147483648..2147483647)
    MAX-ACCESS      read-only
    STATUS          current
    DESCRIPTION     
            "Unique number for this connection"
    ::= { ptIOHWTIPCServerProcessEntry 1 }

ptIOHWTIPCServerProcessIOManagerIndex OBJECT-TYPE
    SYNTAX          Integer32 (-2147483648..2147483647)
    MAX-ACCESS      not-accessible
    STATUS          current
    DESCRIPTION     
            "This is the index of the parent type for this object.
             This parent type is IOManager."
    ::= { ptIOHWTIPCServerProcessEntry 242 }

ptIOHWTIPCServerProcessTIPCServerIndex OBJECT-TYPE
    SYNTAX          Integer32 (-2147483648..2147483647)
    MAX-ACCESS      not-accessible
    STATUS          current
    DESCRIPTION     
            "This is the index of the parent type for this object.
             This parent type is TIPCServer."
    ::= { ptIOHWTIPCServerProcessEntry 243 }

ptIOHWTIPCServerProcessParentOID OBJECT-TYPE
    SYNTAX          OBJECT IDENTIFIER
    MAX-ACCESS      read-create
    STATUS          current
    DESCRIPTION     
            "The OID of the parent object for this instance"
    ::= { ptIOHWTIPCServerProcessEntry 253 }

ptIOHWTIPCServerProcessRowStatus OBJECT-TYPE
    SYNTAX          RowStatus
    MAX-ACCESS      read-create
    STATUS          current
    DESCRIPTION     
            "The row status for the IOHWTIPCServerProcess table"
    ::= { ptIOHWTIPCServerProcessEntry 254 }

ptIOHWTIPCServerProcessIndex OBJECT-TYPE
    SYNTAX          Integer32 (-2147483648..2147483647)
    MAX-ACCESS      not-accessible
    STATUS          current
    DESCRIPTION     
            "The row number for the IOHWTIPCServerProcess table"
    ::= { ptIOHWTIPCServerProcessEntry 255 }

ptIOHWTCPServer OBJECT IDENTIFIER
    ::= { ptIOHWIOManager 1094 }

ptIOHWTCPServerTable OBJECT-TYPE
    SYNTAX          SEQUENCE OF PtIOHWTCPServerEntry
    MAX-ACCESS      not-accessible
    STATUS          current
    DESCRIPTION     
            "No description supplied in the proxy config file."
    ::= { ptIOHWTCPServer 1 }

ptIOHWTCPServerEntry OBJECT-TYPE
    SYNTAX          PtIOHWTCPServerEntry
    MAX-ACCESS      not-accessible
    STATUS          current
    DESCRIPTION     
            "A sequence of IOHWTCPServer attributes."
    INDEX           { ptConnGroupIndex, ptIOHWTCPServerIOManagerIndex, 
                      ptIOHWTCPServerIndex }
    ::= { ptIOHWTCPServerTable 1 }

PtIOHWTCPServerEntry ::=
    SEQUENCE {
        ptIOHWTCPServerListeningOnPort  Integer32,
        ptIOHWTCPServerNumberOfConnections  Integer32,
        ptIOHWTCPServerIOManagerIndex   Integer32,
        ptIOHWTCPServerParentOID        OBJECT IDENTIFIER,
        ptIOHWTCPServerRowStatus        RowStatus,
        ptIOHWTCPServerIndex            Integer32
    }

ptIOHWTCPServerListeningOnPort OBJECT-TYPE
    SYNTAX          Integer32 (1024..2147483647)
    MAX-ACCESS      read-only
    STATUS          current
    DESCRIPTION     
            "Port on which TCP Server listens"
    ::= { ptIOHWTCPServerEntry 1 }

ptIOHWTCPServerNumberOfConnections OBJECT-TYPE
    SYNTAX          Integer32 (0..2147483647)
    MAX-ACCESS      read-only
    STATUS          current
    DESCRIPTION     
            "Number of connections to this server"
    ::= { ptIOHWTCPServerEntry 2 }

ptIOHWTCPServerIOManagerIndex OBJECT-TYPE
    SYNTAX          Integer32 (-2147483648..2147483647)
    MAX-ACCESS      not-accessible
    STATUS          current
    DESCRIPTION     
            "This is the index of the parent type for this object.
             This parent type is IOManager."
    ::= { ptIOHWTCPServerEntry 242 }

ptIOHWTCPServerParentOID OBJECT-TYPE
    SYNTAX          OBJECT IDENTIFIER
    MAX-ACCESS      read-create
    STATUS          current
    DESCRIPTION     
            "The OID of the parent object for this instance"
    ::= { ptIOHWTCPServerEntry 253 }

ptIOHWTCPServerRowStatus OBJECT-TYPE
    SYNTAX          RowStatus
    MAX-ACCESS      read-create
    STATUS          current
    DESCRIPTION     
            "The row status for the IOHWTCPServer table"
    ::= { ptIOHWTCPServerEntry 254 }

ptIOHWTCPServerIndex OBJECT-TYPE
    SYNTAX          Integer32 (-2147483648..2147483647)
    MAX-ACCESS      not-accessible
    STATUS          current
    DESCRIPTION     
            "The row number for the IOHWTCPServer table"
    ::= { ptIOHWTCPServerEntry 255 }

ptIOHWTCPConnection OBJECT IDENTIFIER
    ::= { ptIOHWIOManager 1110 }

ptIOHWTCPConnectionTable OBJECT-TYPE
    SYNTAX          SEQUENCE OF PtIOHWTCPConnectionEntry
    MAX-ACCESS      not-accessible
    STATUS          current
    DESCRIPTION     
            "No description supplied in the proxy config file."
    ::= { ptIOHWTCPConnection 1 }

ptIOHWTCPConnectionEntry OBJECT-TYPE
    SYNTAX          PtIOHWTCPConnectionEntry
    MAX-ACCESS      not-accessible
    STATUS          current
    DESCRIPTION     
            "A sequence of IOHWTCPConnection attributes."
    INDEX           { ptConnGroupIndex, 
                      ptIOHWTCPConnectionIOManagerIndex, 
                      ptIOHWTCPConnectionIndex }
    ::= { ptIOHWTCPConnectionTable 1 }

PtIOHWTCPConnectionEntry ::=
    SEQUENCE {
        ptIOHWTCPConnectionASPID        Integer32,
        ptIOHWTCPConnectionRemoteIP     DisplayString,
        ptIOHWTCPConnectionIOManagerIndex Integer32,
        ptIOHWTCPConnectionParentOID    OBJECT IDENTIFIER,
        ptIOHWTCPConnectionRowStatus    RowStatus,
        ptIOHWTCPConnectionIndex        Integer32
    }

ptIOHWTCPConnectionASPID OBJECT-TYPE
    SYNTAX          Integer32 (-2147483648..2147483647)
    MAX-ACCESS      read-only
    STATUS          current
    DESCRIPTION     
            "Unique number for this connection"
    ::= { ptIOHWTCPConnectionEntry 1 }

ptIOHWTCPConnectionRemoteIP OBJECT-TYPE
    SYNTAX          DisplayString (SIZE(0..255))
    MAX-ACCESS      read-only
    STATUS          current
    DESCRIPTION     
            "Remote IP of this connection"
    ::= { ptIOHWTCPConnectionEntry 2 }

ptIOHWTCPConnectionIOManagerIndex OBJECT-TYPE
    SYNTAX          Integer32 (-2147483648..2147483647)
    MAX-ACCESS      not-accessible
    STATUS          current
    DESCRIPTION     
            "This is the index of the parent type for this object.
             This parent type is IOManager."
    ::= { ptIOHWTCPConnectionEntry 242 }

ptIOHWTCPConnectionParentOID OBJECT-TYPE
    SYNTAX          OBJECT IDENTIFIER
    MAX-ACCESS      read-create
    STATUS          current
    DESCRIPTION     
            "The OID of the parent object for this instance"
    ::= { ptIOHWTCPConnectionEntry 253 }

ptIOHWTCPConnectionRowStatus OBJECT-TYPE
    SYNTAX          RowStatus
    MAX-ACCESS      read-create
    STATUS          current
    DESCRIPTION     
            "The row status for the IOHWTCPConnection table"
    ::= { ptIOHWTCPConnectionEntry 254 }

ptIOHWTCPConnectionIndex OBJECT-TYPE
    SYNTAX          Integer32 (-2147483648..2147483647)
    MAX-ACCESS      not-accessible
    STATUS          current
    DESCRIPTION     
            "The row number for the IOHWTCPConnection table"
    ::= { ptIOHWTCPConnectionEntry 255 }

ptpeereventProcessEvents OBJECT IDENTIFIER
    ::= { ptConnGroup 1131 }

ptpeereventProcessEventsTable OBJECT-TYPE
    SYNTAX          SEQUENCE OF PtpeereventProcessEventsEntry
    MAX-ACCESS      not-accessible
    STATUS          current
    DESCRIPTION     
            "No description supplied in the proxy config file."
    ::= { ptpeereventProcessEvents 1 }

ptpeereventProcessEventsEntry OBJECT-TYPE
    SYNTAX          PtpeereventProcessEventsEntry
    MAX-ACCESS      not-accessible
    STATUS          current
    DESCRIPTION     
            "A sequence of peereventProcessEvents attributes."
    INDEX           { ptConnGroupIndex, ptpeereventProcessEventsIndex }
    ::= { ptpeereventProcessEventsTable 1 }

PtpeereventProcessEventsEntry ::=
    SEQUENCE {
        ptpeereventProcessEventsName    DisplayString,
        ptpeereventProcessEventsCount   Integer32,
        ptpeereventProcessEventsParentOID OBJECT IDENTIFIER,
        ptpeereventProcessEventsRowStatus RowStatus,
        ptpeereventProcessEventsIndex   Integer32
    }

ptpeereventProcessEventsName OBJECT-TYPE
    SYNTAX          DisplayString (SIZE(0..255))
    MAX-ACCESS      read-only
    STATUS          current
    DESCRIPTION     
            "Process Events unique application name."
    ::= { ptpeereventProcessEventsEntry 1 }

ptpeereventProcessEventsCount OBJECT-TYPE
    SYNTAX          Integer32 (-2147483648..2147483647)
    MAX-ACCESS      read-only
    STATUS          current
    DESCRIPTION     
            "Number of Process Event objects."
    ::= { ptpeereventProcessEventsEntry 2 }

ptpeereventProcessEventsParentOID OBJECT-TYPE
    SYNTAX          OBJECT IDENTIFIER
    MAX-ACCESS      read-create
    STATUS          current
    DESCRIPTION     
            "The OID of the parent object for this instance"
    ::= { ptpeereventProcessEventsEntry 253 }

ptpeereventProcessEventsRowStatus OBJECT-TYPE
    SYNTAX          RowStatus
    MAX-ACCESS      read-create
    STATUS          current
    DESCRIPTION     
            "The row status for the peereventProcessEvents table"
    ::= { ptpeereventProcessEventsEntry 254 }

ptpeereventProcessEventsIndex OBJECT-TYPE
    SYNTAX          Integer32 (-2147483648..2147483647)
    MAX-ACCESS      not-accessible
    STATUS          current
    DESCRIPTION     
            "The row number for the peereventProcessEvents table"
    ::= { ptpeereventProcessEventsEntry 255 }

ptpeereventProcessEvent OBJECT IDENTIFIER
    ::= { ptpeereventProcessEvents 1132 }

ptpeereventProcessEventTable OBJECT-TYPE
    SYNTAX          SEQUENCE OF PtpeereventProcessEventEntry
    MAX-ACCESS      not-accessible
    STATUS          current
    DESCRIPTION     
            "No description supplied in the proxy config file."
    ::= { ptpeereventProcessEvent 1 }

ptpeereventProcessEventEntry OBJECT-TYPE
    SYNTAX          PtpeereventProcessEventEntry
    MAX-ACCESS      not-accessible
    STATUS          current
    DESCRIPTION     
            "A sequence of peereventProcessEvent attributes."
    INDEX           { ptConnGroupIndex, 
                      ptpeereventProcessEventProcessEventsIndex, 
                      ptpeereventProcessEventIndex }
    ::= { ptpeereventProcessEventTable 1 }

PtpeereventProcessEventEntry ::=
    SEQUENCE {
        ptpeereventProcessEventSlot     Integer32,
        ptpeereventProcessEventInitialization     INTEGER,
        ptpeereventProcessEventTrafficStatus    INTEGER,
        ptpeereventProcessEventFileWrite INTEGER,
        ptpeereventProcessEventSlotManager  INTEGER,
        ptpeereventProcessEventStatsManager   INTEGER,
        ptpeereventProcessEventIMFManager INTEGER,
        ptpeereventProcessEventLowerLayer INTEGER,
        ptpeereventProcessEventName     DisplayString,
        ptpeereventProcessEventProcessEventsIndex         Integer32,
        ptpeereventProcessEventParentOID OBJECT IDENTIFIER,
        ptpeereventProcessEventRowStatus RowStatus,
        ptpeereventProcessEventIndex    Integer32
    }

ptpeereventProcessEventSlot OBJECT-TYPE
    SYNTAX          Integer32 (-2147483648..2147483647)
    MAX-ACCESS      read-only
    STATUS          current
    DESCRIPTION     
            "Process corresponding slot. \nIn certain deployments where an application has more than one process on a given slot, the name attribute must be used to properly identify the process. \nIn PCE, the slot represents the LDL peer ID for cross-mate STP support."
    ::= { ptpeereventProcessEventEntry 1 }

ptpeereventProcessEventInitialization OBJECT-TYPE
    SYNTAX          INTEGER { notApplicable(0), inProgress(1), 
                        completed(2) }
    MAX-ACCESS      read-only
    STATUS          current
    DESCRIPTION     
            "Process initialization status (NOT APPLICABLE/IN PROGRESS/COMPLETED)."
    ::= { ptpeereventProcessEventEntry 2 }

ptpeereventProcessEventTrafficStatus OBJECT-TYPE
    SYNTAX          INTEGER { down(0), notReady(1), ready(2) }
    MAX-ACCESS      read-only
    STATUS          current
    DESCRIPTION     
            "Process traffic status (DOWN/NOT READY/READY). \nAn event is generated when the traffic status is set to NOT READY. The event is cleared when the status leaves the NOT READY state."
    ::= { ptpeereventProcessEventEntry 3 }

ptpeereventProcessEventFileWrite OBJECT-TYPE
    SYNTAX          INTEGER { notApplicable(0), failure(1), success(2) }
    MAX-ACCESS      read-only
    STATUS          current
    DESCRIPTION     
            "Process file write status (FAILURE/SUCCESS). \nAn event is generated when the file write is set to FAILURE. The event is cleared on a reset to SUCCESS."
    ::= { ptpeereventProcessEventEntry 4 }

ptpeereventProcessEventSlotManager OBJECT-TYPE
    SYNTAX          INTEGER { notApplicable(0), notConnected(1), 
                        connected(2) }
    MAX-ACCESS      read-only
    STATUS          current
    DESCRIPTION     
            "Process slot manager connection (NOT APPLICABLE/NOT CONNECTED/CONNECTED). \nAn event is generated when the connection status is set to NOT CONNECTED. The event is cleared on a set to CONNECTED."
    ::= { ptpeereventProcessEventEntry 5 }

ptpeereventProcessEventStatsManager OBJECT-TYPE
    SYNTAX          INTEGER { notApplicable(0), notConnected(1), 
                        connected(2) }
    MAX-ACCESS      read-only
    STATUS          current
    DESCRIPTION     
            "Process stats manager connection (NOT APPLICABLE/NOT CONNECTED/CONNECTED). \nAn event is generated when the connection status is set to NOT CONNECTED. The event is cleared on a set to CONNECTED."
    ::= { ptpeereventProcessEventEntry 6 }

ptpeereventProcessEventIMFManager OBJECT-TYPE
    SYNTAX          INTEGER { notApplicable(0), notConnected(1), 
                        connected(2) }
    MAX-ACCESS      read-only
    STATUS          current
    DESCRIPTION     
            "Process IMF manager connection (NOT APPLICABLE/NOT CONNECTED/CONNECTED). \nAn event is generated when the connection status is set to NOT CONNECTED. The event is cleared on a set to CONNECTED."
    ::= { ptpeereventProcessEventEntry 7 }

ptpeereventProcessEventLowerLayer OBJECT-TYPE
    SYNTAX          INTEGER { notApplicable(0), notConnected(1), 
                        partiallyConnected(2), connected(3) }
    MAX-ACCESS      read-only
    STATUS          current
    DESCRIPTION     
            "Process lower layer connections (NOT APPLICABLE/NOT CONNECTED/PARTIALLY CONNECTED/CONNECTED). \nA major event is generated when the layer connection status is set to PARTIALLY CONNECTED and a critical event is generated when the layer connection status is set to NOT CONNECTED. The critical event is cleared, if defined, on a set to PARTIALLY CONNECTED and the major event is cleared on a set to CONNECTED."
    ::= { ptpeereventProcessEventEntry 8 }

ptpeereventProcessEventName OBJECT-TYPE
    SYNTAX          DisplayString (SIZE(0..255))
    MAX-ACCESS      read-only
    STATUS          current
    DESCRIPTION     
            "Process corresponding name."
    ::= { ptpeereventProcessEventEntry 9 }

ptpeereventProcessEventProcessEventsIndex OBJECT-TYPE
    SYNTAX          Integer32 (-2147483648..2147483647)
    MAX-ACCESS      not-accessible
    STATUS          current
    DESCRIPTION     
            "This is the index of the parent type for this object.
             This parent type is ProcessEvents."
    ::= { ptpeereventProcessEventEntry 242 }

ptpeereventProcessEventParentOID OBJECT-TYPE
    SYNTAX          OBJECT IDENTIFIER
    MAX-ACCESS      read-create
    STATUS          current
    DESCRIPTION     
            "The OID of the parent object for this instance"
    ::= { ptpeereventProcessEventEntry 253 }

ptpeereventProcessEventRowStatus OBJECT-TYPE
    SYNTAX          RowStatus
    MAX-ACCESS      read-create
    STATUS          current
    DESCRIPTION     
            "The row status for the peereventProcessEvent table"
    ::= { ptpeereventProcessEventEntry 254 }

ptpeereventProcessEventIndex OBJECT-TYPE
    SYNTAX          Integer32 (-2147483648..2147483647)
    MAX-ACCESS      not-accessible
    STATUS          current
    DESCRIPTION     
            "The row number for the peereventProcessEvent table"
    ::= { ptpeereventProcessEventEntry 255 }

ptimfIMFConfiguration OBJECT IDENTIFIER
    ::= { ptConnGroup 1151 }

ptimfIMFConfigurationTable OBJECT-TYPE
    SYNTAX          SEQUENCE OF PtimfIMFConfigurationEntry
    MAX-ACCESS      not-accessible
    STATUS          current
    DESCRIPTION     
            "No description supplied in the proxy config file."
    ::= { ptimfIMFConfiguration 1 }

ptimfIMFConfigurationEntry OBJECT-TYPE
    SYNTAX          PtimfIMFConfigurationEntry
    MAX-ACCESS      not-accessible
    STATUS          current
    DESCRIPTION     
            "A sequence of imfIMFConfiguration attributes."
    INDEX           { ptConnGroupIndex, ptimfIMFConfigurationIndex }
    ::= { ptimfIMFConfigurationTable 1 }

PtimfIMFConfigurationEntry ::=
    SEQUENCE {
        ptimfIMFConfigurationVersion    Integer32,
        ptimfIMFConfigurationLicenseStatus  INTEGER,
        ptimfIMFConfigurationErrors     INTEGER,
        ptimfIMFConfigurationSetupManagement    INTEGER,
        ptimfIMFConfigurationExecutionTrace   INTEGER,
        ptimfIMFConfigurationPeerManagement   INTEGER,
        ptimfIMFConfigurationActions    INTEGER,
        ptimfIMFConfigurationParentOID  OBJECT IDENTIFIER,
        ptimfIMFConfigurationRowStatus  RowStatus,
        ptimfIMFConfigurationIndex      Integer32
    }

ptimfIMFConfigurationVersion OBJECT-TYPE
    SYNTAX          Integer32 (-2147483648..2147483647)
    MAX-ACCESS      read-only
    STATUS          current
    DESCRIPTION     
            "Integrated Monitor Feed version currently supported that is backward compatible with older library versions if necessary."
    ::= { ptimfIMFConfigurationEntry 1 }

ptimfIMFConfigurationLicenseStatus OBJECT-TYPE
    SYNTAX          INTEGER { unlicensed(0), active(1) }
    MAX-ACCESS      read-only
    STATUS          current
    DESCRIPTION     
            "IMF license status (ACTIVE/UNLICENSED). \nIf the IMF is not licensed, the traffic processes TIPC service is closed and no traffic will be processed."
    ::= { ptimfIMFConfigurationEntry 2 }

ptimfIMFConfigurationErrors OBJECT-TYPE
    SYNTAX          INTEGER { notLogged(0), logged(1) }
    MAX-ACCESS      read-create
    STATUS          current
    DESCRIPTION     
            "If this flag is set to LOGGED, then the system logs to the debug log file all application errors. \nIt is strongly recommended that this attribute be set to LOGGED for live systems."
    ::= { ptimfIMFConfigurationEntry 10 }

ptimfIMFConfigurationSetupManagement OBJECT-TYPE
    SYNTAX          INTEGER { notLogged(0), logged(1) }
    MAX-ACCESS      read-create
    STATUS          current
    DESCRIPTION     
            "If this flag is set to LOGGED, then the system logs to the debug log file all application setup information. \nIt is recommended that this attribute be set to LOGGED for live systems."
    ::= { ptimfIMFConfigurationEntry 11 }

ptimfIMFConfigurationExecutionTrace OBJECT-TYPE
    SYNTAX          INTEGER { notLogged(0), logged(1) }
    MAX-ACCESS      read-create
    STATUS          current
    DESCRIPTION     
            "If this flag is set to LOGGED, then the system logs to the debug log file the complete execution trace during the processing of incoming traffic. \nIt is required that this attribute be set to NOT LOGGED for live systems."
    ::= { ptimfIMFConfigurationEntry 12 }

ptimfIMFConfigurationPeerManagement OBJECT-TYPE
    SYNTAX          INTEGER { notLogged(0), logged(1) }
    MAX-ACCESS      read-create
    STATUS          current
    DESCRIPTION     
            "If this flag is set to LOGGED, then the system logs to the debug log file the application inter-peer information. \nIt is required that this attribute be set to NOT LOGGED for live systems."
    ::= { ptimfIMFConfigurationEntry 13 }

ptimfIMFConfigurationActions OBJECT-TYPE
    SYNTAX          INTEGER { restoreDebugDefaults(1) }
    MAX-ACCESS      read-create
    STATUS          current
    DESCRIPTION     
            "The OID of all possible actions for this instance"
    ::= { ptimfIMFConfigurationEntry 252 }

ptimfIMFConfigurationParentOID OBJECT-TYPE
    SYNTAX          OBJECT IDENTIFIER
    MAX-ACCESS      read-create
    STATUS          current
    DESCRIPTION     
            "The OID of the parent object for this instance"
    ::= { ptimfIMFConfigurationEntry 253 }

ptimfIMFConfigurationRowStatus OBJECT-TYPE
    SYNTAX          RowStatus
    MAX-ACCESS      read-create
    STATUS          current
    DESCRIPTION     
            "The row status for the imfIMFConfiguration table"
    ::= { ptimfIMFConfigurationEntry 254 }

ptimfIMFConfigurationIndex OBJECT-TYPE
    SYNTAX          Integer32 (-2147483648..2147483647)
    MAX-ACCESS      not-accessible
    STATUS          current
    DESCRIPTION     
            "The row number for the imfIMFConfiguration table"
    ::= { ptimfIMFConfigurationEntry 255 }

ptimfIMFConnections OBJECT IDENTIFIER
    ::= { ptConnGroup 1152 }

ptimfIMFConnectionsTable OBJECT-TYPE
    SYNTAX          SEQUENCE OF PtimfIMFConnectionsEntry
    MAX-ACCESS      not-accessible
    STATUS          current
    DESCRIPTION     
            "No description supplied in the proxy config file."
    ::= { ptimfIMFConnections 1 }

ptimfIMFConnectionsEntry OBJECT-TYPE
    SYNTAX          PtimfIMFConnectionsEntry
    MAX-ACCESS      not-accessible
    STATUS          current
    DESCRIPTION     
            "A sequence of imfIMFConnections attributes."
    INDEX           { ptConnGroupIndex, ptimfIMFConnectionsIndex }
    ::= { ptimfIMFConnectionsTable 1 }

PtimfIMFConnectionsEntry ::=
    SEQUENCE {
        ptimfIMFConnectionsCount        Integer32,
        ptimfIMFConnectionsParentOID    OBJECT IDENTIFIER,
        ptimfIMFConnectionsRowStatus    RowStatus,
        ptimfIMFConnectionsIndex        Integer32
    }

ptimfIMFConnectionsCount OBJECT-TYPE
    SYNTAX          Integer32 (-2147483648..2147483647)
    MAX-ACCESS      read-only
    STATUS          current
    DESCRIPTION     
            "Number of IMF Connections."
    ::= { ptimfIMFConnectionsEntry 1 }

ptimfIMFConnectionsParentOID OBJECT-TYPE
    SYNTAX          OBJECT IDENTIFIER
    MAX-ACCESS      read-create
    STATUS          current
    DESCRIPTION     
            "The OID of the parent object for this instance"
    ::= { ptimfIMFConnectionsEntry 253 }

ptimfIMFConnectionsRowStatus OBJECT-TYPE
    SYNTAX          RowStatus
    MAX-ACCESS      read-create
    STATUS          current
    DESCRIPTION     
            "The row status for the imfIMFConnections table"
    ::= { ptimfIMFConnectionsEntry 254 }

ptimfIMFConnectionsIndex OBJECT-TYPE
    SYNTAX          Integer32 (-2147483648..2147483647)
    MAX-ACCESS      not-accessible
    STATUS          current
    DESCRIPTION     
            "The row number for the imfIMFConnections table"
    ::= { ptimfIMFConnectionsEntry 255 }

ptimfIMFConnection OBJECT IDENTIFIER
    ::= { ptimfIMFConnections 1153 }

ptimfIMFConnectionTable OBJECT-TYPE
    SYNTAX          SEQUENCE OF PtimfIMFConnectionEntry
    MAX-ACCESS      not-accessible
    STATUS          current
    DESCRIPTION     
            "No description supplied in the proxy config file."
    ::= { ptimfIMFConnection 1 }

ptimfIMFConnectionEntry OBJECT-TYPE
    SYNTAX          PtimfIMFConnectionEntry
    MAX-ACCESS      not-accessible
    STATUS          current
    DESCRIPTION     
            "A sequence of imfIMFConnection attributes."
    INDEX           { ptConnGroupIndex, 
                      ptimfIMFConnectionIMFConnectionsIndex, 
                      ptimfIMFConnectionIndex }
    ::= { ptimfIMFConnectionTable 1 }

PtimfIMFConnectionEntry ::=
    SEQUENCE {
        ptimfIMFConnectionName          DisplayString,
        ptimfIMFConnectionSlot          Integer32,
        ptimfIMFConnectionInterface     INTEGER,
        ptimfIMFConnectionIPProtocol    INTEGER,
        ptimfIMFConnectionTrafficDirection  INTEGER,
        ptimfIMFConnectionLocalIPAddress1 DisplayString,
        ptimfIMFConnectionLocalIPAddress2 DisplayString,
        ptimfIMFConnectionLocalPort     Integer32,
        ptimfIMFConnectionRemoteIPAddress1  DisplayString,
        ptimfIMFConnectionRemoteIPAddress2  DisplayString,
        ptimfIMFConnectionRemotePort    Integer32,
        ptimfIMFConnectionStatus        INTEGER,
        ptimfIMFConnectionConnectionID  Integer32,
        ptimfIMFConnectionIMFConnectionsIndex     Integer32,
        ptimfIMFConnectionActions       INTEGER,
        ptimfIMFConnectionParentOID     OBJECT IDENTIFIER,
        ptimfIMFConnectionRowStatus     RowStatus,
        ptimfIMFConnectionIndex         Integer32
    }

ptimfIMFConnectionName OBJECT-TYPE
    SYNTAX          DisplayString (SIZE(0..255))
    MAX-ACCESS      read-only
    STATUS          current
    DESCRIPTION     
            "IMF Connection unique name. The maximum number of characters the attribute may contain is 15."
    ::= { ptimfIMFConnectionEntry 1 }

ptimfIMFConnectionSlot OBJECT-TYPE
    SYNTAX          Integer32 (-2147483648..2147483647)
    MAX-ACCESS      read-only
    STATUS          current
    DESCRIPTION     
            "IMF Connection slot number."
    ::= { ptimfIMFConnectionEntry 2 }

ptimfIMFConnectionInterface OBJECT-TYPE
    SYNTAX          INTEGER { default(0) }
    MAX-ACCESS      read-only
    STATUS          current
    DESCRIPTION     
            "IMF Connection interface (DEFAULT)."
    ::= { ptimfIMFConnectionEntry 3 }

ptimfIMFConnectionIPProtocol OBJECT-TYPE
    SYNTAX          INTEGER { tcp(0) }
    MAX-ACCESS      read-only
    STATUS          current
    DESCRIPTION     
            "IMF Connection IP protocol (TCP only)."
    ::= { ptimfIMFConnectionEntry 4 }

ptimfIMFConnectionTrafficDirection OBJECT-TYPE
    SYNTAX          INTEGER { all(0), incoming(1), outgoing(2) }
    MAX-ACCESS      read-create
    STATUS          current
    DESCRIPTION     
            "Interface supported traffic direction. \nValid values: ALL, INCOMING, and OUTGOING. \nDefault value: ALL."
    ::= { ptimfIMFConnectionEntry 5 }

ptimfIMFConnectionLocalIPAddress1 OBJECT-TYPE
    SYNTAX          DisplayString (SIZE(0..255))
    MAX-ACCESS      read-create
    STATUS          current
    DESCRIPTION     
            "Primary local IP address of this IMF Connection. \nThis may be a hostname provisioned in /etc/hosts or an IP Address. \nThis information is only used if the connection IP Protocol attribute is set to SCTP. TCP/IP does not require knowledge of the local address."
    ::= { ptimfIMFConnectionEntry 6 }

ptimfIMFConnectionLocalIPAddress2 OBJECT-TYPE
    SYNTAX          DisplayString (SIZE(0..255))
    MAX-ACCESS      read-create
    STATUS          current
    DESCRIPTION     
            "Secondary local IP address of this IMF Connection. \nThis may be a hostname provisioned in /etc/hosts or an IP Address. \nThis information is only used if the connection IP Protocol attribute is set to SCTP. TCP/IP does not require knowledge of the local address."
    ::= { ptimfIMFConnectionEntry 7 }

ptimfIMFConnectionLocalPort OBJECT-TYPE
    SYNTAX          Integer32 (0..65535)
    MAX-ACCESS      read-create
    STATUS          current
    DESCRIPTION     
            "Local port of this IMF Connection. \nThis information is only used if the connection IP Protocol attribute is set to SCTP. TCP/IP does not require knowledge of the local port, will be assigned internally."
    ::= { ptimfIMFConnectionEntry 8 }

ptimfIMFConnectionRemoteIPAddress1 OBJECT-TYPE
    SYNTAX          DisplayString (SIZE(0..255))
    MAX-ACCESS      read-create
    STATUS          current
    DESCRIPTION     
            "Primary remote IP address of this IMF Connection. \nThis may be a hostname provisioned in /etc/hosts or an IP Address. \nThis is the address of the IMF 3rd party probe."
    ::= { ptimfIMFConnectionEntry 9 }

ptimfIMFConnectionRemoteIPAddress2 OBJECT-TYPE
    SYNTAX          DisplayString (SIZE(0..255))
    MAX-ACCESS      read-create
    STATUS          current
    DESCRIPTION     
            "Secondary remote IP address of this IMF Connection. \nThis may be a hostname provisioned in /etc/hosts or an IP Address. \nThis information is only used if the connection IP Protocol attribute is set to SCTP. TCP/IP does not require knowledge of the local address."
    ::= { ptimfIMFConnectionEntry 10 }

ptimfIMFConnectionRemotePort OBJECT-TYPE
    SYNTAX          Integer32 (0..65535)
    MAX-ACCESS      read-create
    STATUS          current
    DESCRIPTION     
            "Remote port of this IMF Connection. \nThis is the port of the IMF 3rd party probe."
    ::= { ptimfIMFConnectionEntry 11 }

ptimfIMFConnectionStatus OBJECT-TYPE
    SYNTAX          INTEGER { notApplicable(0), inactive(1), 
                        notConnected(2), connected(3) }
    MAX-ACCESS      read-only
    STATUS          current
    DESCRIPTION     
            "IMF Connection status (NOT APPLICABLE/INACTIVE/NOT CONNECTED/CONNECTED). \nNOT APPLICABLE only applies to UDP protocol."
    ::= { ptimfIMFConnectionEntry 12 }

ptimfIMFConnectionConnectionID OBJECT-TYPE
    SYNTAX          Integer32 (-2147483648..2147483647)
    MAX-ACCESS      read-only
    STATUS          current
    DESCRIPTION     
            "Internal hidden attribute"
    ::= { ptimfIMFConnectionEntry 13 }

ptimfIMFConnectionIMFConnectionsIndex OBJECT-TYPE
    SYNTAX          Integer32 (-2147483648..2147483647)
    MAX-ACCESS      not-accessible
    STATUS          current
    DESCRIPTION     
            "This is the index of the parent type for this object.
             This parent type is IMFConnections."
    ::= { ptimfIMFConnectionEntry 242 }

ptimfIMFConnectionActions OBJECT-TYPE
    SYNTAX          INTEGER { activate(1), deactivate(2) }
    MAX-ACCESS      read-create
    STATUS          current
    DESCRIPTION     
            "The OID of all possible actions for this instance"
    ::= { ptimfIMFConnectionEntry 252 }

ptimfIMFConnectionParentOID OBJECT-TYPE
    SYNTAX          OBJECT IDENTIFIER
    MAX-ACCESS      read-create
    STATUS          current
    DESCRIPTION     
            "The OID of the parent object for this instance"
    ::= { ptimfIMFConnectionEntry 253 }

ptimfIMFConnectionRowStatus OBJECT-TYPE
    SYNTAX          RowStatus
    MAX-ACCESS      read-create
    STATUS          current
    DESCRIPTION     
            "The row status for the imfIMFConnection table"
    ::= { ptimfIMFConnectionEntry 254 }

ptimfIMFConnectionIndex OBJECT-TYPE
    SYNTAX          Integer32 (-2147483648..2147483647)
    MAX-ACCESS      not-accessible
    STATUS          current
    DESCRIPTION     
            "The row number for the imfIMFConnection table"
    ::= { ptimfIMFConnectionEntry 255 }

ptimfIMFTrafficProcesses OBJECT IDENTIFIER
    ::= { ptConnGroup 1154 }

ptimfIMFTrafficProcessesTable OBJECT-TYPE
    SYNTAX          SEQUENCE OF PtimfIMFTrafficProcessesEntry
    MAX-ACCESS      not-accessible
    STATUS          current
    DESCRIPTION     
            "No description supplied in the proxy config file."
    ::= { ptimfIMFTrafficProcesses 1 }

ptimfIMFTrafficProcessesEntry OBJECT-TYPE
    SYNTAX          PtimfIMFTrafficProcessesEntry
    MAX-ACCESS      not-accessible
    STATUS          current
    DESCRIPTION     
            "A sequence of imfIMFTrafficProcesses attributes."
    INDEX           { ptConnGroupIndex, ptimfIMFTrafficProcessesIndex }
    ::= { ptimfIMFTrafficProcessesTable 1 }

PtimfIMFTrafficProcessesEntry ::=
    SEQUENCE {
        ptimfIMFTrafficProcessesCount   Integer32,
        ptimfIMFTrafficProcessesParentOID OBJECT IDENTIFIER,
        ptimfIMFTrafficProcessesRowStatus RowStatus,
        ptimfIMFTrafficProcessesIndex   Integer32
    }

ptimfIMFTrafficProcessesCount OBJECT-TYPE
    SYNTAX          Integer32 (-2147483648..2147483647)
    MAX-ACCESS      read-only
    STATUS          current
    DESCRIPTION     
            "Number of IMF Traffic Processes."
    ::= { ptimfIMFTrafficProcessesEntry 1 }

ptimfIMFTrafficProcessesParentOID OBJECT-TYPE
    SYNTAX          OBJECT IDENTIFIER
    MAX-ACCESS      read-create
    STATUS          current
    DESCRIPTION     
            "The OID of the parent object for this instance"
    ::= { ptimfIMFTrafficProcessesEntry 253 }

ptimfIMFTrafficProcessesRowStatus OBJECT-TYPE
    SYNTAX          RowStatus
    MAX-ACCESS      read-create
    STATUS          current
    DESCRIPTION     
            "The row status for the imfIMFTrafficProcesses table"
    ::= { ptimfIMFTrafficProcessesEntry 254 }

ptimfIMFTrafficProcessesIndex OBJECT-TYPE
    SYNTAX          Integer32 (-2147483648..2147483647)
    MAX-ACCESS      not-accessible
    STATUS          current
    DESCRIPTION     
            "The row number for the imfIMFTrafficProcesses table"
    ::= { ptimfIMFTrafficProcessesEntry 255 }

ptimfIMFTrafficProcess OBJECT IDENTIFIER
    ::= { ptimfIMFTrafficProcesses 1155 }

ptimfIMFTrafficProcessTable OBJECT-TYPE
    SYNTAX          SEQUENCE OF PtimfIMFTrafficProcessEntry
    MAX-ACCESS      not-accessible
    STATUS          current
    DESCRIPTION     
            "No description supplied in the proxy config file."
    ::= { ptimfIMFTrafficProcess 1 }

ptimfIMFTrafficProcessEntry OBJECT-TYPE
    SYNTAX          PtimfIMFTrafficProcessEntry
    MAX-ACCESS      not-accessible
    STATUS          current
    DESCRIPTION     
            "A sequence of imfIMFTrafficProcess attributes."
    INDEX           { ptConnGroupIndex, 
                      ptimfIMFTrafficProcessIMFTrafficProcessesIndex, 
                      ptimfIMFTrafficProcessIndex }
    ::= { ptimfIMFTrafficProcessTable 1 }

PtimfIMFTrafficProcessEntry ::=
    SEQUENCE {
        ptimfIMFTrafficProcessName      DisplayString,
        ptimfIMFTrafficProcessSlot      Integer32,
        ptimfIMFTrafficProcessVersion   Integer32,
        ptimfIMFTrafficProcessIMFTrafficProcessesIndex              Integer32,
        ptimfIMFTrafficProcessParentOID OBJECT IDENTIFIER,
        ptimfIMFTrafficProcessRowStatus RowStatus,
        ptimfIMFTrafficProcessIndex     Integer32
    }

ptimfIMFTrafficProcessName OBJECT-TYPE
    SYNTAX          DisplayString (SIZE(0..255))
    MAX-ACCESS      read-only
    STATUS          current
    DESCRIPTION     
            "IMF Traffic Process name."
    ::= { ptimfIMFTrafficProcessEntry 1 }

ptimfIMFTrafficProcessSlot OBJECT-TYPE
    SYNTAX          Integer32 (-2147483648..2147483647)
    MAX-ACCESS      read-only
    STATUS          current
    DESCRIPTION     
            "IMF Traffic Process slot."
    ::= { ptimfIMFTrafficProcessEntry 2 }

ptimfIMFTrafficProcessVersion OBJECT-TYPE
    SYNTAX          Integer32 (-2147483648..2147483647)
    MAX-ACCESS      read-only
    STATUS          current
    DESCRIPTION     
            "IMF Traffic Process version."
    ::= { ptimfIMFTrafficProcessEntry 3 }

ptimfIMFTrafficProcessIMFTrafficProcessesIndex OBJECT-TYPE
    SYNTAX          Integer32 (-2147483648..2147483647)
    MAX-ACCESS      not-accessible
    STATUS          current
    DESCRIPTION     
            "This is the index of the parent type for this object.
             This parent type is IMFTrafficProcesses."
    ::= { ptimfIMFTrafficProcessEntry 242 }

ptimfIMFTrafficProcessParentOID OBJECT-TYPE
    SYNTAX          OBJECT IDENTIFIER
    MAX-ACCESS      read-create
    STATUS          current
    DESCRIPTION     
            "The OID of the parent object for this instance"
    ::= { ptimfIMFTrafficProcessEntry 253 }

ptimfIMFTrafficProcessRowStatus OBJECT-TYPE
    SYNTAX          RowStatus
    MAX-ACCESS      read-create
    STATUS          current
    DESCRIPTION     
            "The row status for the imfIMFTrafficProcess table"
    ::= { ptimfIMFTrafficProcessEntry 254 }

ptimfIMFTrafficProcessIndex OBJECT-TYPE
    SYNTAX          Integer32 (-2147483648..2147483647)
    MAX-ACCESS      not-accessible
    STATUS          current
    DESCRIPTION     
            "The row number for the imfIMFTrafficProcess table"
    ::= { ptimfIMFTrafficProcessEntry 255 }

ptimfIMFPacketCapture OBJECT IDENTIFIER
    ::= { ptConnGroup 1156 }

ptimfIMFPacketCaptureTable OBJECT-TYPE
    SYNTAX          SEQUENCE OF PtimfIMFPacketCaptureEntry
    MAX-ACCESS      not-accessible
    STATUS          current
    DESCRIPTION     
            "No description supplied in the proxy config file."
    ::= { ptimfIMFPacketCapture 1 }

ptimfIMFPacketCaptureEntry OBJECT-TYPE
    SYNTAX          PtimfIMFPacketCaptureEntry
    MAX-ACCESS      not-accessible
    STATUS          current
    DESCRIPTION     
            "A sequence of imfIMFPacketCapture attributes."
    INDEX           { ptConnGroupIndex, ptimfIMFPacketCaptureIndex }
    ::= { ptimfIMFPacketCaptureTable 1 }

PtimfIMFPacketCaptureEntry ::=
    SEQUENCE {
        ptimfIMFPacketCaptureCaptureTime Integer32,
        ptimfIMFPacketCaptureStatus     INTEGER,
        ptimfIMFPacketCaptureActions    INTEGER,
        ptimfIMFPacketCaptureParentOID  OBJECT IDENTIFIER,
        ptimfIMFPacketCaptureRowStatus  RowStatus,
        ptimfIMFPacketCaptureIndex      Integer32
    }

ptimfIMFPacketCaptureCaptureTime OBJECT-TYPE
    SYNTAX          Integer32 (-2147483648..2147483647)
    MAX-ACCESS      read-create
    STATUS          current
    DESCRIPTION     
            "Time in seconds to run the capture. \nWhen the user starts the capture, a timer is started for this many seconds. \nIf the user does not manually stop the capture first, the capture is stopped when the timer finishes. \nPlease wait five seconds after starting the capture before sending the desired traffic."
    ::= { ptimfIMFPacketCaptureEntry 1 }

ptimfIMFPacketCaptureStatus OBJECT-TYPE
    SYNTAX          INTEGER { stopped(0), running(1) }
    MAX-ACCESS      read-only
    STATUS          current
    DESCRIPTION     
            "Current status of the packet capture feature. \nWhen RUNNING, captured packets are saved to the file /var/log/packet_capture.pcap. \nIf that file already exists, it will be overwritten. \nThe file is accessible under File Retrieval on the web interface."
    ::= { ptimfIMFPacketCaptureEntry 2 }

ptimfIMFPacketCaptureActions OBJECT-TYPE
    SYNTAX          INTEGER { start(1), stop(2) }
    MAX-ACCESS      read-create
    STATUS          current
    DESCRIPTION     
            "The OID of all possible actions for this instance"
    ::= { ptimfIMFPacketCaptureEntry 252 }

ptimfIMFPacketCaptureParentOID OBJECT-TYPE
    SYNTAX          OBJECT IDENTIFIER
    MAX-ACCESS      read-create
    STATUS          current
    DESCRIPTION     
            "The OID of the parent object for this instance"
    ::= { ptimfIMFPacketCaptureEntry 253 }

ptimfIMFPacketCaptureRowStatus OBJECT-TYPE
    SYNTAX          RowStatus
    MAX-ACCESS      read-create
    STATUS          current
    DESCRIPTION     
            "The row status for the imfIMFPacketCapture table"
    ::= { ptimfIMFPacketCaptureEntry 254 }

ptimfIMFPacketCaptureIndex OBJECT-TYPE
    SYNTAX          Integer32 (-2147483648..2147483647)
    MAX-ACCESS      not-accessible
    STATUS          current
    DESCRIPTION     
            "The row number for the imfIMFPacketCapture table"
    ::= { ptimfIMFPacketCaptureEntry 255 }

pthwmonHardwareMonitor OBJECT IDENTIFIER
    ::= { ptConnGroup 1171 }

pthwmonHardwareMonitorTable OBJECT-TYPE
    SYNTAX          SEQUENCE OF PthwmonHardwareMonitorEntry
    MAX-ACCESS      not-accessible
    STATUS          current
    DESCRIPTION     
            "No description supplied in the proxy config file."
    ::= { pthwmonHardwareMonitor 1 }

pthwmonHardwareMonitorEntry OBJECT-TYPE
    SYNTAX          PthwmonHardwareMonitorEntry
    MAX-ACCESS      not-accessible
    STATUS          current
    DESCRIPTION     
            "A sequence of hwmonHardwareMonitor attributes."
    INDEX           { ptConnGroupIndex, pthwmonHardwareMonitorIndex }
    ::= { pthwmonHardwareMonitorTable 1 }

PthwmonHardwareMonitorEntry ::=
    SEQUENCE {
        pthwmonHardwareMonitorStatus    DisplayString,
        pthwmonHardwareMonitorDebugLogging  INTEGER,
        pthwmonHardwareMonitorMinorTelcoAlarm     INTEGER,
        pthwmonHardwareMonitorMajorTelcoAlarm     INTEGER,
        pthwmonHardwareMonitorCriticalTelcoAlarm        INTEGER,
        pthwmonHardwareMonitorActiveMCH DisplayString,
        pthwmonHardwareMonitorHardwareMonitorSlot         DisplayString,
        pthwmonHardwareMonitorActions   INTEGER,
        pthwmonHardwareMonitorParentOID OBJECT IDENTIFIER,
        pthwmonHardwareMonitorRowStatus RowStatus,
        pthwmonHardwareMonitorIndex     Integer32
    }

pthwmonHardwareMonitorStatus OBJECT-TYPE
    SYNTAX          DisplayString (SIZE(0..255))
    MAX-ACCESS      read-only
    STATUS          current
    DESCRIPTION     
            "Hardware monitor status."
    ::= { pthwmonHardwareMonitorEntry 1 }

pthwmonHardwareMonitorDebugLogging OBJECT-TYPE
    SYNTAX          INTEGER { disabled(0), enabled(1) }
    MAX-ACCESS      read-create
    STATUS          current
    DESCRIPTION     
            "Enable/disable debug logging."
    ::= { pthwmonHardwareMonitorEntry 2 }

pthwmonHardwareMonitorMinorTelcoAlarm OBJECT-TYPE
    SYNTAX          INTEGER { alUnset(0), alSet(1) }
    MAX-ACCESS      read-only
    STATUS          current
    DESCRIPTION     
            "Alarm state indicated by MCH ! light."
    ::= { pthwmonHardwareMonitorEntry 3 }

pthwmonHardwareMonitorMajorTelcoAlarm OBJECT-TYPE
    SYNTAX          INTEGER { alUnset(0), alSet(1) }
    MAX-ACCESS      read-only
    STATUS          current
    DESCRIPTION     
            "Alarm state indicated by MCH !! light."
    ::= { pthwmonHardwareMonitorEntry 4 }

pthwmonHardwareMonitorCriticalTelcoAlarm OBJECT-TYPE
    SYNTAX          INTEGER { alUnset(0), alSet(1) }
    MAX-ACCESS      read-only
    STATUS          current
    DESCRIPTION     
            "Alarm state indicated by MCH !!! light."
    ::= { pthwmonHardwareMonitorEntry 5 }

pthwmonHardwareMonitorActiveMCH OBJECT-TYPE
    SYNTAX          DisplayString (SIZE(0..255))
    MAX-ACCESS      read-only
    STATUS          current
    DESCRIPTION     
            "Identifies the MCH that is actively processing IPMC commands and controlling the Telco Alarm Panel."
    ::= { pthwmonHardwareMonitorEntry 6 }

pthwmonHardwareMonitorHardwareMonitorSlot OBJECT-TYPE
    SYNTAX          DisplayString (SIZE(0..255))
    MAX-ACCESS      read-only
    STATUS          current
    DESCRIPTION     
            "Slot HWMON is running on."
    ::= { pthwmonHardwareMonitorEntry 7 }

pthwmonHardwareMonitorActions OBJECT-TYPE
    SYNTAX          INTEGER { resetTelcoAlarm(1), 
                        restoreDebugDefaults(2) }
    MAX-ACCESS      read-create
    STATUS          current
    DESCRIPTION     
            "The OID of all possible actions for this instance"
    ::= { pthwmonHardwareMonitorEntry 252 }

pthwmonHardwareMonitorParentOID OBJECT-TYPE
    SYNTAX          OBJECT IDENTIFIER
    MAX-ACCESS      read-create
    STATUS          current
    DESCRIPTION     
            "The OID of the parent object for this instance"
    ::= { pthwmonHardwareMonitorEntry 253 }

pthwmonHardwareMonitorRowStatus OBJECT-TYPE
    SYNTAX          RowStatus
    MAX-ACCESS      read-create
    STATUS          current
    DESCRIPTION     
            "The row status for the hwmonHardwareMonitor table"
    ::= { pthwmonHardwareMonitorEntry 254 }

pthwmonHardwareMonitorIndex OBJECT-TYPE
    SYNTAX          Integer32 (-2147483648..2147483647)
    MAX-ACCESS      not-accessible
    STATUS          current
    DESCRIPTION     
            "The row number for the hwmonHardwareMonitor table"
    ::= { pthwmonHardwareMonitorEntry 255 }

pthwmonSlot OBJECT IDENTIFIER
    ::= { pthwmonHardwareMonitor 1172 }

pthwmonSlotTable OBJECT-TYPE
    SYNTAX          SEQUENCE OF PthwmonSlotEntry
    MAX-ACCESS      not-accessible
    STATUS          current
    DESCRIPTION     
            "No description supplied in the proxy config file."
    ::= { pthwmonSlot 1 }

pthwmonSlotEntry OBJECT-TYPE
    SYNTAX          PthwmonSlotEntry
    MAX-ACCESS      not-accessible
    STATUS          current
    DESCRIPTION     
            "A sequence of hwmonSlot attributes."
    INDEX           { ptConnGroupIndex, pthwmonSlotHardwareMonitorIndex, 
                      pthwmonSlotIndex }
    ::= { pthwmonSlotTable 1 }

PthwmonSlotEntry ::=
    SEQUENCE {
        pthwmonSlotSlotNumber           Integer32,
        pthwmonSlotBoardManufactureDate DisplayString,
        pthwmonSlotBoardManufacturer    DisplayString,
        pthwmonSlotBoardProductName     DisplayString,
        pthwmonSlotBoardSerialNumber    DisplayString,
        pthwmonSlotBoardPartNumber      DisplayString,
        pthwmonSlotBoardFRUFileID       DisplayString,
        pthwmonSlotProductManufacturer  DisplayString,
        pthwmonSlotProductName          DisplayString,
        pthwmonSlotProductModelNumber   DisplayString,
        pthwmonSlotProductVersion       DisplayString,
        pthwmonSlotProductSerialNumber  DisplayString,
        pthwmonSlotProductFRUFileID     DisplayString,
        pthwmonSlotMMCFirmwareVersion   DisplayString,
        pthwmonSlotBootcodeFirmwareVersion  DisplayString,
        pthwmonSlotHardwareMonitorIndex Integer32,
        pthwmonSlotParentOID            OBJECT IDENTIFIER,
        pthwmonSlotRowStatus            RowStatus,
        pthwmonSlotIndex                Integer32
    }

pthwmonSlotSlotNumber OBJECT-TYPE
    SYNTAX          Integer32 (-2147483648..2147483647)
    MAX-ACCESS      read-only
    STATUS          current
    DESCRIPTION     
            "Slot number."
    ::= { pthwmonSlotEntry 1 }

pthwmonSlotBoardManufactureDate OBJECT-TYPE
    SYNTAX          DisplayString (SIZE(0..255))
    MAX-ACCESS      read-only
    STATUS          current
    DESCRIPTION     
            "Manufacture date of the board."
    ::= { pthwmonSlotEntry 2 }

pthwmonSlotBoardManufacturer OBJECT-TYPE
    SYNTAX          DisplayString (SIZE(0..255))
    MAX-ACCESS      read-only
    STATUS          current
    DESCRIPTION     
            "Manufacturer of the board."
    ::= { pthwmonSlotEntry 3 }

pthwmonSlotBoardProductName OBJECT-TYPE
    SYNTAX          DisplayString (SIZE(0..255))
    MAX-ACCESS      read-only
    STATUS          current
    DESCRIPTION     
            "Product name of the board."
    ::= { pthwmonSlotEntry 4 }

pthwmonSlotBoardSerialNumber OBJECT-TYPE
    SYNTAX          DisplayString (SIZE(0..255))
    MAX-ACCESS      read-only
    STATUS          current
    DESCRIPTION     
            "Serial number of the board."
    ::= { pthwmonSlotEntry 5 }

pthwmonSlotBoardPartNumber OBJECT-TYPE
    SYNTAX          DisplayString (SIZE(0..255))
    MAX-ACCESS      read-only
    STATUS          current
    DESCRIPTION     
            "Part number of the board."
    ::= { pthwmonSlotEntry 6 }

pthwmonSlotBoardFRUFileID OBJECT-TYPE
    SYNTAX          DisplayString (SIZE(0..255))
    MAX-ACCESS      read-only
    STATUS          current
    DESCRIPTION     
            "FRU file ID of the board."
    ::= { pthwmonSlotEntry 7 }

pthwmonSlotProductManufacturer OBJECT-TYPE
    SYNTAX          DisplayString (SIZE(0..255))
    MAX-ACCESS      read-only
    STATUS          current
    DESCRIPTION     
            "Manufacturer of the product."
    ::= { pthwmonSlotEntry 8 }

pthwmonSlotProductName OBJECT-TYPE
    SYNTAX          DisplayString (SIZE(0..255))
    MAX-ACCESS      read-only
    STATUS          current
    DESCRIPTION     
            "Name of the product."
    ::= { pthwmonSlotEntry 9 }

pthwmonSlotProductModelNumber OBJECT-TYPE
    SYNTAX          DisplayString (SIZE(0..255))
    MAX-ACCESS      read-only
    STATUS          current
    DESCRIPTION     
            "Model number of the product."
    ::= { pthwmonSlotEntry 10 }

pthwmonSlotProductVersion OBJECT-TYPE
    SYNTAX          DisplayString (SIZE(0..255))
    MAX-ACCESS      read-only
    STATUS          current
    DESCRIPTION     
            "Version of the product."
    ::= { pthwmonSlotEntry 11 }

pthwmonSlotProductSerialNumber OBJECT-TYPE
    SYNTAX          DisplayString (SIZE(0..255))
    MAX-ACCESS      read-only
    STATUS          current
    DESCRIPTION     
            "Serial number of the product."
    ::= { pthwmonSlotEntry 12 }

pthwmonSlotProductFRUFileID OBJECT-TYPE
    SYNTAX          DisplayString (SIZE(0..255))
    MAX-ACCESS      read-only
    STATUS          current
    DESCRIPTION     
            "FRU file ID of the product."
    ::= { pthwmonSlotEntry 13 }

pthwmonSlotMMCFirmwareVersion OBJECT-TYPE
    SYNTAX          DisplayString (SIZE(0..255))
    MAX-ACCESS      read-only
    STATUS          current
    DESCRIPTION     
            "MMC or MCMC Firmware Version."
    ::= { pthwmonSlotEntry 14 }

pthwmonSlotBootcodeFirmwareVersion OBJECT-TYPE
    SYNTAX          DisplayString (SIZE(0..255))
    MAX-ACCESS      read-only
    STATUS          current
    DESCRIPTION     
            "Bootcode Firmware Version."
    ::= { pthwmonSlotEntry 15 }

pthwmonSlotHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonSlotEntry 242 }

pthwmonSlotParentOID OBJECT-TYPE
    SYNTAX          OBJECT IDENTIFIER
    MAX-ACCESS      read-create
    STATUS          current
    DESCRIPTION     
            "The OID of the parent object for this instance"
    ::= { pthwmonSlotEntry 253 }

pthwmonSlotRowStatus OBJECT-TYPE
    SYNTAX          RowStatus
    MAX-ACCESS      read-create
    STATUS          current
    DESCRIPTION     
            "The row status for the hwmonSlot table"
    ::= { pthwmonSlotEntry 254 }

pthwmonSlotIndex OBJECT-TYPE
    SYNTAX          Integer32 (-2147483648..2147483647)
    MAX-ACCESS      not-accessible
    STATUS          current
    DESCRIPTION     
            "The row number for the hwmonSlot table"
    ::= { pthwmonSlotEntry 255 }

pthwmonDiscreteSensor OBJECT IDENTIFIER
    ::= { pthwmonSlot 1173 }

pthwmonDiscreteSensorTable OBJECT-TYPE
    SYNTAX          SEQUENCE OF PthwmonDiscreteSensorEntry
    MAX-ACCESS      not-accessible
    STATUS          current
    DESCRIPTION     
            "No description supplied in the proxy config file."
    ::= { pthwmonDiscreteSensor 1 }

pthwmonDiscreteSensorEntry OBJECT-TYPE
    SYNTAX          PthwmonDiscreteSensorEntry
    MAX-ACCESS      not-accessible
    STATUS          current
    DESCRIPTION     
            "A sequence of hwmonDiscreteSensor attributes."
    INDEX           { ptConnGroupIndex, 
                      pthwmonDiscreteSensorHardwareMonitorIndex, 
                      pthwmonDiscreteSensorSlotIndex, 
                      pthwmonDiscreteSensorIndex }
    ::= { pthwmonDiscreteSensorTable 1 }

PthwmonDiscreteSensorEntry ::=
    SEQUENCE {
        pthwmonDiscreteSensorName       DisplayString,
        pthwmonDiscreteSensorSlot       Integer32,
        pthwmonDiscreteSensorPortalID   Integer32,
        pthwmonDiscreteSensorIPMINumber Integer32,
        pthwmonDiscreteSensorAlarmState INTEGER,
        pthwmonDiscreteSensorCurrentStatus  DisplayString,
        pthwmonDiscreteSensorHardwareMonitorIndex         Integer32,
        pthwmonDiscreteSensorSlotIndex  Integer32,
        pthwmonDiscreteSensorActions    INTEGER,
        pthwmonDiscreteSensorParentOID  OBJECT IDENTIFIER,
        pthwmonDiscreteSensorRowStatus  RowStatus,
        pthwmonDiscreteSensorIndex      Integer32
    }

pthwmonDiscreteSensorName OBJECT-TYPE
    SYNTAX          DisplayString (SIZE(0..255))
    MAX-ACCESS      read-only
    STATUS          current
    DESCRIPTION     
            "Name of this sensor."
    ::= { pthwmonDiscreteSensorEntry 1 }

pthwmonDiscreteSensorSlot OBJECT-TYPE
    SYNTAX          Integer32 (-2147483648..2147483647)
    MAX-ACCESS      read-only
    STATUS          current
    DESCRIPTION     
            "Slot number that owns this sensor. The chassis shelf manager is slot 0."
    ::= { pthwmonDiscreteSensorEntry 2 }

pthwmonDiscreteSensorPortalID OBJECT-TYPE
    SYNTAX          Integer32 (-2147483648..2147483647)
    MAX-ACCESS      read-only
    STATUS          current
    DESCRIPTION     
            "Portal ID associated with this sensor."
    ::= { pthwmonDiscreteSensorEntry 3 }

pthwmonDiscreteSensorIPMINumber OBJECT-TYPE
    SYNTAX          Integer32 (-2147483648..2147483647)
    MAX-ACCESS      read-only
    STATUS          current
    DESCRIPTION     
            "IPMI number associated with this sensor."
    ::= { pthwmonDiscreteSensorEntry 4 }

pthwmonDiscreteSensorAlarmState OBJECT-TYPE
    SYNTAX          INTEGER { ok(0), fault(1), unknown(2) }
    MAX-ACCESS      read-only
    STATUS          current
    DESCRIPTION     
            "Alarm state. Values: OK, or FAULT."
    ::= { pthwmonDiscreteSensorEntry 5 }

pthwmonDiscreteSensorCurrentStatus OBJECT-TYPE
    SYNTAX          DisplayString (SIZE(0..255))
    MAX-ACCESS      read-only
    STATUS          current
    DESCRIPTION     
            "Current sensor status. (Use 'Read Sensor' action.)"
    ::= { pthwmonDiscreteSensorEntry 6 }

pthwmonDiscreteSensorHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonDiscreteSensorEntry 242 }

pthwmonDiscreteSensorSlotIndex OBJECT-TYPE
    SYNTAX          Integer32 (-2147483648..2147483647)
    MAX-ACCESS      not-accessible
    STATUS          current
    DESCRIPTION     
            "This is the index of the parent type for this object.
             This parent type is Slot."
    ::= { pthwmonDiscreteSensorEntry 243 }

pthwmonDiscreteSensorActions OBJECT-TYPE
    SYNTAX          INTEGER { readSensor(1) }
    MAX-ACCESS      read-create
    STATUS          current
    DESCRIPTION     
            "The OID of all possible actions for this instance"
    ::= { pthwmonDiscreteSensorEntry 252 }

pthwmonDiscreteSensorParentOID OBJECT-TYPE
    SYNTAX          OBJECT IDENTIFIER
    MAX-ACCESS      read-create
    STATUS          current
    DESCRIPTION     
            "The OID of the parent object for this instance"
    ::= { pthwmonDiscreteSensorEntry 253 }

pthwmonDiscreteSensorRowStatus OBJECT-TYPE
    SYNTAX          RowStatus
    MAX-ACCESS      read-create
    STATUS          current
    DESCRIPTION     
            "The row status for the hwmonDiscreteSensor table"
    ::= { pthwmonDiscreteSensorEntry 254 }

pthwmonDiscreteSensorIndex OBJECT-TYPE
    SYNTAX          Integer32 (-2147483648..2147483647)
    MAX-ACCESS      not-accessible
    STATUS          current
    DESCRIPTION     
            "The row number for the hwmonDiscreteSensor table"
    ::= { pthwmonDiscreteSensorEntry 255 }

pthwmonThresholdSensor OBJECT IDENTIFIER
    ::= { pthwmonSlot 1174 }

pthwmonThresholdSensorTable OBJECT-TYPE
    SYNTAX          SEQUENCE OF PthwmonThresholdSensorEntry
    MAX-ACCESS      not-accessible
    STATUS          current
    DESCRIPTION     
            "No description supplied in the proxy config file."
    ::= { pthwmonThresholdSensor 1 }

pthwmonThresholdSensorEntry OBJECT-TYPE
    SYNTAX          PthwmonThresholdSensorEntry
    MAX-ACCESS      not-accessible
    STATUS          current
    DESCRIPTION     
            "A sequence of hwmonThresholdSensor attributes."
    INDEX           { ptConnGroupIndex, 
                      pthwmonThresholdSensorHardwareMonitorIndex, 
                      pthwmonThresholdSensorSlotIndex, 
                      pthwmonThresholdSensorIndex }
    ::= { pthwmonThresholdSensorTable 1 }

PthwmonThresholdSensorEntry ::=
    SEQUENCE {
        pthwmonThresholdSensorName      DisplayString,
        pthwmonThresholdSensorSlot      Integer32,
        pthwmonThresholdSensorPortalID  Integer32,
        pthwmonThresholdSensorIPMINumber Integer32,
        pthwmonThresholdSensorUnits     DisplayString,
        pthwmonThresholdSensorAlarmState INTEGER,
        pthwmonThresholdSensorCurrentReading    DisplayString,
        pthwmonThresholdSensorMaximumReading    DisplayString,
        pthwmonThresholdSensorMinimumReading    DisplayString,
        pthwmonThresholdSensorUpperCriticalThresh         DisplayString,
        pthwmonThresholdSensorUpperMajorThresh      DisplayString,
        pthwmonThresholdSensorUpperMinorThresh      DisplayString,
        pthwmonThresholdSensorLowerMinorThresh      DisplayString,
        pthwmonThresholdSensorLowerMajorThresh      DisplayString,
        pthwmonThresholdSensorLowerCriticalThresh         DisplayString,
        pthwmonThresholdSensorHardwareMonitorIndex          Integer32,
        pthwmonThresholdSensorSlotIndex Integer32,
        pthwmonThresholdSensorActions   INTEGER,
        pthwmonThresholdSensorParentOID OBJECT IDENTIFIER,
        pthwmonThresholdSensorRowStatus RowStatus,
        pthwmonThresholdSensorIndex     Integer32
    }

pthwmonThresholdSensorName OBJECT-TYPE
    SYNTAX          DisplayString (SIZE(0..255))
    MAX-ACCESS      read-only
    STATUS          current
    DESCRIPTION     
            "Name of this sensor."
    ::= { pthwmonThresholdSensorEntry 1 }

pthwmonThresholdSensorSlot OBJECT-TYPE
    SYNTAX          Integer32 (-2147483648..2147483647)
    MAX-ACCESS      read-only
    STATUS          current
    DESCRIPTION     
            "Slot number that owns this sensor. The chassis shelf manager is slot 0."
    ::= { pthwmonThresholdSensorEntry 2 }

pthwmonThresholdSensorPortalID OBJECT-TYPE
    SYNTAX          Integer32 (-2147483648..2147483647)
    MAX-ACCESS      read-only
    STATUS          current
    DESCRIPTION     
            "Portal ID associated with this sensor."
    ::= { pthwmonThresholdSensorEntry 3 }

pthwmonThresholdSensorIPMINumber OBJECT-TYPE
    SYNTAX          Integer32 (-2147483648..2147483647)
    MAX-ACCESS      read-only
    STATUS          current
    DESCRIPTION     
            "IPMI number associated with this sensor."
    ::= { pthwmonThresholdSensorEntry 4 }

pthwmonThresholdSensorUnits OBJECT-TYPE
    SYNTAX          DisplayString (SIZE(0..255))
    MAX-ACCESS      read-only
    STATUS          current
    DESCRIPTION     
            "Units in which the threshold levels are represented."
    ::= { pthwmonThresholdSensorEntry 5 }

pthwmonThresholdSensorAlarmState OBJECT-TYPE
    SYNTAX          INTEGER { ok(0), lowerCritical(1), lowerMajor(2), 
                        lowerMinor(3), upperMinor(4), upperMajor(5), 
                        upperCritical(6), unknown(7) }
    MAX-ACCESS      read-only
    STATUS          current
    DESCRIPTION     
            "Alarm state. Values: OK, or some threshold fault."
    ::= { pthwmonThresholdSensorEntry 6 }

pthwmonThresholdSensorCurrentReading OBJECT-TYPE
    SYNTAX          DisplayString (SIZE(0..255))
    MAX-ACCESS      read-only
    STATUS          current
    DESCRIPTION     
            "Current sensor reading. (Use 'Read Sensor' action.)"
    ::= { pthwmonThresholdSensorEntry 7 }

pthwmonThresholdSensorMaximumReading OBJECT-TYPE
    SYNTAX          DisplayString (SIZE(0..255))
    MAX-ACCESS      read-only
    STATUS          current
    DESCRIPTION     
            "Maximum sensor reading. (Use 'Read Sensor' action.)"
    ::= { pthwmonThresholdSensorEntry 8 }

pthwmonThresholdSensorMinimumReading OBJECT-TYPE
    SYNTAX          DisplayString (SIZE(0..255))
    MAX-ACCESS      read-only
    STATUS          current
    DESCRIPTION     
            "Minimum sensor reading. (Use 'Read Sensor' action.)"
    ::= { pthwmonThresholdSensorEntry 9 }

pthwmonThresholdSensorUpperCriticalThresh OBJECT-TYPE
    SYNTAX          DisplayString (SIZE(0..255))
    MAX-ACCESS      read-only
    STATUS          current
    DESCRIPTION     
            "Upper critical threshold sensor reading. (Use 'Read Sensor' action.)"
    ::= { pthwmonThresholdSensorEntry 10 }

pthwmonThresholdSensorUpperMajorThresh OBJECT-TYPE
    SYNTAX          DisplayString (SIZE(0..255))
    MAX-ACCESS      read-only
    STATUS          current
    DESCRIPTION     
            "Upper major threshold sensor reading. (Use 'Read Sensor' action.)"
    ::= { pthwmonThresholdSensorEntry 11 }

pthwmonThresholdSensorUpperMinorThresh OBJECT-TYPE
    SYNTAX          DisplayString (SIZE(0..255))
    MAX-ACCESS      read-only
    STATUS          current
    DESCRIPTION     
            "Upper minor threshold sensor reading. (Use 'Read Sensor' action.)"
    ::= { pthwmonThresholdSensorEntry 12 }

pthwmonThresholdSensorLowerMinorThresh OBJECT-TYPE
    SYNTAX          DisplayString (SIZE(0..255))
    MAX-ACCESS      read-only
    STATUS          current
    DESCRIPTION     
            "Lower minor threshold sensor reading. (Use 'Read Sensor' action.)"
    ::= { pthwmonThresholdSensorEntry 13 }

pthwmonThresholdSensorLowerMajorThresh OBJECT-TYPE
    SYNTAX          DisplayString (SIZE(0..255))
    MAX-ACCESS      read-only
    STATUS          current
    DESCRIPTION     
            "Lower major threshold sensor reading. (Use 'Read Sensor' action.)"
    ::= { pthwmonThresholdSensorEntry 14 }

pthwmonThresholdSensorLowerCriticalThresh OBJECT-TYPE
    SYNTAX          DisplayString (SIZE(0..255))
    MAX-ACCESS      read-only
    STATUS          current
    DESCRIPTION     
            "Lower critical threshold sensor reading. (Use 'Read Sensor' action.)"
    ::= { pthwmonThresholdSensorEntry 15 }

pthwmonThresholdSensorHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonThresholdSensorEntry 242 }

pthwmonThresholdSensorSlotIndex OBJECT-TYPE
    SYNTAX          Integer32 (-2147483648..2147483647)
    MAX-ACCESS      not-accessible
    STATUS          current
    DESCRIPTION     
            "This is the index of the parent type for this object.
             This parent type is Slot."
    ::= { pthwmonThresholdSensorEntry 243 }

pthwmonThresholdSensorActions OBJECT-TYPE
    SYNTAX          INTEGER { readSensor(1) }
    MAX-ACCESS      read-create
    STATUS          current
    DESCRIPTION     
            "The OID of all possible actions for this instance"
    ::= { pthwmonThresholdSensorEntry 252 }

pthwmonThresholdSensorParentOID OBJECT-TYPE
    SYNTAX          OBJECT IDENTIFIER
    MAX-ACCESS      read-create
    STATUS          current
    DESCRIPTION     
            "The OID of the parent object for this instance"
    ::= { pthwmonThresholdSensorEntry 253 }

pthwmonThresholdSensorRowStatus OBJECT-TYPE
    SYNTAX          RowStatus
    MAX-ACCESS      read-create
    STATUS          current
    DESCRIPTION     
            "The row status for the hwmonThresholdSensor table"
    ::= { pthwmonThresholdSensorEntry 254 }

pthwmonThresholdSensorIndex OBJECT-TYPE
    SYNTAX          Integer32 (-2147483648..2147483647)
    MAX-ACCESS      not-accessible
    STATUS          current
    DESCRIPTION     
            "The row number for the hwmonThresholdSensor table"
    ::= { pthwmonThresholdSensorEntry 255 }

pthwmonPowerSupply OBJECT IDENTIFIER
    ::= { pthwmonSlot 1175 }

pthwmonPowerSupplyTable OBJECT-TYPE
    SYNTAX          SEQUENCE OF PthwmonPowerSupplyEntry
    MAX-ACCESS      not-accessible
    STATUS          current
    DESCRIPTION     
            "No description supplied in the proxy config file."
    ::= { pthwmonPowerSupply 1 }

pthwmonPowerSupplyEntry OBJECT-TYPE
    SYNTAX          PthwmonPowerSupplyEntry
    MAX-ACCESS      not-accessible
    STATUS          current
    DESCRIPTION     
            "A sequence of hwmonPowerSupply attributes."
    INDEX           { ptConnGroupIndex, 
                      pthwmonPowerSupplyHardwareMonitorIndex, 
                      pthwmonPowerSupplySlotIndex, 
                      pthwmonPowerSupplyIndex }
    ::= { pthwmonPowerSupplyTable 1 }

PthwmonPowerSupplyEntry ::=
    SEQUENCE {
        pthwmonPowerSupplyPowerSupplyID Integer32,
        pthwmonPowerSupplyProductManufacturer     DisplayString,
        pthwmonPowerSupplyProductName   DisplayString,
        pthwmonPowerSupplyProductModelNumber    DisplayString,
        pthwmonPowerSupplyProductVersion DisplayString,
        pthwmonPowerSupplyProductSerialNumber     DisplayString,
        pthwmonPowerSupplyProductFRUFileID  DisplayString,
        pthwmonPowerSupplyBoardManufactureDate      DisplayString,
        pthwmonPowerSupplyBoardPartNumber DisplayString,
        pthwmonPowerSupplyMMCFirmwareVersion    DisplayString,
        pthwmonPowerSupplyHardwareMonitorIndex      Integer32,
        pthwmonPowerSupplySlotIndex     Integer32,
        pthwmonPowerSupplyParentOID     OBJECT IDENTIFIER,
        pthwmonPowerSupplyRowStatus     RowStatus,
        pthwmonPowerSupplyIndex         Integer32
    }

pthwmonPowerSupplyPowerSupplyID OBJECT-TYPE
    SYNTAX          Integer32 (-2147483648..2147483647)
    MAX-ACCESS      read-only
    STATUS          current
    DESCRIPTION     
            "Power Supply ID."
    ::= { pthwmonPowerSupplyEntry 1 }

pthwmonPowerSupplyProductManufacturer OBJECT-TYPE
    SYNTAX          DisplayString (SIZE(0..255))
    MAX-ACCESS      read-only
    STATUS          current
    DESCRIPTION     
            "Manufacturer of the product."
    ::= { pthwmonPowerSupplyEntry 2 }

pthwmonPowerSupplyProductName OBJECT-TYPE
    SYNTAX          DisplayString (SIZE(0..255))
    MAX-ACCESS      read-only
    STATUS          current
    DESCRIPTION     
            "Name of the product."
    ::= { pthwmonPowerSupplyEntry 3 }

pthwmonPowerSupplyProductModelNumber OBJECT-TYPE
    SYNTAX          DisplayString (SIZE(0..255))
    MAX-ACCESS      read-only
    STATUS          current
    DESCRIPTION     
            "Model number of the product."
    ::= { pthwmonPowerSupplyEntry 4 }

pthwmonPowerSupplyProductVersion OBJECT-TYPE
    SYNTAX          DisplayString (SIZE(0..255))
    MAX-ACCESS      read-only
    STATUS          current
    DESCRIPTION     
            "Version of the product."
    ::= { pthwmonPowerSupplyEntry 5 }

pthwmonPowerSupplyProductSerialNumber OBJECT-TYPE
    SYNTAX          DisplayString (SIZE(0..255))
    MAX-ACCESS      read-only
    STATUS          current
    DESCRIPTION     
            "Serial number of the product."
    ::= { pthwmonPowerSupplyEntry 6 }

pthwmonPowerSupplyProductFRUFileID OBJECT-TYPE
    SYNTAX          DisplayString (SIZE(0..255))
    MAX-ACCESS      read-only
    STATUS          current
    DESCRIPTION     
            "FRU file ID of the product."
    ::= { pthwmonPowerSupplyEntry 7 }

pthwmonPowerSupplyBoardManufactureDate OBJECT-TYPE
    SYNTAX          DisplayString (SIZE(0..255))
    MAX-ACCESS      read-only
    STATUS          current
    DESCRIPTION     
            "Manufacture date of the board."
    ::= { pthwmonPowerSupplyEntry 8 }

pthwmonPowerSupplyBoardPartNumber OBJECT-TYPE
    SYNTAX          DisplayString (SIZE(0..255))
    MAX-ACCESS      read-only
    STATUS          current
    DESCRIPTION     
            "Part number of the board."
    ::= { pthwmonPowerSupplyEntry 9 }

pthwmonPowerSupplyMMCFirmwareVersion OBJECT-TYPE
    SYNTAX          DisplayString (SIZE(0..255))
    MAX-ACCESS      read-only
    STATUS          current
    DESCRIPTION     
            "MMC or MCMC Firmware Version."
    ::= { pthwmonPowerSupplyEntry 10 }

pthwmonPowerSupplyHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonPowerSupplyEntry 242 }

pthwmonPowerSupplySlotIndex OBJECT-TYPE
    SYNTAX          Integer32 (-2147483648..2147483647)
    MAX-ACCESS      not-accessible
    STATUS          current
    DESCRIPTION     
            "This is the index of the parent type for this object.
             This parent type is Slot."
    ::= { pthwmonPowerSupplyEntry 243 }

pthwmonPowerSupplyParentOID OBJECT-TYPE
    SYNTAX          OBJECT IDENTIFIER
    MAX-ACCESS      read-create
    STATUS          current
    DESCRIPTION     
            "The OID of the parent object for this instance"
    ::= { pthwmonPowerSupplyEntry 253 }

pthwmonPowerSupplyRowStatus OBJECT-TYPE
    SYNTAX          RowStatus
    MAX-ACCESS      read-create
    STATUS          current
    DESCRIPTION     
            "The row status for the hwmonPowerSupply table"
    ::= { pthwmonPowerSupplyEntry 254 }

pthwmonPowerSupplyIndex OBJECT-TYPE
    SYNTAX          Integer32 (-2147483648..2147483647)
    MAX-ACCESS      not-accessible
    STATUS          current
    DESCRIPTION     
            "The row number for the hwmonPowerSupply table"
    ::= { pthwmonPowerSupplyEntry 255 }

pthwmonFanTray OBJECT IDENTIFIER
    ::= { pthwmonSlot 1176 }

pthwmonFanTrayTable OBJECT-TYPE
    SYNTAX          SEQUENCE OF PthwmonFanTrayEntry
    MAX-ACCESS      not-accessible
    STATUS          current
    DESCRIPTION     
            "No description supplied in the proxy config file."
    ::= { pthwmonFanTray 1 }

pthwmonFanTrayEntry OBJECT-TYPE
    SYNTAX          PthwmonFanTrayEntry
    MAX-ACCESS      not-accessible
    STATUS          current
    DESCRIPTION     
            "A sequence of hwmonFanTray attributes."
    INDEX           { ptConnGroupIndex, 
                      pthwmonFanTrayHardwareMonitorIndex, 
                      pthwmonFanTraySlotIndex, pthwmonFanTrayIndex }
    ::= { pthwmonFanTrayTable 1 }

PthwmonFanTrayEntry ::=
    SEQUENCE {
        pthwmonFanTrayFanTrayID         Integer32,
        pthwmonFanTrayProductManufacturer DisplayString,
        pthwmonFanTrayProductName       DisplayString,
        pthwmonFanTrayProductModelNumber DisplayString,
        pthwmonFanTrayProductVersion    DisplayString,
        pthwmonFanTrayProductSerialNumber DisplayString,
        pthwmonFanTrayProductFRUFileID  DisplayString,
        pthwmonFanTrayBoardManufactureDate  DisplayString,
        pthwmonFanTrayBoardPartNumber   DisplayString,
        pthwmonFanTrayMMCFirmwareVersion DisplayString,
        pthwmonFanTrayHardwareMonitorIndex  Integer32,
        pthwmonFanTraySlotIndex         Integer32,
        pthwmonFanTrayParentOID         OBJECT IDENTIFIER,
        pthwmonFanTrayRowStatus         RowStatus,
        pthwmonFanTrayIndex             Integer32
    }

pthwmonFanTrayFanTrayID OBJECT-TYPE
    SYNTAX          Integer32 (-2147483648..2147483647)
    MAX-ACCESS      read-only
    STATUS          current
    DESCRIPTION     
            "Fan Tray ID."
    ::= { pthwmonFanTrayEntry 1 }

pthwmonFanTrayProductManufacturer OBJECT-TYPE
    SYNTAX          DisplayString (SIZE(0..255))
    MAX-ACCESS      read-only
    STATUS          current
    DESCRIPTION     
            "Manufacturer of the product."
    ::= { pthwmonFanTrayEntry 2 }

pthwmonFanTrayProductName OBJECT-TYPE
    SYNTAX          DisplayString (SIZE(0..255))
    MAX-ACCESS      read-only
    STATUS          current
    DESCRIPTION     
            "Name of the product."
    ::= { pthwmonFanTrayEntry 3 }

pthwmonFanTrayProductModelNumber OBJECT-TYPE
    SYNTAX          DisplayString (SIZE(0..255))
    MAX-ACCESS      read-only
    STATUS          current
    DESCRIPTION     
            "Model number of the product."
    ::= { pthwmonFanTrayEntry 4 }

pthwmonFanTrayProductVersion OBJECT-TYPE
    SYNTAX          DisplayString (SIZE(0..255))
    MAX-ACCESS      read-only
    STATUS          current
    DESCRIPTION     
            "Version of the product."
    ::= { pthwmonFanTrayEntry 5 }

pthwmonFanTrayProductSerialNumber OBJECT-TYPE
    SYNTAX          DisplayString (SIZE(0..255))
    MAX-ACCESS      read-only
    STATUS          current
    DESCRIPTION     
            "Serial number of the product."
    ::= { pthwmonFanTrayEntry 6 }

pthwmonFanTrayProductFRUFileID OBJECT-TYPE
    SYNTAX          DisplayString (SIZE(0..255))
    MAX-ACCESS      read-only
    STATUS          current
    DESCRIPTION     
            "FRU file ID of the product."
    ::= { pthwmonFanTrayEntry 7 }

pthwmonFanTrayBoardManufactureDate OBJECT-TYPE
    SYNTAX          DisplayString (SIZE(0..255))
    MAX-ACCESS      read-only
    STATUS          current
    DESCRIPTION     
            "Manufacture date of the board."
    ::= { pthwmonFanTrayEntry 8 }

pthwmonFanTrayBoardPartNumber OBJECT-TYPE
    SYNTAX          DisplayString (SIZE(0..255))
    MAX-ACCESS      read-only
    STATUS          current
    DESCRIPTION     
            "Part number of the board."
    ::= { pthwmonFanTrayEntry 9 }

pthwmonFanTrayMMCFirmwareVersion OBJECT-TYPE
    SYNTAX          DisplayString (SIZE(0..255))
    MAX-ACCESS      read-only
    STATUS          current
    DESCRIPTION     
            "MMC or MCMC Firmware Version."
    ::= { pthwmonFanTrayEntry 10 }

pthwmonFanTrayHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonFanTrayEntry 242 }

pthwmonFanTraySlotIndex OBJECT-TYPE
    SYNTAX          Integer32 (-2147483648..2147483647)
    MAX-ACCESS      not-accessible
    STATUS          current
    DESCRIPTION     
            "This is the index of the parent type for this object.
             This parent type is Slot."
    ::= { pthwmonFanTrayEntry 243 }

pthwmonFanTrayParentOID OBJECT-TYPE
    SYNTAX          OBJECT IDENTIFIER
    MAX-ACCESS      read-create
    STATUS          current
    DESCRIPTION     
            "The OID of the parent object for this instance"
    ::= { pthwmonFanTrayEntry 253 }

pthwmonFanTrayRowStatus OBJECT-TYPE
    SYNTAX          RowStatus
    MAX-ACCESS      read-create
    STATUS          current
    DESCRIPTION     
            "The row status for the hwmonFanTray table"
    ::= { pthwmonFanTrayEntry 254 }

pthwmonFanTrayIndex OBJECT-TYPE
    SYNTAX          Integer32 (-2147483648..2147483647)
    MAX-ACCESS      not-accessible
    STATUS          current
    DESCRIPTION     
            "The row number for the hwmonFanTray table"
    ::= { pthwmonFanTrayEntry 255 }

pthwmonShelf OBJECT IDENTIFIER
    ::= { pthwmonSlot 1177 }

pthwmonShelfTable OBJECT-TYPE
    SYNTAX          SEQUENCE OF PthwmonShelfEntry
    MAX-ACCESS      not-accessible
    STATUS          current
    DESCRIPTION     
            "No description supplied in the proxy config file."
    ::= { pthwmonShelf 1 }

pthwmonShelfEntry OBJECT-TYPE
    SYNTAX          PthwmonShelfEntry
    MAX-ACCESS      not-accessible
    STATUS          current
    DESCRIPTION     
            "A sequence of hwmonShelf attributes."
    INDEX           { ptConnGroupIndex, pthwmonShelfHardwareMonitorIndex, 
                      pthwmonShelfSlotIndex, pthwmonShelfIndex }
    ::= { pthwmonShelfTable 1 }

PthwmonShelfEntry ::=
    SEQUENCE {
        pthwmonShelfShelfID             Integer32,
        pthwmonShelfBoardManufactureDate DisplayString,
        pthwmonShelfBoardPartNumber     DisplayString,
        pthwmonShelfProductManufacturer DisplayString,
        pthwmonShelfProductName         DisplayString,
        pthwmonShelfProductModelNumber  DisplayString,
        pthwmonShelfProductVersion      DisplayString,
        pthwmonShelfProductSerialNumber DisplayString,
        pthwmonShelfHardwareMonitorIndex Integer32,
        pthwmonShelfSlotIndex           Integer32,
        pthwmonShelfParentOID           OBJECT IDENTIFIER,
        pthwmonShelfRowStatus           RowStatus,
        pthwmonShelfIndex               Integer32
    }

pthwmonShelfShelfID OBJECT-TYPE
    SYNTAX          Integer32 (-2147483648..2147483647)
    MAX-ACCESS      read-only
    STATUS          current
    DESCRIPTION     
            "Shelf ID."
    ::= { pthwmonShelfEntry 1 }

pthwmonShelfBoardManufactureDate OBJECT-TYPE
    SYNTAX          DisplayString (SIZE(0..255))
    MAX-ACCESS      read-only
    STATUS          current
    DESCRIPTION     
            "Manufacturing Date of the product."
    ::= { pthwmonShelfEntry 2 }

pthwmonShelfBoardPartNumber OBJECT-TYPE
    SYNTAX          DisplayString (SIZE(0..255))
    MAX-ACCESS      read-only
    STATUS          current
    DESCRIPTION     
            "Part number of the shelf backplane."
    ::= { pthwmonShelfEntry 3 }

pthwmonShelfProductManufacturer OBJECT-TYPE
    SYNTAX          DisplayString (SIZE(0..255))
    MAX-ACCESS      read-only
    STATUS          current
    DESCRIPTION     
            "Manufacturer of the product."
    ::= { pthwmonShelfEntry 4 }

pthwmonShelfProductName OBJECT-TYPE
    SYNTAX          DisplayString (SIZE(0..255))
    MAX-ACCESS      read-only
    STATUS          current
    DESCRIPTION     
            "Name of the product."
    ::= { pthwmonShelfEntry 5 }

pthwmonShelfProductModelNumber OBJECT-TYPE
    SYNTAX          DisplayString (SIZE(0..255))
    MAX-ACCESS      read-only
    STATUS          current
    DESCRIPTION     
            "Model number of the product."
    ::= { pthwmonShelfEntry 6 }

pthwmonShelfProductVersion OBJECT-TYPE
    SYNTAX          DisplayString (SIZE(0..255))
    MAX-ACCESS      read-only
    STATUS          current
    DESCRIPTION     
            "Version of the product."
    ::= { pthwmonShelfEntry 7 }

pthwmonShelfProductSerialNumber OBJECT-TYPE
    SYNTAX          DisplayString (SIZE(0..255))
    MAX-ACCESS      read-only
    STATUS          current
    DESCRIPTION     
            "Serial number of the product."
    ::= { pthwmonShelfEntry 8 }

pthwmonShelfHardwareMonitorIndex OBJECT-TYPE
    SYNTAX          Integer32 (-2147483648..2147483647)
    MAX-ACCESS      not-accessible
    STATUS          current
    DESCRIPTION     
            "This is the index of the parent type for this object.
             This parent type is HardwareMonitor."
    ::= { pthwmonShelfEntry 242 }

pthwmonShelfSlotIndex OBJECT-TYPE
    SYNTAX          Integer32 (-2147483648..2147483647)
    MAX-ACCESS      not-accessible
    STATUS          current
    DESCRIPTION     
            "This is the index of the parent type for this object.
             This parent type is Slot."
    ::= { pthwmonShelfEntry 243 }

pthwmonShelfParentOID OBJECT-TYPE
    SYNTAX          OBJECT IDENTIFIER
    MAX-ACCESS      read-create
    STATUS          current
    DESCRIPTION     
            "The OID of the parent object for this instance"
    ::= { pthwmonShelfEntry 253 }

pthwmonShelfRowStatus OBJECT-TYPE
    SYNTAX          RowStatus
    MAX-ACCESS      read-create
    STATUS          current
    DESCRIPTION     
            "The row status for the hwmonShelf table"
    ::= { pthwmonShelfEntry 254 }

pthwmonShelfIndex OBJECT-TYPE
    SYNTAX          Integer32 (-2147483648..2147483647)
    MAX-ACCESS      not-accessible
    STATUS          current
    DESCRIPTION     
            "The row number for the hwmonShelf table"
    ::= { pthwmonShelfEntry 255 }

ptSWMSwitchMonitor OBJECT IDENTIFIER
    ::= { ptConnGroup 1181 }

ptSWMSwitchMonitorTable OBJECT-TYPE
    SYNTAX          SEQUENCE OF PtSWMSwitchMonitorEntry
    MAX-ACCESS      not-accessible
    STATUS          current
    DESCRIPTION     
            "No description supplied in the proxy config file."
    ::= { ptSWMSwitchMonitor 1 }

ptSWMSwitchMonitorEntry OBJECT-TYPE
    SYNTAX          PtSWMSwitchMonitorEntry
    MAX-ACCESS      not-accessible
    STATUS          current
    DESCRIPTION     
            "A sequence of SWMSwitchMonitor attributes."
    INDEX           { ptConnGroupIndex, ptSWMSwitchMonitorIndex }
    ::= { ptSWMSwitchMonitorTable 1 }

PtSWMSwitchMonitorEntry ::=
    SEQUENCE {
        ptSWMSwitchMonitorErrors        INTEGER,
        ptSWMSwitchMonitorSetupManagement INTEGER,
        ptSWMSwitchMonitorExecutionTrace INTEGER,
        ptSWMSwitchMonitorPeerManagement INTEGER,
        ptSWMSwitchMonitorActions       INTEGER,
        ptSWMSwitchMonitorParentOID     OBJECT IDENTIFIER,
        ptSWMSwitchMonitorRowStatus     RowStatus,
        ptSWMSwitchMonitorIndex         Integer32
    }

ptSWMSwitchMonitorErrors OBJECT-TYPE
    SYNTAX          INTEGER { notLogged(0), logged(1) }
    MAX-ACCESS      read-create
    STATUS          current
    DESCRIPTION     
            "Enable or disable debug logging of the Switch Monitor errors; \nshould be logged for production systems."
    ::= { ptSWMSwitchMonitorEntry 22 }

ptSWMSwitchMonitorSetupManagement OBJECT-TYPE
    SYNTAX          INTEGER { notLogged(0), logged(1) }
    MAX-ACCESS      read-create
    STATUS          current
    DESCRIPTION     
            "Enable or disable debug logging of setup management; \nshould be logged for production systems."
    ::= { ptSWMSwitchMonitorEntry 23 }

ptSWMSwitchMonitorExecutionTrace OBJECT-TYPE
    SYNTAX          INTEGER { notLogged(0), logged(1) }
    MAX-ACCESS      read-create
    STATUS          current
    DESCRIPTION     
            "Enable or disable debug logging of the execution trace; \nmust not be logged for production systems."
    ::= { ptSWMSwitchMonitorEntry 24 }

ptSWMSwitchMonitorPeerManagement OBJECT-TYPE
    SYNTAX          INTEGER { notLogged(0), logged(1) }
    MAX-ACCESS      read-create
    STATUS          current
    DESCRIPTION     
            "Enable or disable debug logging of peer management; \nmust not be logged for production systems."
    ::= { ptSWMSwitchMonitorEntry 25 }

ptSWMSwitchMonitorActions OBJECT-TYPE
    SYNTAX          INTEGER { restoreDebugDefaults(1) }
    MAX-ACCESS      read-create
    STATUS          current
    DESCRIPTION     
            "The OID of all possible actions for this instance"
    ::= { ptSWMSwitchMonitorEntry 252 }

ptSWMSwitchMonitorParentOID OBJECT-TYPE
    SYNTAX          OBJECT IDENTIFIER
    MAX-ACCESS      read-create
    STATUS          current
    DESCRIPTION     
            "The OID of the parent object for this instance"
    ::= { ptSWMSwitchMonitorEntry 253 }

ptSWMSwitchMonitorRowStatus OBJECT-TYPE
    SYNTAX          RowStatus
    MAX-ACCESS      read-create
    STATUS          current
    DESCRIPTION     
            "The row status for the SWMSwitchMonitor table"
    ::= { ptSWMSwitchMonitorEntry 254 }

ptSWMSwitchMonitorIndex OBJECT-TYPE
    SYNTAX          Integer32 (-2147483648..2147483647)
    MAX-ACCESS      not-accessible
    STATUS          current
    DESCRIPTION     
            "The row number for the SWMSwitchMonitor table"
    ::= { ptSWMSwitchMonitorEntry 255 }

ptSWMSwitches OBJECT IDENTIFIER
    ::= { ptConnGroup 1182 }

ptSWMSwitchesTable OBJECT-TYPE
    SYNTAX          SEQUENCE OF PtSWMSwitchesEntry
    MAX-ACCESS      not-accessible
    STATUS          current
    DESCRIPTION     
            "No description supplied in the proxy config file."
    ::= { ptSWMSwitches 1 }

ptSWMSwitchesEntry OBJECT-TYPE
    SYNTAX          PtSWMSwitchesEntry
    MAX-ACCESS      not-accessible
    STATUS          current
    DESCRIPTION     
            "A sequence of SWMSwitches attributes."
    INDEX           { ptConnGroupIndex, ptSWMSwitchesIndex }
    ::= { ptSWMSwitchesTable 1 }

PtSWMSwitchesEntry ::=
    SEQUENCE {
        ptSWMSwitchesCount              Integer32,
        ptSWMSwitchesParentOID          OBJECT IDENTIFIER,
        ptSWMSwitchesRowStatus          RowStatus,
        ptSWMSwitchesIndex              Integer32
    }

ptSWMSwitchesCount OBJECT-TYPE
    SYNTAX          Integer32 (-2147483648..2147483647)
    MAX-ACCESS      read-only
    STATUS          current
    DESCRIPTION     
            "Number of switches that must be detected in the chassis."
    ::= { ptSWMSwitchesEntry 1 }

ptSWMSwitchesParentOID OBJECT-TYPE
    SYNTAX          OBJECT IDENTIFIER
    MAX-ACCESS      read-create
    STATUS          current
    DESCRIPTION     
            "The OID of the parent object for this instance"
    ::= { ptSWMSwitchesEntry 253 }

ptSWMSwitchesRowStatus OBJECT-TYPE
    SYNTAX          RowStatus
    MAX-ACCESS      read-create
    STATUS          current
    DESCRIPTION     
            "The row status for the SWMSwitches table"
    ::= { ptSWMSwitchesEntry 254 }

ptSWMSwitchesIndex OBJECT-TYPE
    SYNTAX          Integer32 (-2147483648..2147483647)
    MAX-ACCESS      not-accessible
    STATUS          current
    DESCRIPTION     
            "The row number for the SWMSwitches table"
    ::= { ptSWMSwitchesEntry 255 }

ptSWMSwitch OBJECT IDENTIFIER
    ::= { ptSWMSwitches 1183 }

ptSWMSwitchTable OBJECT-TYPE
    SYNTAX          SEQUENCE OF PtSWMSwitchEntry
    MAX-ACCESS      not-accessible
    STATUS          current
    DESCRIPTION     
            "No description supplied in the proxy config file."
    ::= { ptSWMSwitch 1 }

ptSWMSwitchEntry OBJECT-TYPE
    SYNTAX          PtSWMSwitchEntry
    MAX-ACCESS      not-accessible
    STATUS          current
    DESCRIPTION     
            "A sequence of SWMSwitch attributes."
    INDEX           { ptConnGroupIndex, ptSWMSwitchSwitchesIndex, 
                      ptSWMSwitchIndex }
    ::= { ptSWMSwitchTable 1 }

PtSWMSwitchEntry ::=
    SEQUENCE {
        ptSWMSwitchSlotNumber           Integer32,
        ptSWMSwitchType                 INTEGER,
        ptSWMSwitchIPAddress            DisplayString,
        ptSWMSwitchSlotStatus           INTEGER,
        ptSWMSwitchSwitchSyncStatus     INTEGER,
        ptSWMSwitchSwitchIntegrityStatus INTEGER,
        ptSWMSwitchSwitchesIndex        Integer32,
        ptSWMSwitchParentOID            OBJECT IDENTIFIER,
        ptSWMSwitchRowStatus            RowStatus,
        ptSWMSwitchIndex                Integer32
    }

ptSWMSwitchSlotNumber OBJECT-TYPE
    SYNTAX          Integer32 (-2147483648..2147483647)
    MAX-ACCESS      read-only
    STATUS          current
    DESCRIPTION     
            "Physical slot location of the switch board."
    ::= { ptSWMSwitchEntry 1 }

ptSWMSwitchType OBJECT-TYPE
    SYNTAX          INTEGER { unknown(0), cpc4416(1), cpc6600(2), 
                        cpc6620(3), amc671(4), mez10gbe(5) }
    MAX-ACCESS      read-only
    STATUS          current
    DESCRIPTION     
            "Name of the switch board detected. The switch type could be a CPC4416, CPC6600, CPC6620, AMC671, MEZ10GBE or UNKNOWN. readonly field"
    ::= { ptSWMSwitchEntry 2 }

ptSWMSwitchIPAddress OBJECT-TYPE
    SYNTAX          DisplayString (SIZE(0..255))
    MAX-ACCESS      read-only
    STATUS          current
    DESCRIPTION     
            "IP Address of the switch board detected."
    ::= { ptSWMSwitchEntry 3 }

ptSWMSwitchSlotStatus OBJECT-TYPE
    SYNTAX          INTEGER { querying(0), extracted(1), available(2), 
                        pendingExtractionRequest(3), 
                        readyToBeExtracted(4), lostConnection(5) }
    MAX-ACCESS      read-only
    STATUS          current
    DESCRIPTION     
            "Current status for this slot. Can be one of the following states; AVAILABLE: slot is communicating normally. UNKNOWN_STATE: slot is not present. LOST_CONNECTION: Switch Monitor has lost connection to this slot."
    ::= { ptSWMSwitchEntry 4 }

ptSWMSwitchSwitchSyncStatus OBJECT-TYPE
    SYNTAX          INTEGER { down(0), up(1), unknown(2) }
    MAX-ACCESS      read-only
    STATUS          current
    DESCRIPTION     
            "Current status of the Switch Sync Interface for this slot. Can be one of the following states; UP: interface is communicating normally. DOWN: interface is down for this slot. UNKNOWN: interface is unknown or not applicable for this slot."
    ::= { ptSWMSwitchEntry 5 }

ptSWMSwitchSwitchIntegrityStatus OBJECT-TYPE
    SYNTAX          INTEGER { passed(0), failed(1), unknown(2) }
    MAX-ACCESS      read-only
    STATUS          current
    DESCRIPTION     
            "Current status of the Switch Integrity for this slot. Can be one of the following states; PASSED: switch integrity tests Passed. FAILED: switch integrity tests failed for this slot. UNKNOWN: integrity status is unknown for this slot."
    ::= { ptSWMSwitchEntry 6 }

ptSWMSwitchSwitchesIndex OBJECT-TYPE
    SYNTAX          Integer32 (-2147483648..2147483647)
    MAX-ACCESS      not-accessible
    STATUS          current
    DESCRIPTION     
            "This is the index of the parent type for this object.
             This parent type is Switches."
    ::= { ptSWMSwitchEntry 242 }

ptSWMSwitchParentOID OBJECT-TYPE
    SYNTAX          OBJECT IDENTIFIER
    MAX-ACCESS      read-create
    STATUS          current
    DESCRIPTION     
            "The OID of the parent object for this instance"
    ::= { ptSWMSwitchEntry 253 }

ptSWMSwitchRowStatus OBJECT-TYPE
    SYNTAX          RowStatus
    MAX-ACCESS      read-create
    STATUS          current
    DESCRIPTION     
            "The row status for the SWMSwitch table"
    ::= { ptSWMSwitchEntry 254 }

ptSWMSwitchIndex OBJECT-TYPE
    SYNTAX          Integer32 (-2147483648..2147483647)
    MAX-ACCESS      not-accessible
    STATUS          current
    DESCRIPTION     
            "The row number for the SWMSwitch table"
    ::= { ptSWMSwitchEntry 255 }

ptSWMExternalPort OBJECT IDENTIFIER
    ::= { ptSWMSwitch 1184 }

ptSWMExternalPortTable OBJECT-TYPE
    SYNTAX          SEQUENCE OF PtSWMExternalPortEntry
    MAX-ACCESS      not-accessible
    STATUS          current
    DESCRIPTION     
            "No description supplied in the proxy config file."
    ::= { ptSWMExternalPort 1 }

ptSWMExternalPortEntry OBJECT-TYPE
    SYNTAX          PtSWMExternalPortEntry
    MAX-ACCESS      not-accessible
    STATUS          current
    DESCRIPTION     
            "A sequence of SWMExternalPort attributes."
    INDEX           { ptConnGroupIndex, ptSWMExternalPortSwitchesIndex, 
                      ptSWMExternalPortSwitchIndex, 
                      ptSWMExternalPortIndex }
    ::= { ptSWMExternalPortTable 1 }

PtSWMExternalPortEntry ::=
    SEQUENCE {
        ptSWMExternalPortSlotNumber     Integer32,
        ptSWMExternalPortPortNumber     Integer32,
        ptSWMExternalPortState          INTEGER,
        ptSWMExternalPortNotification   INTEGER,
        ptSWMExternalPortPortName       DisplayString,
        ptSWMExternalPortSwitchesIndex  Integer32,
        ptSWMExternalPortSwitchIndex    Integer32,
        ptSWMExternalPortParentOID      OBJECT IDENTIFIER,
        ptSWMExternalPortRowStatus      RowStatus,
        ptSWMExternalPortIndex          Integer32
    }

ptSWMExternalPortSlotNumber OBJECT-TYPE
    SYNTAX          Integer32 (-2147483648..2147483647)
    MAX-ACCESS      read-only
    STATUS          current
    DESCRIPTION     
            "Slot number of the switch board."
    ::= { ptSWMExternalPortEntry 1 }

ptSWMExternalPortPortNumber OBJECT-TYPE
    SYNTAX          Integer32 (-2147483648..2147483647)
    MAX-ACCESS      read-only
    STATUS          current
    DESCRIPTION     
            "This value corresponds to the number of the port on the switch."
    ::= { ptSWMExternalPortEntry 2 }

ptSWMExternalPortState OBJECT-TYPE
    SYNTAX          INTEGER { querying(0), extracted(1), available(2), 
                        pendingExtractionRequest(3), 
                        readyToBeExtracted(4), lostConnection(5) }
    MAX-ACCESS      read-only
    STATUS          current
    DESCRIPTION     
            "Current status for this slot. Can be one of the following states; AVAILABLE: slot is communicating normally. UNKNOWN_STATE: slot is not present. LOST_CONNECTION: Switch Monitor has lost connection to this slot."
    ::= { ptSWMExternalPortEntry 3 }

ptSWMExternalPortNotification OBJECT-TYPE
    SYNTAX          INTEGER { disabled(0), enabled(1) }
    MAX-ACCESS      read-create
    STATUS          current
    DESCRIPTION     
            "Specifies if notifications are to be created on port up/down or not. DISABLED: Events are not created for this port ENABLED: Events are created for this port."
    ::= { ptSWMExternalPortEntry 4 }

ptSWMExternalPortPortName OBJECT-TYPE
    SYNTAX          DisplayString (SIZE(0..255))
    MAX-ACCESS      read-only
    STATUS          current
    DESCRIPTION     
            "The name of the port contains the value seen on the faceplate that corresponds to this port."
    ::= { ptSWMExternalPortEntry 5 }

ptSWMExternalPortSwitchesIndex OBJECT-TYPE
    SYNTAX          Integer32 (-2147483648..2147483647)
    MAX-ACCESS      not-accessible
    STATUS          current
    DESCRIPTION     
            "This is the index of the parent type for this object.
             This parent type is Switches."
    ::= { ptSWMExternalPortEntry 242 }

ptSWMExternalPortSwitchIndex OBJECT-TYPE
    SYNTAX          Integer32 (-2147483648..2147483647)
    MAX-ACCESS      not-accessible
    STATUS          current
    DESCRIPTION     
            "This is the index of the parent type for this object.
             This parent type is Switch."
    ::= { ptSWMExternalPortEntry 243 }

ptSWMExternalPortParentOID OBJECT-TYPE
    SYNTAX          OBJECT IDENTIFIER
    MAX-ACCESS      read-create
    STATUS          current
    DESCRIPTION     
            "The OID of the parent object for this instance"
    ::= { ptSWMExternalPortEntry 253 }

ptSWMExternalPortRowStatus OBJECT-TYPE
    SYNTAX          RowStatus
    MAX-ACCESS      read-create
    STATUS          current
    DESCRIPTION     
            "The row status for the SWMExternalPort table"
    ::= { ptSWMExternalPortEntry 254 }

ptSWMExternalPortIndex OBJECT-TYPE
    SYNTAX          Integer32 (-2147483648..2147483647)
    MAX-ACCESS      not-accessible
    STATUS          current
    DESCRIPTION     
            "The row number for the SWMExternalPort table"
    ::= { ptSWMExternalPortEntry 255 }

ptdscdbDSCDBConfiguration OBJECT IDENTIFIER
    ::= { ptConnGroup 1191 }

ptdscdbDSCDBConfigurationTable OBJECT-TYPE
    SYNTAX          SEQUENCE OF PtdscdbDSCDBConfigurationEntry
    MAX-ACCESS      not-accessible
    STATUS          current
    DESCRIPTION     
            "No description supplied in the proxy config file."
    ::= { ptdscdbDSCDBConfiguration 1 }

ptdscdbDSCDBConfigurationEntry OBJECT-TYPE
    SYNTAX          PtdscdbDSCDBConfigurationEntry
    MAX-ACCESS      not-accessible
    STATUS          current
    DESCRIPTION     
            "A sequence of dscdbDSCDBConfiguration attributes."
    INDEX           { ptConnGroupIndex, ptdscdbDSCDBConfigurationIndex }
    ::= { ptdscdbDSCDBConfigurationTable 1 }

PtdscdbDSCDBConfigurationEntry ::=
    SEQUENCE {
        ptdscdbDSCDBConfigurationTimeToLive   Integer32,
        ptdscdbDSCDBConfigurationGracePeriod    Integer32,
        ptdscdbDSCDBConfigurationLogSyncInterval        Integer32,
        ptdscdbDSCDBConfigurationReplicationFactor          Integer32,
        ptdscdbDSCDBConfigurationErrors INTEGER,
        ptdscdbDSCDBConfigurationSetupManagement        INTEGER,
        ptdscdbDSCDBConfigurationExecutionTrace       INTEGER,
        ptdscdbDSCDBConfigurationDistributionManagement               INTEGER,
        ptdscdbDSCDBConfigurationParentOID  OBJECT IDENTIFIER,
        ptdscdbDSCDBConfigurationRowStatus  RowStatus,
        ptdscdbDSCDBConfigurationIndex  Integer32
    }

ptdscdbDSCDBConfigurationTimeToLive OBJECT-TYPE
    SYNTAX          Integer32
    MAX-ACCESS      read-create
    STATUS          current
    DESCRIPTION     
            "Time-To-Live value given to newly inserted records into the database."
    ::= { ptdscdbDSCDBConfigurationEntry 1 }

ptdscdbDSCDBConfigurationGracePeriod OBJECT-TYPE
    SYNTAX          Integer32
    MAX-ACCESS      read-create
    STATUS          current
    DESCRIPTION     
            "Grace time a record is kept in DB after it is marked for deletion."
    ::= { ptdscdbDSCDBConfigurationEntry 2 }

ptdscdbDSCDBConfigurationLogSyncInterval OBJECT-TYPE
    SYNTAX          Integer32
    MAX-ACCESS      read-create
    STATUS          current
    DESCRIPTION     
            "Inverval time for how often records are synced to disk."
    ::= { ptdscdbDSCDBConfigurationEntry 3 }

ptdscdbDSCDBConfigurationReplicationFactor OBJECT-TYPE
    SYNTAX          Integer32
    MAX-ACCESS      read-create
    STATUS          current
    DESCRIPTION     
            "Number of Nodes among which data is replicated."
    ::= { ptdscdbDSCDBConfigurationEntry 4 }

ptdscdbDSCDBConfigurationErrors OBJECT-TYPE
    SYNTAX          INTEGER { notLogged(0), logged(1) }
    MAX-ACCESS      read-create
    STATUS          current
    DESCRIPTION     
            "If set to LOGGED, the system logs to debug all DB Agent errors. \nShould be set to LOGGED for live systems."
    ::= { ptdscdbDSCDBConfigurationEntry 5 }

ptdscdbDSCDBConfigurationSetupManagement OBJECT-TYPE
    SYNTAX          INTEGER { notLogged(0), logged(1) }
    MAX-ACCESS      read-create
    STATUS          current
    DESCRIPTION     
            "If set to LOGGED, the system logs to debug the DB Agent setup information. \nShould be set to LOGGED for live systems."
    ::= { ptdscdbDSCDBConfigurationEntry 6 }

ptdscdbDSCDBConfigurationExecutionTrace OBJECT-TYPE
    SYNTAX          INTEGER { notLogged(0), logged(1) }
    MAX-ACCESS      read-create
    STATUS          current
    DESCRIPTION     
            "If set to LOGGED, the system logs to debug the execution trace during the processing of incoming DB Agent traffic. \nMust be set to NOT LOGGED for live systems."
    ::= { ptdscdbDSCDBConfigurationEntry 7 }

ptdscdbDSCDBConfigurationDistributionManagement OBJECT-TYPE
    SYNTAX          INTEGER { notLogged(0), logged(1) }
    MAX-ACCESS      read-create
    STATUS          current
    DESCRIPTION     
            "If set to LOGGED, the system logs to debug the DB Agent distribution information. \nMust be set to NOT LOGGED for live systems."
    ::= { ptdscdbDSCDBConfigurationEntry 8 }

ptdscdbDSCDBConfigurationParentOID OBJECT-TYPE
    SYNTAX          OBJECT IDENTIFIER
    MAX-ACCESS      read-create
    STATUS          current
    DESCRIPTION     
            "The OID of the parent object for this instance"
    ::= { ptdscdbDSCDBConfigurationEntry 253 }

ptdscdbDSCDBConfigurationRowStatus OBJECT-TYPE
    SYNTAX          RowStatus
    MAX-ACCESS      read-create
    STATUS          current
    DESCRIPTION     
            "The row status for the dscdbDSCDBConfiguration table"
    ::= { ptdscdbDSCDBConfigurationEntry 254 }

ptdscdbDSCDBConfigurationIndex OBJECT-TYPE
    SYNTAX          Integer32 (-2147483648..2147483647)
    MAX-ACCESS      not-accessible
    STATUS          current
    DESCRIPTION     
            "The row number for the dscdbDSCDBConfiguration table"
    ::= { ptdscdbDSCDBConfigurationEntry 255 }

ptdscdbDBConnections OBJECT IDENTIFIER
    ::= { ptConnGroup 1192 }

ptdscdbDBConnectionsTable OBJECT-TYPE
    SYNTAX          SEQUENCE OF PtdscdbDBConnectionsEntry
    MAX-ACCESS      not-accessible
    STATUS          current
    DESCRIPTION     
            "No description supplied in the proxy config file."
    ::= { ptdscdbDBConnections 1 }

ptdscdbDBConnectionsEntry OBJECT-TYPE
    SYNTAX          PtdscdbDBConnectionsEntry
    MAX-ACCESS      not-accessible
    STATUS          current
    DESCRIPTION     
            "A sequence of dscdbDBConnections attributes."
    INDEX           { ptConnGroupIndex, ptdscdbDBConnectionsIndex }
    ::= { ptdscdbDBConnectionsTable 1 }

PtdscdbDBConnectionsEntry ::=
    SEQUENCE {
        ptdscdbDBConnectionsCount       Integer32,
        ptdscdbDBConnectionsParentOID   OBJECT IDENTIFIER,
        ptdscdbDBConnectionsRowStatus   RowStatus,
        ptdscdbDBConnectionsIndex       Integer32
    }

ptdscdbDBConnectionsCount OBJECT-TYPE
    SYNTAX          Integer32 (-2147483648..2147483647)
    MAX-ACCESS      read-only
    STATUS          current
    DESCRIPTION     
            "Number of DB Connections."
    ::= { ptdscdbDBConnectionsEntry 1 }

ptdscdbDBConnectionsParentOID OBJECT-TYPE
    SYNTAX          OBJECT IDENTIFIER
    MAX-ACCESS      read-create
    STATUS          current
    DESCRIPTION     
            "The OID of the parent object for this instance"
    ::= { ptdscdbDBConnectionsEntry 253 }

ptdscdbDBConnectionsRowStatus OBJECT-TYPE
    SYNTAX          RowStatus
    MAX-ACCESS      read-create
    STATUS          current
    DESCRIPTION     
            "The row status for the dscdbDBConnections table"
    ::= { ptdscdbDBConnectionsEntry 254 }

ptdscdbDBConnectionsIndex OBJECT-TYPE
    SYNTAX          Integer32 (-2147483648..2147483647)
    MAX-ACCESS      not-accessible
    STATUS          current
    DESCRIPTION     
            "The row number for the dscdbDBConnections table"
    ::= { ptdscdbDBConnectionsEntry 255 }

ptdscdbDBConnection OBJECT IDENTIFIER
    ::= { ptConnGroup 1193 }

ptdscdbDBConnectionTable OBJECT-TYPE
    SYNTAX          SEQUENCE OF PtdscdbDBConnectionEntry
    MAX-ACCESS      not-accessible
    STATUS          current
    DESCRIPTION     
            "No description supplied in the proxy config file."
    ::= { ptdscdbDBConnection 1 }

ptdscdbDBConnectionEntry OBJECT-TYPE
    SYNTAX          PtdscdbDBConnectionEntry
    MAX-ACCESS      not-accessible
    STATUS          current
    DESCRIPTION     
            "A sequence of dscdbDBConnection attributes."
    INDEX           { ptConnGroupIndex, ptdscdbDBConnectionIndex }
    ::= { ptdscdbDBConnectionTable 1 }

PtdscdbDBConnectionEntry ::=
    SEQUENCE {
        ptdscdbDBConnectionSlot         Integer32,
        ptdscdbDBConnectionConnectivityStatus     INTEGER,
        ptdscdbDBConnectionParentOID    OBJECT IDENTIFIER,
        ptdscdbDBConnectionRowStatus    RowStatus,
        ptdscdbDBConnectionIndex        Integer32
    }

ptdscdbDBConnectionSlot OBJECT-TYPE
    SYNTAX          Integer32 (-2147483648..2147483647)
    MAX-ACCESS      read-only
    STATUS          current
    DESCRIPTION     
            "Associated slot of the Application CPU for this DB connection."
    ::= { ptdscdbDBConnectionEntry 1 }

ptdscdbDBConnectionConnectivityStatus OBJECT-TYPE
    SYNTAX          INTEGER { notConnected(0), connected(1) }
    MAX-ACCESS      read-only
    STATUS          current
    DESCRIPTION     
            "DB connectivity status (NOT CONNECTED, CONNECTED). \nBased on the per slot connectivity status. CONNECTED will be displayed as soon as a DB Agent on a given slot is connected to the local DB. \nAssociated to alarm 1903 (DB Connection Down)."
    ::= { ptdscdbDBConnectionEntry 2 }

ptdscdbDBConnectionParentOID OBJECT-TYPE
    SYNTAX          OBJECT IDENTIFIER
    MAX-ACCESS      read-create
    STATUS          current
    DESCRIPTION     
            "The OID of the parent object for this instance"
    ::= { ptdscdbDBConnectionEntry 253 }

ptdscdbDBConnectionRowStatus OBJECT-TYPE
    SYNTAX          RowStatus
    MAX-ACCESS      read-create
    STATUS          current
    DESCRIPTION     
            "The row status for the dscdbDBConnection table"
    ::= { ptdscdbDBConnectionEntry 254 }

ptdscdbDBConnectionIndex OBJECT-TYPE
    SYNTAX          Integer32 (-2147483648..2147483647)
    MAX-ACCESS      not-accessible
    STATUS          current
    DESCRIPTION     
            "The row number for the dscdbDBConnection table"
    ::= { ptdscdbDBConnectionEntry 255 }

ptinapgwINAPGWConfiguration OBJECT IDENTIFIER
    ::= { ptConnGroup 1301 }

ptinapgwINAPGWConfigurationTable OBJECT-TYPE
    SYNTAX          SEQUENCE OF PtinapgwINAPGWConfigurationEntry
    MAX-ACCESS      not-accessible
    STATUS          current
    DESCRIPTION     
            "No description supplied in the proxy config file."
    ::= { ptinapgwINAPGWConfiguration 1 }

ptinapgwINAPGWConfigurationEntry OBJECT-TYPE
    SYNTAX          PtinapgwINAPGWConfigurationEntry
    MAX-ACCESS      not-accessible
    STATUS          current
    DESCRIPTION     
            "A sequence of inapgwINAPGWConfiguration attributes."
    INDEX           { ptConnGroupIndex, ptinapgwINAPGWConfigurationIndex }
    ::= { ptinapgwINAPGWConfigurationTable 1 }

PtinapgwINAPGWConfigurationEntry ::=
    SEQUENCE {
        ptinapgwINAPGWConfigurationINAPGWLicense        INTEGER,
        ptinapgwINAPGWConfigurationTrafficStatus        INTEGER,
        ptinapgwINAPGWConfigurationE164INAPGW     DisplayString,
        ptinapgwINAPGWConfigurationTransactionTimeout             Integer32,
        ptinapgwINAPGWConfigurationErrors INTEGER,
        ptinapgwINAPGWConfigurationSetupManagement          INTEGER,
        ptinapgwINAPGWConfigurationExecutionTrace         INTEGER,
        ptinapgwINAPGWConfigurationDistributionManagement                 INTEGER,
        ptinapgwINAPGWConfigurationActions  INTEGER,
        ptinapgwINAPGWConfigurationParentOID    OBJECT IDENTIFIER,
        ptinapgwINAPGWConfigurationRowStatus    RowStatus,
        ptinapgwINAPGWConfigurationIndex Integer32
    }

ptinapgwINAPGWConfigurationINAPGWLicense OBJECT-TYPE
    SYNTAX          INTEGER { unlicensed(0), licensed(1) }
    MAX-ACCESS      read-only
    STATUS          current
    DESCRIPTION     
            "INAP Gateway feature license (UNLICENSED/LICENSED). \nIf the INAP Gateway is unlicensed, the SS7 traffic cannot be activated."
    ::= { ptinapgwINAPGWConfigurationEntry 1 }

ptinapgwINAPGWConfigurationTrafficStatus OBJECT-TYPE
    SYNTAX          INTEGER { inactive(0), notConnected(1), connected(2) }
    MAX-ACCESS      read-only
    STATUS          current
    DESCRIPTION     
            "SCCP connectivity status (INACTIVE, NOT CONNECTED, CONNECTED). \nBased on the per NA connectivity status. CONNECTED will be displayed as soon as an SCCP NA on any slot is connected. \nAssociated to alarm 1301 (INAPGW SS7 Down)."
    ::= { ptinapgwINAPGWConfigurationEntry 2 }

ptinapgwINAPGWConfigurationE164INAPGW OBJECT-TYPE
    SYNTAX          DisplayString (SIZE(0..255))
    MAX-ACCESS      read-create
    STATUS          current
    DESCRIPTION     
            "INAP Gateway E.164 number. \nMust be unique on each mate-STP. \nThe generated INAP Initial-DP query will include these digits in the SCCP Calling Party Address parameter. \nMust be defined to activate traffic."
    ::= { ptinapgwINAPGWConfigurationEntry 3 }

ptinapgwINAPGWConfigurationTransactionTimeout OBJECT-TYPE
    SYNTAX          Integer32 (1..10)
    MAX-ACCESS      read-create
    STATUS          current
    DESCRIPTION     
            "INAPGW Transaction Timeout (1 to 10). \nPending transaction timeout for the INAP queries in seconds. \nDefault: 2 seconds."
    ::= { ptinapgwINAPGWConfigurationEntry 8 }

ptinapgwINAPGWConfigurationErrors OBJECT-TYPE
    SYNTAX          INTEGER { notLogged(0), logged(1) }
    MAX-ACCESS      read-create
    STATUS          current
    DESCRIPTION     
            "If set to LOGGED, the system logs to debug all INAPGW errors. \nShould be set to LOGGED for live systems."
    ::= { ptinapgwINAPGWConfigurationEntry 9 }

ptinapgwINAPGWConfigurationSetupManagement OBJECT-TYPE
    SYNTAX          INTEGER { notLogged(0), logged(1) }
    MAX-ACCESS      read-create
    STATUS          current
    DESCRIPTION     
            "If set to LOGGED, the system logs to debug the INAPGW setup information. \nShould be set to LOGGED for live systems."
    ::= { ptinapgwINAPGWConfigurationEntry 10 }

ptinapgwINAPGWConfigurationExecutionTrace OBJECT-TYPE
    SYNTAX          INTEGER { notLogged(0), logged(1) }
    MAX-ACCESS      read-create
    STATUS          current
    DESCRIPTION     
            "If set to LOGGED, the system logs to debug the execution trace during the processing of incoming INAPGW traffic. \nMust be set to NOT LOGGED for live systems."
    ::= { ptinapgwINAPGWConfigurationEntry 11 }

ptinapgwINAPGWConfigurationDistributionManagement OBJECT-TYPE
    SYNTAX          INTEGER { notLogged(0), logged(1) }
    MAX-ACCESS      read-create
    STATUS          current
    DESCRIPTION     
            "If set to LOGGED, the system logs to debug the INAPGW distribution information. \nMust be set to NOT LOGGED for live systems."
    ::= { ptinapgwINAPGWConfigurationEntry 12 }

ptinapgwINAPGWConfigurationActions OBJECT-TYPE
    SYNTAX          INTEGER { activateTraffic(1), deactivateTraffic(2), 
                        restoreDebugDefaults(3) }
    MAX-ACCESS      read-create
    STATUS          current
    DESCRIPTION     
            "The OID of all possible actions for this instance"
    ::= { ptinapgwINAPGWConfigurationEntry 252 }

ptinapgwINAPGWConfigurationParentOID OBJECT-TYPE
    SYNTAX          OBJECT IDENTIFIER
    MAX-ACCESS      read-create
    STATUS          current
    DESCRIPTION     
            "The OID of the parent object for this instance"
    ::= { ptinapgwINAPGWConfigurationEntry 253 }

ptinapgwINAPGWConfigurationRowStatus OBJECT-TYPE
    SYNTAX          RowStatus
    MAX-ACCESS      read-create
    STATUS          current
    DESCRIPTION     
            "The row status for the inapgwINAPGWConfiguration table"
    ::= { ptinapgwINAPGWConfigurationEntry 254 }

ptinapgwINAPGWConfigurationIndex OBJECT-TYPE
    SYNTAX          Integer32 (-2147483648..2147483647)
    MAX-ACCESS      not-accessible
    STATUS          current
    DESCRIPTION     
            "The row number for the inapgwINAPGWConfiguration table"
    ::= { ptinapgwINAPGWConfigurationEntry 255 }

ptinapgwSCCPNAs OBJECT IDENTIFIER
    ::= { ptConnGroup 1302 }

ptinapgwSCCPNAsTable OBJECT-TYPE
    SYNTAX          SEQUENCE OF PtinapgwSCCPNAsEntry
    MAX-ACCESS      not-accessible
    STATUS          current
    DESCRIPTION     
            "No description supplied in the proxy config file."
    ::= { ptinapgwSCCPNAs 1 }

ptinapgwSCCPNAsEntry OBJECT-TYPE
    SYNTAX          PtinapgwSCCPNAsEntry
    MAX-ACCESS      not-accessible
    STATUS          current
    DESCRIPTION     
            "A sequence of inapgwSCCPNAs attributes."
    INDEX           { ptConnGroupIndex, ptinapgwSCCPNAsIndex }
    ::= { ptinapgwSCCPNAsTable 1 }

PtinapgwSCCPNAsEntry ::=
    SEQUENCE {
        ptinapgwSCCPNAsParentOID        OBJECT IDENTIFIER,
        ptinapgwSCCPNAsRowStatus        RowStatus,
        ptinapgwSCCPNAsIndex            Integer32
    }

ptinapgwSCCPNAsParentOID OBJECT-TYPE
    SYNTAX          OBJECT IDENTIFIER
    MAX-ACCESS      read-create
    STATUS          current
    DESCRIPTION     
            "The OID of the parent object for this instance"
    ::= { ptinapgwSCCPNAsEntry 253 }

ptinapgwSCCPNAsRowStatus OBJECT-TYPE
    SYNTAX          RowStatus
    MAX-ACCESS      read-create
    STATUS          current
    DESCRIPTION     
            "The row status for the inapgwSCCPNAs table"
    ::= { ptinapgwSCCPNAsEntry 254 }

ptinapgwSCCPNAsIndex OBJECT-TYPE
    SYNTAX          Integer32 (-2147483648..2147483647)
    MAX-ACCESS      not-accessible
    STATUS          current
    DESCRIPTION     
            "The row number for the inapgwSCCPNAs table"
    ::= { ptinapgwSCCPNAsEntry 255 }

ptinapgwSCCPNA OBJECT IDENTIFIER
    ::= { ptinapgwSCCPNAs 1303 }

ptinapgwSCCPNATable OBJECT-TYPE
    SYNTAX          SEQUENCE OF PtinapgwSCCPNAEntry
    MAX-ACCESS      not-accessible
    STATUS          current
    DESCRIPTION     
            "No description supplied in the proxy config file."
    ::= { ptinapgwSCCPNA 1 }

ptinapgwSCCPNAEntry OBJECT-TYPE
    SYNTAX          PtinapgwSCCPNAEntry
    MAX-ACCESS      not-accessible
    STATUS          current
    DESCRIPTION     
            "A sequence of inapgwSCCPNA attributes."
    INDEX           { ptConnGroupIndex, ptinapgwSCCPNASCCPNAsIndex, 
                      ptinapgwSCCPNAIndex }
    ::= { ptinapgwSCCPNATable 1 }

PtinapgwSCCPNAEntry ::=
    SEQUENCE {
        ptinapgwSCCPNANA                Integer32,
        ptinapgwSCCPNAStatus            INTEGER,
        ptinapgwSCCPNASCCPNAsIndex      Integer32,
        ptinapgwSCCPNAActions           INTEGER,
        ptinapgwSCCPNAParentOID         OBJECT IDENTIFIER,
        ptinapgwSCCPNARowStatus         RowStatus,
        ptinapgwSCCPNAIndex             Integer32
    }

ptinapgwSCCPNANA OBJECT-TYPE
    SYNTAX          Integer32 (1..99)
    MAX-ACCESS      read-only
    STATUS          current
    DESCRIPTION     
            "SCCP Network Appearance"
    ::= { ptinapgwSCCPNAEntry 1 }

ptinapgwSCCPNAStatus OBJECT-TYPE
    SYNTAX          INTEGER { inactive(0), notConnected(1), connected(2) }
    MAX-ACCESS      read-only
    STATUS          current
    DESCRIPTION     
            "SCCP NA connectivity status (INACTIVE, NOT CONNECTED, CONNECTED). \nBased on the per NA connection connectivity status. CONNECTED will be displayed as soon as an SCCP NA connection is connected. \nAssociated to alarm 1303 (INAPGW SCCP NA Down)."
    ::= { ptinapgwSCCPNAEntry 2 }

ptinapgwSCCPNASCCPNAsIndex OBJECT-TYPE
    SYNTAX          Integer32 (-2147483648..2147483647)
    MAX-ACCESS      not-accessible
    STATUS          current
    DESCRIPTION     
            "This is the index of the parent type for this object.
             This parent type is SCCPNAs."
    ::= { ptinapgwSCCPNAEntry 242 }

ptinapgwSCCPNAActions OBJECT-TYPE
    SYNTAX          INTEGER { activate(1), deactivate(2) }
    MAX-ACCESS      read-create
    STATUS          current
    DESCRIPTION     
            "The OID of all possible actions for this instance"
    ::= { ptinapgwSCCPNAEntry 252 }

ptinapgwSCCPNAParentOID OBJECT-TYPE
    SYNTAX          OBJECT IDENTIFIER
    MAX-ACCESS      read-create
    STATUS          current
    DESCRIPTION     
            "The OID of the parent object for this instance"
    ::= { ptinapgwSCCPNAEntry 253 }

ptinapgwSCCPNARowStatus OBJECT-TYPE
    SYNTAX          RowStatus
    MAX-ACCESS      read-create
    STATUS          current
    DESCRIPTION     
            "The row status for the inapgwSCCPNA table"
    ::= { ptinapgwSCCPNAEntry 254 }

ptinapgwSCCPNAIndex OBJECT-TYPE
    SYNTAX          Integer32 (-2147483648..2147483647)
    MAX-ACCESS      not-accessible
    STATUS          current
    DESCRIPTION     
            "The row number for the inapgwSCCPNA table"
    ::= { ptinapgwSCCPNAEntry 255 }

ptinapgwSCCPNAConnection OBJECT IDENTIFIER
    ::= { ptinapgwSCCPNA 1304 }

ptinapgwSCCPNAConnectionTable OBJECT-TYPE
    SYNTAX          SEQUENCE OF PtinapgwSCCPNAConnectionEntry
    MAX-ACCESS      not-accessible
    STATUS          current
    DESCRIPTION     
            "No description supplied in the proxy config file."
    ::= { ptinapgwSCCPNAConnection 1 }

ptinapgwSCCPNAConnectionEntry OBJECT-TYPE
    SYNTAX          PtinapgwSCCPNAConnectionEntry
    MAX-ACCESS      not-accessible
    STATUS          current
    DESCRIPTION     
            "A sequence of inapgwSCCPNAConnection attributes."
    INDEX           { ptConnGroupIndex, 
                      ptinapgwSCCPNAConnectionSCCPNAsIndex, 
                      ptinapgwSCCPNAConnectionSCCPNAIndex, 
                      ptinapgwSCCPNAConnectionIndex }
    ::= { ptinapgwSCCPNAConnectionTable 1 }

PtinapgwSCCPNAConnectionEntry ::=
    SEQUENCE {
        ptinapgwSCCPNAConnectionSlot    Integer32,
        ptinapgwSCCPNAConnectionStatus  INTEGER,
        ptinapgwSCCPNAConnectionSCCPNAsIndex    Integer32,
        ptinapgwSCCPNAConnectionSCCPNAIndex   Integer32,
        ptinapgwSCCPNAConnectionParentOID OBJECT IDENTIFIER,
        ptinapgwSCCPNAConnectionRowStatus RowStatus,
        ptinapgwSCCPNAConnectionIndex   Integer32
    }

ptinapgwSCCPNAConnectionSlot OBJECT-TYPE
    SYNTAX          Integer32 (-2147483648..2147483647)
    MAX-ACCESS      read-only
    STATUS          current
    DESCRIPTION     
            "Associated slot of the routing CPU for this SCCP NA connection."
    ::= { ptinapgwSCCPNAConnectionEntry 1 }

ptinapgwSCCPNAConnectionStatus OBJECT-TYPE
    SYNTAX          INTEGER { inactive(0), notConnected(1), connected(2) }
    MAX-ACCESS      read-only
    STATUS          current
    DESCRIPTION     
            "SCCP connectivity status (INACTIVE, NOT CONNECTED, CONNECTED). \nBased on the per slot connectivity status. CONNECTED will be displayed as soon as an SCCP connection on any slot is connected. \nAssociated to alarm 1305 (INAPGW SCCP NA Connection Down)."
    ::= { ptinapgwSCCPNAConnectionEntry 2 }

ptinapgwSCCPNAConnectionSCCPNAsIndex OBJECT-TYPE
    SYNTAX          Integer32 (-2147483648..2147483647)
    MAX-ACCESS      not-accessible
    STATUS          current
    DESCRIPTION     
            "This is the index of the parent type for this object.
             This parent type is SCCPNAs."
    ::= { ptinapgwSCCPNAConnectionEntry 242 }

ptinapgwSCCPNAConnectionSCCPNAIndex OBJECT-TYPE
    SYNTAX          Integer32 (-2147483648..2147483647)
    MAX-ACCESS      not-accessible
    STATUS          current
    DESCRIPTION     
            "This is the index of the parent type for this object.
             This parent type is SCCPNA."
    ::= { ptinapgwSCCPNAConnectionEntry 243 }

ptinapgwSCCPNAConnectionParentOID OBJECT-TYPE
    SYNTAX          OBJECT IDENTIFIER
    MAX-ACCESS      read-create
    STATUS          current
    DESCRIPTION     
            "The OID of the parent object for this instance"
    ::= { ptinapgwSCCPNAConnectionEntry 253 }

ptinapgwSCCPNAConnectionRowStatus OBJECT-TYPE
    SYNTAX          RowStatus
    MAX-ACCESS      read-create
    STATUS          current
    DESCRIPTION     
            "The row status for the inapgwSCCPNAConnection table"
    ::= { ptinapgwSCCPNAConnectionEntry 254 }

ptinapgwSCCPNAConnectionIndex OBJECT-TYPE
    SYNTAX          Integer32 (-2147483648..2147483647)
    MAX-ACCESS      not-accessible
    STATUS          current
    DESCRIPTION     
            "The row number for the inapgwSCCPNAConnection table"
    ::= { ptinapgwSCCPNAConnectionEntry 255 }

ptinapgwSCCPRegistrations OBJECT IDENTIFIER
    ::= { ptConnGroup 1305 }

ptinapgwSCCPRegistrationsTable OBJECT-TYPE
    SYNTAX          SEQUENCE OF PtinapgwSCCPRegistrationsEntry
    MAX-ACCESS      not-accessible
    STATUS          current
    DESCRIPTION     
            "No description supplied in the proxy config file."
    ::= { ptinapgwSCCPRegistrations 1 }

ptinapgwSCCPRegistrationsEntry OBJECT-TYPE
    SYNTAX          PtinapgwSCCPRegistrationsEntry
    MAX-ACCESS      not-accessible
    STATUS          current
    DESCRIPTION     
            "A sequence of inapgwSCCPRegistrations attributes."
    INDEX           { ptConnGroupIndex, ptinapgwSCCPRegistrationsIndex }
    ::= { ptinapgwSCCPRegistrationsTable 1 }

PtinapgwSCCPRegistrationsEntry ::=
    SEQUENCE {
        ptinapgwSCCPRegistrationsParentOID  OBJECT IDENTIFIER,
        ptinapgwSCCPRegistrationsRowStatus  RowStatus,
        ptinapgwSCCPRegistrationsIndex  Integer32
    }

ptinapgwSCCPRegistrationsParentOID OBJECT-TYPE
    SYNTAX          OBJECT IDENTIFIER
    MAX-ACCESS      read-create
    STATUS          current
    DESCRIPTION     
            "The OID of the parent object for this instance"
    ::= { ptinapgwSCCPRegistrationsEntry 253 }

ptinapgwSCCPRegistrationsRowStatus OBJECT-TYPE
    SYNTAX          RowStatus
    MAX-ACCESS      read-create
    STATUS          current
    DESCRIPTION     
            "The row status for the inapgwSCCPRegistrations table"
    ::= { ptinapgwSCCPRegistrationsEntry 254 }

ptinapgwSCCPRegistrationsIndex OBJECT-TYPE
    SYNTAX          Integer32 (-2147483648..2147483647)
    MAX-ACCESS      not-accessible
    STATUS          current
    DESCRIPTION     
            "The row number for the inapgwSCCPRegistrations table"
    ::= { ptinapgwSCCPRegistrationsEntry 255 }

ptinapgwSCCPPCSSNRegistration OBJECT IDENTIFIER
    ::= { ptinapgwSCCPRegistrations 1306 }

ptinapgwSCCPPCSSNRegistrationTable OBJECT-TYPE
    SYNTAX          SEQUENCE OF PtinapgwSCCPPCSSNRegistrationEntry
    MAX-ACCESS      not-accessible
    STATUS          current
    DESCRIPTION     
            "No description supplied in the proxy config file."
    ::= { ptinapgwSCCPPCSSNRegistration 1 }

ptinapgwSCCPPCSSNRegistrationEntry OBJECT-TYPE
    SYNTAX          PtinapgwSCCPPCSSNRegistrationEntry
    MAX-ACCESS      not-accessible
    STATUS          current
    DESCRIPTION     
            "A sequence of inapgwSCCPPCSSNRegistration attributes."
    INDEX           { ptConnGroupIndex, 
                      ptinapgwSCCPPCSSNRegistrationSCCPRegistrationsIndex, 
                      ptinapgwSCCPPCSSNRegistrationIndex }
    ::= { ptinapgwSCCPPCSSNRegistrationTable 1 }

PtinapgwSCCPPCSSNRegistrationEntry ::=
    SEQUENCE {
        ptinapgwSCCPPCSSNRegistrationNA Integer32,
        ptinapgwSCCPPCSSNRegistrationPC Integer32,
        ptinapgwSCCPPCSSNRegistrationSSN Integer32,
        ptinapgwSCCPPCSSNRegistrationStatus   INTEGER,
        ptinapgwSCCPPCSSNRegistrationSCCPRegistrationsIndex                   Integer32,
        ptinapgwSCCPPCSSNRegistrationParentOID      OBJECT IDENTIFIER,
        ptinapgwSCCPPCSSNRegistrationRowStatus      RowStatus,
        ptinapgwSCCPPCSSNRegistrationIndex  Integer32
    }

ptinapgwSCCPPCSSNRegistrationNA OBJECT-TYPE
    SYNTAX          Integer32 (-2147483648..2147483647)
    MAX-ACCESS      read-only
    STATUS          current
    DESCRIPTION     
            "Network Appearance of the INAPGW SCCP service registration"
    ::= { ptinapgwSCCPPCSSNRegistrationEntry 1 }

ptinapgwSCCPPCSSNRegistrationPC OBJECT-TYPE
    SYNTAX          Integer32 (-2147483648..2147483647)
    MAX-ACCESS      read-only
    STATUS          current
    DESCRIPTION     
            "Pointcode of the INAPGW SCCP service registration."
    ::= { ptinapgwSCCPPCSSNRegistrationEntry 2 }

ptinapgwSCCPPCSSNRegistrationSSN OBJECT-TYPE
    SYNTAX          Integer32 (2..255)
    MAX-ACCESS      read-only
    STATUS          current
    DESCRIPTION     
            "Subsystem number of the INAPGW SCCP service registration (2 to 255). \nSome standard SSN as per latest specifications Q.0713 (ITU) and GR-246 (ANSI) include: 5 (MAP), 6 (HLR), 7 (VLR), 8 (MSC)."
    ::= { ptinapgwSCCPPCSSNRegistrationEntry 3 }

ptinapgwSCCPPCSSNRegistrationStatus OBJECT-TYPE
    SYNTAX          INTEGER { notRegistered(0), partiallyRegistered(1), 
                        registered(2) }
    MAX-ACCESS      read-only
    STATUS          current
    DESCRIPTION     
            "Status of the PC-SSN registration. \nFully registered when all SCCP connections have successfully registered the PC-SSN. \nValid values: NOT REGISTERED, PARTIALLY REGISTERED, REGISTERED."
    ::= { ptinapgwSCCPPCSSNRegistrationEntry 4 }

ptinapgwSCCPPCSSNRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptinapgwSCCPPCSSNRegistrationEntry 242 }

ptinapgwSCCPPCSSNRegistrationParentOID OBJECT-TYPE
    SYNTAX          OBJECT IDENTIFIER
    MAX-ACCESS      read-create
    STATUS          current
    DESCRIPTION     
            "The OID of the parent object for this instance"
    ::= { ptinapgwSCCPPCSSNRegistrationEntry 253 }

ptinapgwSCCPPCSSNRegistrationRowStatus OBJECT-TYPE
    SYNTAX          RowStatus
    MAX-ACCESS      read-create
    STATUS          current
    DESCRIPTION     
            "The row status for the inapgwSCCPPCSSNRegistration table"
    ::= { ptinapgwSCCPPCSSNRegistrationEntry 254 }

ptinapgwSCCPPCSSNRegistrationIndex OBJECT-TYPE
    SYNTAX          Integer32 (-2147483648..2147483647)
    MAX-ACCESS      not-accessible
    STATUS          current
    DESCRIPTION     
            "The row number for the inapgwSCCPPCSSNRegistration table"
    ::= { ptinapgwSCCPPCSSNRegistrationEntry 255 }

ptinapgwSCCPAppIDRegistration OBJECT IDENTIFIER
    ::= { ptinapgwSCCPRegistrations 1307 }

ptinapgwSCCPAppIDRegistrationTable OBJECT-TYPE
    SYNTAX          SEQUENCE OF PtinapgwSCCPAppIDRegistrationEntry
    MAX-ACCESS      not-accessible
    STATUS          current
    DESCRIPTION     
            "No description supplied in the proxy config file."
    ::= { ptinapgwSCCPAppIDRegistration 1 }

ptinapgwSCCPAppIDRegistrationEntry OBJECT-TYPE
    SYNTAX          PtinapgwSCCPAppIDRegistrationEntry
    MAX-ACCESS      not-accessible
    STATUS          current
    DESCRIPTION     
            "A sequence of inapgwSCCPAppIDRegistration attributes."
    INDEX           { ptConnGroupIndex, 
                      ptinapgwSCCPAppIDRegistrationSCCPRegistrationsIndex, 
                      ptinapgwSCCPAppIDRegistrationIndex }
    ::= { ptinapgwSCCPAppIDRegistrationTable 1 }

PtinapgwSCCPAppIDRegistrationEntry ::=
    SEQUENCE {
        ptinapgwSCCPAppIDRegistrationNA Integer32,
        ptinapgwSCCPAppIDRegistrationApplicationID          DisplayString,
        ptinapgwSCCPAppIDRegistrationStatus   INTEGER,
        ptinapgwSCCPAppIDRegistrationSCCPRegistrationsIndex                   Integer32,
        ptinapgwSCCPAppIDRegistrationParentOID      OBJECT IDENTIFIER,
        ptinapgwSCCPAppIDRegistrationRowStatus      RowStatus,
        ptinapgwSCCPAppIDRegistrationIndex  Integer32
    }

ptinapgwSCCPAppIDRegistrationNA OBJECT-TYPE
    SYNTAX          Integer32 (-2147483648..2147483647)
    MAX-ACCESS      read-only
    STATUS          current
    DESCRIPTION     
            "Network Appearance of the INAPGW SCCP service registration"
    ::= { ptinapgwSCCPAppIDRegistrationEntry 1 }

ptinapgwSCCPAppIDRegistrationApplicationID OBJECT-TYPE
    SYNTAX          DisplayString (SIZE(0..255))
    MAX-ACCESS      read-only
    STATUS          current
    DESCRIPTION     
            "Application ID of the INAPGW SCCP service registration. \nAssociated with the GWST redirection feature. \nValid values: alphanumeric string with - and _ with a maximum of 16 characters (including the null terminating character)."
    ::= { ptinapgwSCCPAppIDRegistrationEntry 2 }

ptinapgwSCCPAppIDRegistrationStatus OBJECT-TYPE
    SYNTAX          INTEGER { notRegistered(0), partiallyRegistered(1), 
                        registered(2) }
    MAX-ACCESS      read-only
    STATUS          current
    DESCRIPTION     
            "Status of the Application ID registration. \nFully registered when all SCCP connections have successfully registered the Application ID. \nValid values: NOT REGISTERED, PARTIALLY REGISTERED, REGISTERED."
    ::= { ptinapgwSCCPAppIDRegistrationEntry 3 }

ptinapgwSCCPAppIDRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptinapgwSCCPAppIDRegistrationEntry 242 }

ptinapgwSCCPAppIDRegistrationParentOID OBJECT-TYPE
    SYNTAX          OBJECT IDENTIFIER
    MAX-ACCESS      read-create
    STATUS          current
    DESCRIPTION     
            "The OID of the parent object for this instance"
    ::= { ptinapgwSCCPAppIDRegistrationEntry 253 }

ptinapgwSCCPAppIDRegistrationRowStatus OBJECT-TYPE
    SYNTAX          RowStatus
    MAX-ACCESS      read-create
    STATUS          current
    DESCRIPTION     
            "The row status for the inapgwSCCPAppIDRegistration table"
    ::= { ptinapgwSCCPAppIDRegistrationEntry 254 }

ptinapgwSCCPAppIDRegistrationIndex OBJECT-TYPE
    SYNTAX          Integer32 (-2147483648..2147483647)
    MAX-ACCESS      not-accessible
    STATUS          current
    DESCRIPTION     
            "The row number for the inapgwSCCPAppIDRegistration table"
    ::= { ptinapgwSCCPAppIDRegistrationEntry 255 }

ptinapgwExternalNPPartners OBJECT IDENTIFIER
    ::= { ptConnGroup 1308 }

ptinapgwExternalNPPartnersTable OBJECT-TYPE
    SYNTAX          SEQUENCE OF PtinapgwExternalNPPartnersEntry
    MAX-ACCESS      not-accessible
    STATUS          current
    DESCRIPTION     
            "No description supplied in the proxy config file."
    ::= { ptinapgwExternalNPPartners 1 }

ptinapgwExternalNPPartnersEntry OBJECT-TYPE
    SYNTAX          PtinapgwExternalNPPartnersEntry
    MAX-ACCESS      not-accessible
    STATUS          current
    DESCRIPTION     
            "A sequence of inapgwExternalNPPartners attributes."
    INDEX           { ptConnGroupIndex, ptinapgwExternalNPPartnersIndex }
    ::= { ptinapgwExternalNPPartnersTable 1 }

PtinapgwExternalNPPartnersEntry ::=
    SEQUENCE {
        ptinapgwExternalNPPartnersParentOID   OBJECT IDENTIFIER,
        ptinapgwExternalNPPartnersRowStatus   RowStatus,
        ptinapgwExternalNPPartnersIndex Integer32
    }

ptinapgwExternalNPPartnersParentOID OBJECT-TYPE
    SYNTAX          OBJECT IDENTIFIER
    MAX-ACCESS      read-create
    STATUS          current
    DESCRIPTION     
            "The OID of the parent object for this instance"
    ::= { ptinapgwExternalNPPartnersEntry 253 }

ptinapgwExternalNPPartnersRowStatus OBJECT-TYPE
    SYNTAX          RowStatus
    MAX-ACCESS      read-create
    STATUS          current
    DESCRIPTION     
            "The row status for the inapgwExternalNPPartners table"
    ::= { ptinapgwExternalNPPartnersEntry 254 }

ptinapgwExternalNPPartnersIndex OBJECT-TYPE
    SYNTAX          Integer32 (-2147483648..2147483647)
    MAX-ACCESS      not-accessible
    STATUS          current
    DESCRIPTION     
            "The row number for the inapgwExternalNPPartners table"
    ::= { ptinapgwExternalNPPartnersEntry 255 }

ptinapgwExternalNPPartner OBJECT IDENTIFIER
    ::= { ptinapgwExternalNPPartners 1309 }

ptinapgwExternalNPPartnerTable OBJECT-TYPE
    SYNTAX          SEQUENCE OF PtinapgwExternalNPPartnerEntry
    MAX-ACCESS      not-accessible
    STATUS          current
    DESCRIPTION     
            "No description supplied in the proxy config file."
    ::= { ptinapgwExternalNPPartner 1 }

ptinapgwExternalNPPartnerEntry OBJECT-TYPE
    SYNTAX          PtinapgwExternalNPPartnerEntry
    MAX-ACCESS      not-accessible
    STATUS          current
    DESCRIPTION     
            "A sequence of inapgwExternalNPPartner attributes."
    INDEX           { ptConnGroupIndex, 
                      ptinapgwExternalNPPartnerExternalNPPartnersIndex, 
                      ptinapgwExternalNPPartnerIndex }
    ::= { ptinapgwExternalNPPartnerTable 1 }

PtinapgwExternalNPPartnerEntry ::=
    SEQUENCE {
        ptinapgwExternalNPPartnerApplicationID      DisplayString,
        ptinapgwExternalNPPartnerNA     Integer32,
        ptinapgwExternalNPPartnerExternalNPE164       DisplayString,
        ptinapgwExternalNPPartnerInitialDPSSN     Integer32,
        ptinapgwExternalNPPartnerInitialDPApplicationContext                    DisplayString,
        ptinapgwExternalNPPartnerInitialDPServiceKey            Integer32,
        ptinapgwExternalNPPartnerInitialDPE164Calling             DisplayString,
        ptinapgwExternalNPPartnerInitialDPEDPSupport            INTEGER,
        ptinapgwExternalNPPartnerINAPContinuePrefix           DisplayString,
        ptinapgwExternalNPPartnerExternalNPPartnersIndex                Integer32,
        ptinapgwExternalNPPartnerParentOID  OBJECT IDENTIFIER,
        ptinapgwExternalNPPartnerRowStatus  RowStatus,
        ptinapgwExternalNPPartnerIndex  Integer32
    }

ptinapgwExternalNPPartnerApplicationID OBJECT-TYPE
    SYNTAX          DisplayString (SIZE(0..255))
    MAX-ACCESS      read-only
    STATUS          current
    DESCRIPTION     
            "Application ID representing the External NP Partner. \nAssociated with the GWST redirection feature. \nValid values: alphanumeric string with - and _ with a maximum of 16 characters."
    ::= { ptinapgwExternalNPPartnerEntry 1 }

ptinapgwExternalNPPartnerNA OBJECT-TYPE
    SYNTAX          Integer32 (1..99)
    MAX-ACCESS      read-create
    STATUS          current
    DESCRIPTION     
            "External NP Partner associated network appearance. \nCorresponding SCCP NA must be defined."
    ::= { ptinapgwExternalNPPartnerEntry 2 }

ptinapgwExternalNPPartnerExternalNPE164 OBJECT-TYPE
    SYNTAX          DisplayString (SIZE(0..255))
    MAX-ACCESS      read-create
    STATUS          current
    DESCRIPTION     
            "External NP Partner E.164 number. \nGT routed INAP queries are sent to this address."
    ::= { ptinapgwExternalNPPartnerEntry 3 }

ptinapgwExternalNPPartnerInitialDPSSN OBJECT-TYPE
    SYNTAX          Integer32
    MAX-ACCESS      read-create
    STATUS          current
    DESCRIPTION     
            "INAP Initial-DP SCCP Called & Calling Subsystem Number. \nDefault of 12 (INAP)."
    ::= { ptinapgwExternalNPPartnerEntry 4 }

ptinapgwExternalNPPartnerInitialDPApplicationContext OBJECT-TYPE
    SYNTAX          DisplayString (SIZE(0..255))
    MAX-ACCESS      read-create
    STATUS          current
    DESCRIPTION     
            "INAP Initial-DP Dialogue Portion Application Context. \nOID formatted string. \nDefault of 0.3.144.12.1.1.1.0."
    ::= { ptinapgwExternalNPPartnerEntry 5 }

ptinapgwExternalNPPartnerInitialDPServiceKey OBJECT-TYPE
    SYNTAX          Integer32
    MAX-ACCESS      read-create
    STATUS          current
    DESCRIPTION     
            "INAP Initial-DP mandatory Service Key parameter. \nDefault of 15."
    ::= { ptinapgwExternalNPPartnerEntry 6 }

ptinapgwExternalNPPartnerInitialDPE164Calling OBJECT-TYPE
    SYNTAX          DisplayString (SIZE(0..255))
    MAX-ACCESS      read-create
    STATUS          current
    DESCRIPTION     
            "INAP Initial-DP Calling Party Number E.164 signals. \nThe generated INAP Initial-DP query will include these E.164 digits with the International nature of address in the Calling Party Number parameter."
    ::= { ptinapgwExternalNPPartnerEntry 7 }

ptinapgwExternalNPPartnerInitialDPEDPSupport OBJECT-TYPE
    SYNTAX          INTEGER { disabled(0), enabled(1) }
    MAX-ACCESS      read-create
    STATUS          current
    DESCRIPTION     
            "INAP Initial-DP optional EDP parameter support. \nIf ENABLED, the EventTypeBCSM parameter (tag 0x9c) is added with LI of 1 and value of analyzedInformation (0x03). \nDefault of DISABLED."
    ::= { ptinapgwExternalNPPartnerEntry 8 }

ptinapgwExternalNPPartnerINAPContinuePrefix OBJECT-TYPE
    SYNTAX          DisplayString (SIZE(0..255))
    MAX-ACCESS      read-create
    STATUS          current
    DESCRIPTION     
            "Prefix added to the SCCP Called Party Address signals for GT routing of the intercepted message based on an INAP Continue response. \nMaximum size is 6 digits. Hexadecimal values supported."
    ::= { ptinapgwExternalNPPartnerEntry 9 }

ptinapgwExternalNPPartnerExternalNPPartnersIndex OBJECT-TYPE
    SYNTAX          Integer32 (-2147483648..2147483647)
    MAX-ACCESS      not-accessible
    STATUS          current
    DESCRIPTION     
            "This is the index of the parent type for this object.
             This parent type is ExternalNPPartners."
    ::= { ptinapgwExternalNPPartnerEntry 242 }

ptinapgwExternalNPPartnerParentOID OBJECT-TYPE
    SYNTAX          OBJECT IDENTIFIER
    MAX-ACCESS      read-create
    STATUS          current
    DESCRIPTION     
            "The OID of the parent object for this instance"
    ::= { ptinapgwExternalNPPartnerEntry 253 }

ptinapgwExternalNPPartnerRowStatus OBJECT-TYPE
    SYNTAX          RowStatus
    MAX-ACCESS      read-create
    STATUS          current
    DESCRIPTION     
            "The row status for the inapgwExternalNPPartner table"
    ::= { ptinapgwExternalNPPartnerEntry 254 }

ptinapgwExternalNPPartnerIndex OBJECT-TYPE
    SYNTAX          Integer32 (-2147483648..2147483647)
    MAX-ACCESS      not-accessible
    STATUS          current
    DESCRIPTION     
            "The row number for the inapgwExternalNPPartner table"
    ::= { ptinapgwExternalNPPartnerEntry 255 }

ptsnamiSNAMIConfiguration OBJECT IDENTIFIER
    ::= { ptConnGroup 1501 }

ptsnamiSNAMIConfigurationTable OBJECT-TYPE
    SYNTAX          SEQUENCE OF PtsnamiSNAMIConfigurationEntry
    MAX-ACCESS      not-accessible
    STATUS          current
    DESCRIPTION     
            "No description supplied in the proxy config file."
    ::= { ptsnamiSNAMIConfiguration 1 }

ptsnamiSNAMIConfigurationEntry OBJECT-TYPE
    SYNTAX          PtsnamiSNAMIConfigurationEntry
    MAX-ACCESS      not-accessible
    STATUS          current
    DESCRIPTION     
            "A sequence of snamiSNAMIConfiguration attributes."
    INDEX           { ptConnGroupIndex, ptsnamiSNAMIConfigurationIndex }
    ::= { ptsnamiSNAMIConfigurationTable 1 }

PtsnamiSNAMIConfigurationEntry ::=
    SEQUENCE {
        ptsnamiSNAMIConfigurationSNAMILicense     INTEGER,
        ptsnamiSNAMIConfigurationSNAMIStatus    INTEGER,
        ptsnamiSNAMIConfigurationSR5129ThresholdTimeout               Integer32,
        ptsnamiSNAMIConfigurationSR5129LocalNodeName            DisplayString,
        ptsnamiSNAMIConfigurationErrors INTEGER,
        ptsnamiSNAMIConfigurationSetupManagement        INTEGER,
        ptsnamiSNAMIConfigurationExecutionTrace       INTEGER,
        ptsnamiSNAMIConfigurationAuditLog INTEGER,
        ptsnamiSNAMIConfigurationActions INTEGER,
        ptsnamiSNAMIConfigurationParentOID  OBJECT IDENTIFIER,
        ptsnamiSNAMIConfigurationRowStatus  RowStatus,
        ptsnamiSNAMIConfigurationIndex  Integer32
    }

ptsnamiSNAMIConfigurationSNAMILicense OBJECT-TYPE
    SYNTAX          INTEGER { unlicensed(0), licensed(1) }
    MAX-ACCESS      read-only
    STATUS          current
    DESCRIPTION     
            "SNAMI feature license (UNLICENSED/LICENSED). \nIf the SNAMI is unlicensed, the SNAMI traffic cannot be activated."
    ::= { ptsnamiSNAMIConfigurationEntry 1 }

ptsnamiSNAMIConfigurationSNAMIStatus OBJECT-TYPE
    SYNTAX          INTEGER { inactive(0), notReady(1), ready(2) }
    MAX-ACCESS      read-only
    STATUS          current
    DESCRIPTION     
            "SNAMI status (INACTIVE/NOT READY/READY). \nThe SNAMI service is READY when SR-5129 connections can be made or a command is being processed."
    ::= { ptsnamiSNAMIConfigurationEntry 2 }

ptsnamiSNAMIConfigurationSR5129ThresholdTimeout OBJECT-TYPE
    SYNTAX          Integer32 (0..2147483647)
    MAX-ACCESS      read-create
    STATUS          current
    DESCRIPTION     
            "SR-5129 Threshold Timeout (in seconds). \nIf no message is processed on the connection during this interval, the connection will be dropped. \nSet to 0 to disable the timeout. \nDefault value: 30 seconds. \nValid values: 0 to +."
    ::= { ptsnamiSNAMIConfigurationEntry 4 }

ptsnamiSNAMIConfigurationSR5129LocalNodeName OBJECT-TYPE
    SYNTAX          DisplayString (SIZE(0..255))
    MAX-ACCESS      read-create
    STATUS          current
    DESCRIPTION     
            "SR-5129 Local Node Name. \nSNAMI server will include this node name the SR-5129 packets. Incoming packets in the Destination Node Name field should have the same node name, or be empty. \nValid values: alphanumeric (fixed size of 17)."
    ::= { ptsnamiSNAMIConfigurationEntry 5 }

ptsnamiSNAMIConfigurationErrors OBJECT-TYPE
    SYNTAX          INTEGER { notLogged(0), logged(1) }
    MAX-ACCESS      read-create
    STATUS          current
    DESCRIPTION     
            "Enable or disable the logging of SNAMI error messages to the debuglog (NOT LOGGED/LOGGED). \nNote: GR-310 command failures due to a precondition check are not logged to the debuglog. See the GR-310 audit log for those related issues. \nThe logging of SNAMI errors should be set to LOGGED for all production systems. \nDefault value: LOGGED."
    ::= { ptsnamiSNAMIConfigurationEntry 7 }

ptsnamiSNAMIConfigurationSetupManagement OBJECT-TYPE
    SYNTAX          INTEGER { notLogged(0), logged(1) }
    MAX-ACCESS      read-create
    STATUS          current
    DESCRIPTION     
            "Enable or disable the logging of startup and setup information to the debuglog (NOT LOGGED/LOGGED). \nThese logs are not related to traffic processing and have no impact on the performance of a running system. \nThe logging of SNAMI startup and setup information should be set to LOGGED for most production systems. \nDefault value: LOGGED."
    ::= { ptsnamiSNAMIConfigurationEntry 8 }

ptsnamiSNAMIConfigurationExecutionTrace OBJECT-TYPE
    SYNTAX          INTEGER { notLogged(0), logged(1) }
    MAX-ACCESS      read-create
    STATUS          current
    DESCRIPTION     
            "Enable or disable the logging of the execution trace to the debuglog (NOT LOGGED/LOGGED). \nThese logs are related to traffic and GR310 server processing and have impact on the performance of a running system. \nThe logging of SNAMI execution trace should be set to NOT LOGGED for most production systems. \nDefault value: NOT LOGGED."
    ::= { ptsnamiSNAMIConfigurationEntry 9 }

ptsnamiSNAMIConfigurationAuditLog OBJECT-TYPE
    SYNTAX          INTEGER { notLogged(0), logged(1) }
    MAX-ACCESS      read-create
    STATUS          current
    DESCRIPTION     
            "Enable or disable the logging of the GR-310 command processing to the GR-310 audit log (NOT LOGGED/LOGGED). \nThe logging of audit log is recommended to be set to LOGGED on all production systems for provisioning accountability. \nDefault value: NOT LOGGED."
    ::= { ptsnamiSNAMIConfigurationEntry 10 }

ptsnamiSNAMIConfigurationActions OBJECT-TYPE
    SYNTAX          INTEGER { activate(1), deactivate(2) }
    MAX-ACCESS      read-create
    STATUS          current
    DESCRIPTION     
            "The OID of all possible actions for this instance"
    ::= { ptsnamiSNAMIConfigurationEntry 252 }

ptsnamiSNAMIConfigurationParentOID OBJECT-TYPE
    SYNTAX          OBJECT IDENTIFIER
    MAX-ACCESS      read-create
    STATUS          current
    DESCRIPTION     
            "The OID of the parent object for this instance"
    ::= { ptsnamiSNAMIConfigurationEntry 253 }

ptsnamiSNAMIConfigurationRowStatus OBJECT-TYPE
    SYNTAX          RowStatus
    MAX-ACCESS      read-create
    STATUS          current
    DESCRIPTION     
            "The row status for the snamiSNAMIConfiguration table"
    ::= { ptsnamiSNAMIConfigurationEntry 254 }

ptsnamiSNAMIConfigurationIndex OBJECT-TYPE
    SYNTAX          Integer32 (-2147483648..2147483647)
    MAX-ACCESS      not-accessible
    STATUS          current
    DESCRIPTION     
            "The row number for the snamiSNAMIConfiguration table"
    ::= { ptsnamiSNAMIConfigurationEntry 255 }

ptsnamiPortNAMappings OBJECT IDENTIFIER
    ::= { ptConnGroup 1502 }

ptsnamiPortNAMappingsTable OBJECT-TYPE
    SYNTAX          SEQUENCE OF PtsnamiPortNAMappingsEntry
    MAX-ACCESS      not-accessible
    STATUS          current
    DESCRIPTION     
            "No description supplied in the proxy config file."
    ::= { ptsnamiPortNAMappings 1 }

ptsnamiPortNAMappingsEntry OBJECT-TYPE
    SYNTAX          PtsnamiPortNAMappingsEntry
    MAX-ACCESS      not-accessible
    STATUS          current
    DESCRIPTION     
            "A sequence of snamiPortNAMappings attributes."
    INDEX           { ptConnGroupIndex, ptsnamiPortNAMappingsIndex }
    ::= { ptsnamiPortNAMappingsTable 1 }

PtsnamiPortNAMappingsEntry ::=
    SEQUENCE {
        ptsnamiPortNAMappingsParentOID  OBJECT IDENTIFIER,
        ptsnamiPortNAMappingsRowStatus  RowStatus,
        ptsnamiPortNAMappingsIndex      Integer32
    }

ptsnamiPortNAMappingsParentOID OBJECT-TYPE
    SYNTAX          OBJECT IDENTIFIER
    MAX-ACCESS      read-create
    STATUS          current
    DESCRIPTION     
            "The OID of the parent object for this instance"
    ::= { ptsnamiPortNAMappingsEntry 253 }

ptsnamiPortNAMappingsRowStatus OBJECT-TYPE
    SYNTAX          RowStatus
    MAX-ACCESS      read-create
    STATUS          current
    DESCRIPTION     
            "The row status for the snamiPortNAMappings table"
    ::= { ptsnamiPortNAMappingsEntry 254 }

ptsnamiPortNAMappingsIndex OBJECT-TYPE
    SYNTAX          Integer32 (-2147483648..2147483647)
    MAX-ACCESS      not-accessible
    STATUS          current
    DESCRIPTION     
            "The row number for the snamiPortNAMappings table"
    ::= { ptsnamiPortNAMappingsEntry 255 }

ptsnamiPortNAMapping OBJECT IDENTIFIER
    ::= { ptsnamiPortNAMappings 1503 }

ptsnamiPortNAMappingTable OBJECT-TYPE
    SYNTAX          SEQUENCE OF PtsnamiPortNAMappingEntry
    MAX-ACCESS      not-accessible
    STATUS          current
    DESCRIPTION     
            "No description supplied in the proxy config file."
    ::= { ptsnamiPortNAMapping 1 }

ptsnamiPortNAMappingEntry OBJECT-TYPE
    SYNTAX          PtsnamiPortNAMappingEntry
    MAX-ACCESS      not-accessible
    STATUS          current
    DESCRIPTION     
            "A sequence of snamiPortNAMapping attributes."
    INDEX           { ptConnGroupIndex, 
                      ptsnamiPortNAMappingPortNAMappingsIndex, 
                      ptsnamiPortNAMappingIndex }
    ::= { ptsnamiPortNAMappingTable 1 }

PtsnamiPortNAMappingEntry ::=
    SEQUENCE {
        ptsnamiPortNAMappingPort        Integer32,
        ptsnamiPortNAMappingNA          Integer32,
        ptsnamiPortNAMappingDestinationName   DisplayString,
        ptsnamiPortNAMappingRoutesetTableName     DisplayString,
        ptsnamiPortNAMappingGTTDBDefName DisplayString,
        ptsnamiPortNAMappingPortNAMappingsIndex       Integer32,
        ptsnamiPortNAMappingParentOID   OBJECT IDENTIFIER,
        ptsnamiPortNAMappingRowStatus   RowStatus,
        ptsnamiPortNAMappingIndex       Integer32
    }

ptsnamiPortNAMappingPort OBJECT-TYPE
    SYNTAX          Integer32 (8611..8618)
    MAX-ACCESS      read-only
    STATUS          current
    DESCRIPTION     
            "TCP/IP port for the SNAMI NA configuration. \nMust be unique. \nValid values: 8611 to 8618."
    ::= { ptsnamiPortNAMappingEntry 1 }

ptsnamiPortNAMappingNA OBJECT-TYPE
    SYNTAX          Integer32 (1..99)
    MAX-ACCESS      read-create
    STATUS          current
    DESCRIPTION     
            "Network Appearance associated with the port (1..99). \nMultiple ports may reuse the same NA."
    ::= { ptsnamiPortNAMappingEntry 2 }

ptsnamiPortNAMappingDestinationName OBJECT-TYPE
    SYNTAX          DisplayString (SIZE(0..255))
    MAX-ACCESS      read-create
    STATUS          current
    DESCRIPTION     
            "Destination name associated with the port. \nValid values: uppercase alphanumeric (fixed size of 12)."
    ::= { ptsnamiPortNAMappingEntry 3 }

ptsnamiPortNAMappingRoutesetTableName OBJECT-TYPE
    SYNTAX          DisplayString (SIZE(0..255))
    MAX-ACCESS      read-only
    STATUS          current
    DESCRIPTION     
            "Routeset Table name associated with the NA. \nDefault value: STANDARD \nValid values: uppercase alphanumeric (maximum size of 8)."
    ::= { ptsnamiPortNAMappingEntry 4 }

ptsnamiPortNAMappingGTTDBDefName OBJECT-TYPE
    SYNTAX          DisplayString (SIZE(0..255))
    MAX-ACCESS      read-only
    STATUS          current
    DESCRIPTION     
            "GTT DB Def name associated with the Port NA. \nDefault value: STANDARD \nValid values: uppercase alphanumeric (maximum size of 15)."
    ::= { ptsnamiPortNAMappingEntry 5 }

ptsnamiPortNAMappingPortNAMappingsIndex OBJECT-TYPE
    SYNTAX          Integer32 (-2147483648..2147483647)
    MAX-ACCESS      not-accessible
    STATUS          current
    DESCRIPTION     
            "This is the index of the parent type for this object.
             This parent type is PortNAMappings."
    ::= { ptsnamiPortNAMappingEntry 242 }

ptsnamiPortNAMappingParentOID OBJECT-TYPE
    SYNTAX          OBJECT IDENTIFIER
    MAX-ACCESS      read-create
    STATUS          current
    DESCRIPTION     
            "The OID of the parent object for this instance"
    ::= { ptsnamiPortNAMappingEntry 253 }

ptsnamiPortNAMappingRowStatus OBJECT-TYPE
    SYNTAX          RowStatus
    MAX-ACCESS      read-create
    STATUS          current
    DESCRIPTION     
            "The row status for the snamiPortNAMapping table"
    ::= { ptsnamiPortNAMappingEntry 254 }

ptsnamiPortNAMappingIndex OBJECT-TYPE
    SYNTAX          Integer32 (-2147483648..2147483647)
    MAX-ACCESS      not-accessible
    STATUS          current
    DESCRIPTION     
            "The row number for the snamiPortNAMapping table"
    ::= { ptsnamiPortNAMappingEntry 255 }

ptsnamiCCSOSNodes OBJECT IDENTIFIER
    ::= { ptConnGroup 1504 }

ptsnamiCCSOSNodesTable OBJECT-TYPE
    SYNTAX          SEQUENCE OF PtsnamiCCSOSNodesEntry
    MAX-ACCESS      not-accessible
    STATUS          current
    DESCRIPTION     
            "No description supplied in the proxy config file."
    ::= { ptsnamiCCSOSNodes 1 }

ptsnamiCCSOSNodesEntry OBJECT-TYPE
    SYNTAX          PtsnamiCCSOSNodesEntry
    MAX-ACCESS      not-accessible
    STATUS          current
    DESCRIPTION     
            "A sequence of snamiCCSOSNodes attributes."
    INDEX           { ptConnGroupIndex, ptsnamiCCSOSNodesIndex }
    ::= { ptsnamiCCSOSNodesTable 1 }

PtsnamiCCSOSNodesEntry ::=
    SEQUENCE {
        ptsnamiCCSOSNodesParentOID      OBJECT IDENTIFIER,
        ptsnamiCCSOSNodesRowStatus      RowStatus,
        ptsnamiCCSOSNodesIndex          Integer32
    }

ptsnamiCCSOSNodesParentOID OBJECT-TYPE
    SYNTAX          OBJECT IDENTIFIER
    MAX-ACCESS      read-create
    STATUS          current
    DESCRIPTION     
            "The OID of the parent object for this instance"
    ::= { ptsnamiCCSOSNodesEntry 253 }

ptsnamiCCSOSNodesRowStatus OBJECT-TYPE
    SYNTAX          RowStatus
    MAX-ACCESS      read-create
    STATUS          current
    DESCRIPTION     
            "The row status for the snamiCCSOSNodes table"
    ::= { ptsnamiCCSOSNodesEntry 254 }

ptsnamiCCSOSNodesIndex OBJECT-TYPE
    SYNTAX          Integer32 (-2147483648..2147483647)
    MAX-ACCESS      not-accessible
    STATUS          current
    DESCRIPTION     
            "The row number for the snamiCCSOSNodes table"
    ::= { ptsnamiCCSOSNodesEntry 255 }

ptsnamiCCSOSNode OBJECT IDENTIFIER
    ::= { ptsnamiCCSOSNodes 1505 }

ptsnamiCCSOSNodeTable OBJECT-TYPE
    SYNTAX          SEQUENCE OF PtsnamiCCSOSNodeEntry
    MAX-ACCESS      not-accessible
    STATUS          current
    DESCRIPTION     
            "No description supplied in the proxy config file."
    ::= { ptsnamiCCSOSNode 1 }

ptsnamiCCSOSNodeEntry OBJECT-TYPE
    SYNTAX          PtsnamiCCSOSNodeEntry
    MAX-ACCESS      not-accessible
    STATUS          current
    DESCRIPTION     
            "A sequence of snamiCCSOSNode attributes."
    INDEX           { ptConnGroupIndex, ptsnamiCCSOSNodeCCSOSNodesIndex, 
                      ptsnamiCCSOSNodeIndex }
    ::= { ptsnamiCCSOSNodeTable 1 }

PtsnamiCCSOSNodeEntry ::=
    SEQUENCE {
        ptsnamiCCSOSNodeHost            DisplayString,
        ptsnamiCCSOSNodeSourceName      DisplayString,
        ptsnamiCCSOSNodeRecordID        Integer32,
        ptsnamiCCSOSNodeCCSOSNodesIndex Integer32,
        ptsnamiCCSOSNodeParentOID       OBJECT IDENTIFIER,
        ptsnamiCCSOSNodeRowStatus       RowStatus,
        ptsnamiCCSOSNodeIndex           Integer32
    }

ptsnamiCCSOSNodeHost OBJECT-TYPE
    SYNTAX          DisplayString (SIZE(0..255))
    MAX-ACCESS      read-only
    STATUS          current
    DESCRIPTION     
            "CCS OS Node associated host name."
    ::= { ptsnamiCCSOSNodeEntry 1 }

ptsnamiCCSOSNodeSourceName OBJECT-TYPE
    SYNTAX          DisplayString (SIZE(0..255))
    MAX-ACCESS      read-create
    STATUS          current
    DESCRIPTION     
            "CCS OS Node associated source name. \nValid values: uppercase alphanumeric (fixed size of 12)."
    ::= { ptsnamiCCSOSNodeEntry 2 }

ptsnamiCCSOSNodeRecordID OBJECT-TYPE
    SYNTAX          Integer32 (-2147483648..2147483647)
    MAX-ACCESS      read-only
    STATUS          current
    DESCRIPTION     
            "Hidden attribute for the unique record ID as used by the proxy. \nMust not be zero."
    ::= { ptsnamiCCSOSNodeEntry 3 }

ptsnamiCCSOSNodeCCSOSNodesIndex OBJECT-TYPE
    SYNTAX          Integer32 (-2147483648..2147483647)
    MAX-ACCESS      not-accessible
    STATUS          current
    DESCRIPTION     
            "This is the index of the parent type for this object.
             This parent type is CCSOSNodes."
    ::= { ptsnamiCCSOSNodeEntry 242 }

ptsnamiCCSOSNodeParentOID OBJECT-TYPE
    SYNTAX          OBJECT IDENTIFIER
    MAX-ACCESS      read-create
    STATUS          current
    DESCRIPTION     
            "The OID of the parent object for this instance"
    ::= { ptsnamiCCSOSNodeEntry 253 }

ptsnamiCCSOSNodeRowStatus OBJECT-TYPE
    SYNTAX          RowStatus
    MAX-ACCESS      read-create
    STATUS          current
    DESCRIPTION     
            "The row status for the snamiCCSOSNode table"
    ::= { ptsnamiCCSOSNodeEntry 254 }

ptsnamiCCSOSNodeIndex OBJECT-TYPE
    SYNTAX          Integer32 (-2147483648..2147483647)
    MAX-ACCESS      not-accessible
    STATUS          current
    DESCRIPTION     
            "The row number for the snamiCCSOSNode table"
    ::= { ptsnamiCCSOSNodeEntry 255 }

ptsnamiGR310ServerConfiguration OBJECT IDENTIFIER
    ::= { ptConnGroup 1506 }

ptsnamiGR310ServerConfigurationTable OBJECT-TYPE
    SYNTAX          SEQUENCE OF PtsnamiGR310ServerConfigurationEntry
    MAX-ACCESS      not-accessible
    STATUS          current
    DESCRIPTION     
            "No description supplied in the proxy config file."
    ::= { ptsnamiGR310ServerConfiguration 1 }

ptsnamiGR310ServerConfigurationEntry OBJECT-TYPE
    SYNTAX          PtsnamiGR310ServerConfigurationEntry
    MAX-ACCESS      not-accessible
    STATUS          current
    DESCRIPTION     
            "A sequence of snamiGR310ServerConfiguration attributes."
    INDEX           { ptConnGroupIndex, 
                      ptsnamiGR310ServerConfigurationIndex }
    ::= { ptsnamiGR310ServerConfigurationTable 1 }

PtsnamiGR310ServerConfigurationEntry ::=
    SEQUENCE {
        ptsnamiGR310ServerConfigurationSlot   Integer32,
        ptsnamiGR310ServerConfigurationStatus     INTEGER,
        ptsnamiGR310ServerConfigurationParentOID        OBJECT IDENTIFIER,
        ptsnamiGR310ServerConfigurationRowStatus        RowStatus,
        ptsnamiGR310ServerConfigurationIndex    Integer32
    }

ptsnamiGR310ServerConfigurationSlot OBJECT-TYPE
    SYNTAX          Integer32 (-2147483648..2147483647)
    MAX-ACCESS      read-only
    STATUS          current
    DESCRIPTION     
            "SNAMI GR-310 Server associated slot."
    ::= { ptsnamiGR310ServerConfigurationEntry 1 }

ptsnamiGR310ServerConfigurationStatus OBJECT-TYPE
    SYNTAX          INTEGER { inactive(0), notReady(1), ready(2), 
                        standingBy(3), lost(4) }
    MAX-ACCESS      read-only
    STATUS          current
    DESCRIPTION     
            "SNAMI GR-310 Server status (INACTIVE/NOT READY/READY/STANDING BY/LOST). \nServer is READY when it is can accept GR-310 connections or is in the process of shutting down."
    ::= { ptsnamiGR310ServerConfigurationEntry 2 }

ptsnamiGR310ServerConfigurationParentOID OBJECT-TYPE
    SYNTAX          OBJECT IDENTIFIER
    MAX-ACCESS      read-create
    STATUS          current
    DESCRIPTION     
            "The OID of the parent object for this instance"
    ::= { ptsnamiGR310ServerConfigurationEntry 253 }

ptsnamiGR310ServerConfigurationRowStatus OBJECT-TYPE
    SYNTAX          RowStatus
    MAX-ACCESS      read-create
    STATUS          current
    DESCRIPTION     
            "The row status for the snamiGR310ServerConfiguration table"
    ::= { ptsnamiGR310ServerConfigurationEntry 254 }

ptsnamiGR310ServerConfigurationIndex OBJECT-TYPE
    SYNTAX          Integer32 (-2147483648..2147483647)
    MAX-ACCESS      not-accessible
    STATUS          current
    DESCRIPTION     
            "The row number for the snamiGR310ServerConfiguration table"
    ::= { ptsnamiGR310ServerConfigurationEntry 255 }

ptnpgwNPGWConfiguration OBJECT IDENTIFIER
    ::= { ptConnGroup 1601 }

ptnpgwNPGWConfigurationTable OBJECT-TYPE
    SYNTAX          SEQUENCE OF PtnpgwNPGWConfigurationEntry
    MAX-ACCESS      not-accessible
    STATUS          current
    DESCRIPTION     
            "No description supplied in the proxy config file."
    ::= { ptnpgwNPGWConfiguration 1 }

ptnpgwNPGWConfigurationEntry OBJECT-TYPE
    SYNTAX          PtnpgwNPGWConfigurationEntry
    MAX-ACCESS      not-accessible
    STATUS          current
    DESCRIPTION     
            "A sequence of npgwNPGWConfiguration attributes."
    INDEX           { ptConnGroupIndex, ptnpgwNPGWConfigurationIndex }
    ::= { ptnpgwNPGWConfigurationTable 1 }

PtnpgwNPGWConfigurationEntry ::=
    SEQUENCE {
        ptnpgwNPGWConfigurationINAPGateway  INTEGER,
        ptnpgwNPGWConfigurationPSXNPGateway   INTEGER,
        ptnpgwNPGWConfigurationMTP3TrafficStatus        INTEGER,
        ptnpgwNPGWConfigurationSCCPTrafficStatus        INTEGER,
        ptnpgwNPGWConfigurationINAPGatewayE164      DisplayString,
        ptnpgwNPGWConfigurationINAPGatewayTimeout         Integer32,
        ptnpgwNPGWConfigurationTransactionTimeout         Integer32,
        ptnpgwNPGWConfigurationErrors   INTEGER,
        ptnpgwNPGWConfigurationSetupManagement      INTEGER,
        ptnpgwNPGWConfigurationExecutionTrace     INTEGER,
        ptnpgwNPGWConfigurationDistributionManagement             INTEGER,
        ptnpgwNPGWConfigurationActions  INTEGER,
        ptnpgwNPGWConfigurationParentOID OBJECT IDENTIFIER,
        ptnpgwNPGWConfigurationRowStatus RowStatus,
        ptnpgwNPGWConfigurationIndex    Integer32
    }

ptnpgwNPGWConfigurationINAPGateway OBJECT-TYPE
    SYNTAX          INTEGER { unlicensed(0), licensed(1) }
    MAX-ACCESS      read-only
    STATUS          current
    DESCRIPTION     
            "INAP Gateway feature license (UNLICENSED/LICENSED). \nIf all gateways are unlicensed, the SS7 traffic cannot be activated."
    ::= { ptnpgwNPGWConfigurationEntry 1 }

ptnpgwNPGWConfigurationPSXNPGateway OBJECT-TYPE
    SYNTAX          INTEGER { unlicensed(0), licensed(1) }
    MAX-ACCESS      read-only
    STATUS          current
    DESCRIPTION     
            "PSX NP Gateway feature license (UNLICENSED/LICENSED). \nIf the gateway is unlicensed, the SS7 traffic cannot be activated."
    ::= { ptnpgwNPGWConfigurationEntry 2 }

ptnpgwNPGWConfigurationMTP3TrafficStatus OBJECT-TYPE
    SYNTAX          INTEGER { inactive(0), notConnected(1), connected(2), 
                        partiallyConnected(3) }
    MAX-ACCESS      read-only
    STATUS          current
    DESCRIPTION     
            "MTP3 connectivity status (INACTIVE, NOT CONNECTED, CONNECTED). \nBased on the per NA connectivity status. CONNECTED will be displayed as soon as an MTP3 NA on any slot is connected. \nAssociated to alarm 1617 (NPGW MTP3 Down)."
    ::= { ptnpgwNPGWConfigurationEntry 3 }

ptnpgwNPGWConfigurationSCCPTrafficStatus OBJECT-TYPE
    SYNTAX          INTEGER { inactive(0), notConnected(1), connected(2), 
                        partiallyConnected(3) }
    MAX-ACCESS      read-only
    STATUS          current
    DESCRIPTION     
            "SCCP connectivity status (INACTIVE, NOT CONNECTED, CONNECTED). \nBased on the per NA connectivity status. CONNECTED will be displayed as soon as an SCCP NA on any slot is connected. \nAssociated to alarm 1601 (NPGW SCCP Down)."
    ::= { ptnpgwNPGWConfigurationEntry 4 }

ptnpgwNPGWConfigurationINAPGatewayE164 OBJECT-TYPE
    SYNTAX          DisplayString (SIZE(0..255))
    MAX-ACCESS      read-create
    STATUS          current
    DESCRIPTION     
            "INAP Gateway E.164 number. \nMust be unique on each mate-STP. \nThe generated INAP Initial-DP query will include these digits in the SCCP Calling Party Address parameter. \nMust be defined to activate traffic."
    ::= { ptnpgwNPGWConfigurationEntry 5 }

ptnpgwNPGWConfigurationINAPGatewayTimeout OBJECT-TYPE
    SYNTAX          Integer32 (1000..10000)
    MAX-ACCESS      read-create
    STATUS          current
    DESCRIPTION     
            "INAP Gateway Transaction Timeout (1000 to 10000). \nPending transaction timeout for the INAP queries in milliseconds (ms). \nDefault: 2000 ms."
    ::= { ptnpgwNPGWConfigurationEntry 6 }

ptnpgwNPGWConfigurationTransactionTimeout OBJECT-TYPE
    SYNTAX          Integer32 (100..5000)
    MAX-ACCESS      read-create
    STATUS          current
    DESCRIPTION     
            "PSX NP Gateway Transaction Timeout (100 to 5000). \nPending transaction timeout for the PSX NP service queries in milliseconds (ms). \nNote: A fallback lifetime timeout will also be initialized based on the Transaction Timeout plus 500 ms. \nDefault: 1000 ms."
    ::= { ptnpgwNPGWConfigurationEntry 7 }

ptnpgwNPGWConfigurationErrors OBJECT-TYPE
    SYNTAX          INTEGER { notLogged(0), logged(1) }
    MAX-ACCESS      read-create
    STATUS          current
    DESCRIPTION     
            "If set to LOGGED, the system logs to debug all NPGW errors. \nShould be set to LOGGED for live systems."
    ::= { ptnpgwNPGWConfigurationEntry 9 }

ptnpgwNPGWConfigurationSetupManagement OBJECT-TYPE
    SYNTAX          INTEGER { notLogged(0), logged(1) }
    MAX-ACCESS      read-create
    STATUS          current
    DESCRIPTION     
            "If set to LOGGED, the system logs to debug the NPGW setup information. \nShould be set to LOGGED for live systems."
    ::= { ptnpgwNPGWConfigurationEntry 10 }

ptnpgwNPGWConfigurationExecutionTrace OBJECT-TYPE
    SYNTAX          INTEGER { notLogged(0), logged(1) }
    MAX-ACCESS      read-create
    STATUS          current
    DESCRIPTION     
            "If set to LOGGED, the system logs to debug the execution trace during the processing of incoming NPGW traffic. \nMust be set to NOT LOGGED for live systems."
    ::= { ptnpgwNPGWConfigurationEntry 11 }

ptnpgwNPGWConfigurationDistributionManagement OBJECT-TYPE
    SYNTAX          INTEGER { notLogged(0), logged(1) }
    MAX-ACCESS      read-create
    STATUS          current
    DESCRIPTION     
            "If set to LOGGED, the system logs to debug the NPGW distribution information. \nMust be set to NOT LOGGED for live systems."
    ::= { ptnpgwNPGWConfigurationEntry 12 }

ptnpgwNPGWConfigurationActions OBJECT-TYPE
    SYNTAX          INTEGER { activate(1), deactivate(2), 
                        restoreDebugDefaults(3) }
    MAX-ACCESS      read-create
    STATUS          current
    DESCRIPTION     
            "The OID of all possible actions for this instance"
    ::= { ptnpgwNPGWConfigurationEntry 252 }

ptnpgwNPGWConfigurationParentOID OBJECT-TYPE
    SYNTAX          OBJECT IDENTIFIER
    MAX-ACCESS      read-create
    STATUS          current
    DESCRIPTION     
            "The OID of the parent object for this instance"
    ::= { ptnpgwNPGWConfigurationEntry 253 }

ptnpgwNPGWConfigurationRowStatus OBJECT-TYPE
    SYNTAX          RowStatus
    MAX-ACCESS      read-create
    STATUS          current
    DESCRIPTION     
            "The row status for the npgwNPGWConfiguration table"
    ::= { ptnpgwNPGWConfigurationEntry 254 }

ptnpgwNPGWConfigurationIndex OBJECT-TYPE
    SYNTAX          Integer32 (-2147483648..2147483647)
    MAX-ACCESS      not-accessible
    STATUS          current
    DESCRIPTION     
            "The row number for the npgwNPGWConfiguration table"
    ::= { ptnpgwNPGWConfigurationEntry 255 }

ptnpgwMTP3NAs OBJECT IDENTIFIER
    ::= { ptConnGroup 1602 }

ptnpgwMTP3NAsTable OBJECT-TYPE
    SYNTAX          SEQUENCE OF PtnpgwMTP3NAsEntry
    MAX-ACCESS      not-accessible
    STATUS          current
    DESCRIPTION     
            "No description supplied in the proxy config file."
    ::= { ptnpgwMTP3NAs 1 }

ptnpgwMTP3NAsEntry OBJECT-TYPE
    SYNTAX          PtnpgwMTP3NAsEntry
    MAX-ACCESS      not-accessible
    STATUS          current
    DESCRIPTION     
            "A sequence of npgwMTP3NAs attributes."
    INDEX           { ptConnGroupIndex, ptnpgwMTP3NAsIndex }
    ::= { ptnpgwMTP3NAsTable 1 }

PtnpgwMTP3NAsEntry ::=
    SEQUENCE {
        ptnpgwMTP3NAsParentOID          OBJECT IDENTIFIER,
        ptnpgwMTP3NAsRowStatus          RowStatus,
        ptnpgwMTP3NAsIndex              Integer32
    }

ptnpgwMTP3NAsParentOID OBJECT-TYPE
    SYNTAX          OBJECT IDENTIFIER
    MAX-ACCESS      read-create
    STATUS          current
    DESCRIPTION     
            "The OID of the parent object for this instance"
    ::= { ptnpgwMTP3NAsEntry 253 }

ptnpgwMTP3NAsRowStatus OBJECT-TYPE
    SYNTAX          RowStatus
    MAX-ACCESS      read-create
    STATUS          current
    DESCRIPTION     
            "The row status for the npgwMTP3NAs table"
    ::= { ptnpgwMTP3NAsEntry 254 }

ptnpgwMTP3NAsIndex OBJECT-TYPE
    SYNTAX          Integer32 (-2147483648..2147483647)
    MAX-ACCESS      not-accessible
    STATUS          current
    DESCRIPTION     
            "The row number for the npgwMTP3NAs table"
    ::= { ptnpgwMTP3NAsEntry 255 }

ptnpgwMTP3NA OBJECT IDENTIFIER
    ::= { ptnpgwMTP3NAs 1603 }

ptnpgwMTP3NATable OBJECT-TYPE
    SYNTAX          SEQUENCE OF PtnpgwMTP3NAEntry
    MAX-ACCESS      not-accessible
    STATUS          current
    DESCRIPTION     
            "No description supplied in the proxy config file."
    ::= { ptnpgwMTP3NA 1 }

ptnpgwMTP3NAEntry OBJECT-TYPE
    SYNTAX          PtnpgwMTP3NAEntry
    MAX-ACCESS      not-accessible
    STATUS          current
    DESCRIPTION     
            "A sequence of npgwMTP3NA attributes."
    INDEX           { ptConnGroupIndex, ptnpgwMTP3NAMTP3NAsIndex, 
                      ptnpgwMTP3NAIndex }
    ::= { ptnpgwMTP3NATable 1 }

PtnpgwMTP3NAEntry ::=
    SEQUENCE {
        ptnpgwMTP3NANA                  Integer32,
        ptnpgwMTP3NAStatus              INTEGER,
        ptnpgwMTP3NAMTP3NAsIndex        Integer32,
        ptnpgwMTP3NAActions             INTEGER,
        ptnpgwMTP3NAParentOID           OBJECT IDENTIFIER,
        ptnpgwMTP3NARowStatus           RowStatus,
        ptnpgwMTP3NAIndex               Integer32
    }

ptnpgwMTP3NANA OBJECT-TYPE
    SYNTAX          Integer32 (1..99)
    MAX-ACCESS      read-only
    STATUS          current
    DESCRIPTION     
            "MTP3 Network Appearance"
    ::= { ptnpgwMTP3NAEntry 1 }

ptnpgwMTP3NAStatus OBJECT-TYPE
    SYNTAX          INTEGER { inactive(0), notConnected(1), connected(2), 
                        partiallyConnected(3) }
    MAX-ACCESS      read-only
    STATUS          current
    DESCRIPTION     
            "MTP3 NA connectivity status (INACTIVE, NOT CONNECTED, CONNECTED). \nBased on the per NA connection connectivity status. CONNECTED will be displayed as soon as an MTP3 NA connection is connected. \nAssociated to alarm 1611 (NPGW MTP3 NA Down)."
    ::= { ptnpgwMTP3NAEntry 2 }

ptnpgwMTP3NAMTP3NAsIndex OBJECT-TYPE
    SYNTAX          Integer32 (-2147483648..2147483647)
    MAX-ACCESS      not-accessible
    STATUS          current
    DESCRIPTION     
            "This is the index of the parent type for this object.
             This parent type is MTP3NAs."
    ::= { ptnpgwMTP3NAEntry 242 }

ptnpgwMTP3NAActions OBJECT-TYPE
    SYNTAX          INTEGER { activate(1), deactivate(2) }
    MAX-ACCESS      read-create
    STATUS          current
    DESCRIPTION     
            "The OID of all possible actions for this instance"
    ::= { ptnpgwMTP3NAEntry 252 }

ptnpgwMTP3NAParentOID OBJECT-TYPE
    SYNTAX          OBJECT IDENTIFIER
    MAX-ACCESS      read-create
    STATUS          current
    DESCRIPTION     
            "The OID of the parent object for this instance"
    ::= { ptnpgwMTP3NAEntry 253 }

ptnpgwMTP3NARowStatus OBJECT-TYPE
    SYNTAX          RowStatus
    MAX-ACCESS      read-create
    STATUS          current
    DESCRIPTION     
            "The row status for the npgwMTP3NA table"
    ::= { ptnpgwMTP3NAEntry 254 }

ptnpgwMTP3NAIndex OBJECT-TYPE
    SYNTAX          Integer32 (-2147483648..2147483647)
    MAX-ACCESS      not-accessible
    STATUS          current
    DESCRIPTION     
            "The row number for the npgwMTP3NA table"
    ::= { ptnpgwMTP3NAEntry 255 }

ptnpgwMTP3NAConnection OBJECT IDENTIFIER
    ::= { ptnpgwMTP3NA 1604 }

ptnpgwMTP3NAConnectionTable OBJECT-TYPE
    SYNTAX          SEQUENCE OF PtnpgwMTP3NAConnectionEntry
    MAX-ACCESS      not-accessible
    STATUS          current
    DESCRIPTION     
            "No description supplied in the proxy config file."
    ::= { ptnpgwMTP3NAConnection 1 }

ptnpgwMTP3NAConnectionEntry OBJECT-TYPE
    SYNTAX          PtnpgwMTP3NAConnectionEntry
    MAX-ACCESS      not-accessible
    STATUS          current
    DESCRIPTION     
            "A sequence of npgwMTP3NAConnection attributes."
    INDEX           { ptConnGroupIndex, 
                      ptnpgwMTP3NAConnectionMTP3NAsIndex, 
                      ptnpgwMTP3NAConnectionMTP3NAIndex, 
                      ptnpgwMTP3NAConnectionIndex }
    ::= { ptnpgwMTP3NAConnectionTable 1 }

PtnpgwMTP3NAConnectionEntry ::=
    SEQUENCE {
        ptnpgwMTP3NAConnectionSlot      Integer32,
        ptnpgwMTP3NAConnectionStatus    INTEGER,
        ptnpgwMTP3NAConnectionMTP3NAsIndex  Integer32,
        ptnpgwMTP3NAConnectionMTP3NAIndex Integer32,
        ptnpgwMTP3NAConnectionParentOID OBJECT IDENTIFIER,
        ptnpgwMTP3NAConnectionRowStatus RowStatus,
        ptnpgwMTP3NAConnectionIndex     Integer32
    }

ptnpgwMTP3NAConnectionSlot OBJECT-TYPE
    SYNTAX          Integer32 (-2147483648..2147483647)
    MAX-ACCESS      read-only
    STATUS          current
    DESCRIPTION     
            "Associated slot of the routing CPU for this MTP3 NA connection."
    ::= { ptnpgwMTP3NAConnectionEntry 1 }

ptnpgwMTP3NAConnectionStatus OBJECT-TYPE
    SYNTAX          INTEGER { inactive(0), notConnected(1), connected(2), 
                        partiallyConnected(3) }
    MAX-ACCESS      read-only
    STATUS          current
    DESCRIPTION     
            "MTP3 connectivity status (INACTIVE, NOT CONNECTED, CONNECTED). \nBased on the per slot connectivity status. CONNECTED will be displayed as soon as an MTP3 connection on any slot is connected. \nAssociated to alarm 1613 (NPGW MTP3 NA Connection Down)."
    ::= { ptnpgwMTP3NAConnectionEntry 2 }

ptnpgwMTP3NAConnectionMTP3NAsIndex OBJECT-TYPE
    SYNTAX          Integer32 (-2147483648..2147483647)
    MAX-ACCESS      not-accessible
    STATUS          current
    DESCRIPTION     
            "This is the index of the parent type for this object.
             This parent type is MTP3NAs."
    ::= { ptnpgwMTP3NAConnectionEntry 242 }

ptnpgwMTP3NAConnectionMTP3NAIndex OBJECT-TYPE
    SYNTAX          Integer32 (-2147483648..2147483647)
    MAX-ACCESS      not-accessible
    STATUS          current
    DESCRIPTION     
            "This is the index of the parent type for this object.
             This parent type is MTP3NA."
    ::= { ptnpgwMTP3NAConnectionEntry 243 }

ptnpgwMTP3NAConnectionParentOID OBJECT-TYPE
    SYNTAX          OBJECT IDENTIFIER
    MAX-ACCESS      read-create
    STATUS          current
    DESCRIPTION     
            "The OID of the parent object for this instance"
    ::= { ptnpgwMTP3NAConnectionEntry 253 }

ptnpgwMTP3NAConnectionRowStatus OBJECT-TYPE
    SYNTAX          RowStatus
    MAX-ACCESS      read-create
    STATUS          current
    DESCRIPTION     
            "The row status for the npgwMTP3NAConnection table"
    ::= { ptnpgwMTP3NAConnectionEntry 254 }

ptnpgwMTP3NAConnectionIndex OBJECT-TYPE
    SYNTAX          Integer32 (-2147483648..2147483647)
    MAX-ACCESS      not-accessible
    STATUS          current
    DESCRIPTION     
            "The row number for the npgwMTP3NAConnection table"
    ::= { ptnpgwMTP3NAConnectionEntry 255 }

ptnpgwMTP3Registrations OBJECT IDENTIFIER
    ::= { ptConnGroup 1605 }

ptnpgwMTP3RegistrationsTable OBJECT-TYPE
    SYNTAX          SEQUENCE OF PtnpgwMTP3RegistrationsEntry
    MAX-ACCESS      not-accessible
    STATUS          current
    DESCRIPTION     
            "No description supplied in the proxy config file."
    ::= { ptnpgwMTP3Registrations 1 }

ptnpgwMTP3RegistrationsEntry OBJECT-TYPE
    SYNTAX          PtnpgwMTP3RegistrationsEntry
    MAX-ACCESS      not-accessible
    STATUS          current
    DESCRIPTION     
            "A sequence of npgwMTP3Registrations attributes."
    INDEX           { ptConnGroupIndex, ptnpgwMTP3RegistrationsIndex }
    ::= { ptnpgwMTP3RegistrationsTable 1 }

PtnpgwMTP3RegistrationsEntry ::=
    SEQUENCE {
        ptnpgwMTP3RegistrationsParentOID OBJECT IDENTIFIER,
        ptnpgwMTP3RegistrationsRowStatus RowStatus,
        ptnpgwMTP3RegistrationsIndex    Integer32
    }

ptnpgwMTP3RegistrationsParentOID OBJECT-TYPE
    SYNTAX          OBJECT IDENTIFIER
    MAX-ACCESS      read-create
    STATUS          current
    DESCRIPTION     
            "The OID of the parent object for this instance"
    ::= { ptnpgwMTP3RegistrationsEntry 253 }

ptnpgwMTP3RegistrationsRowStatus OBJECT-TYPE
    SYNTAX          RowStatus
    MAX-ACCESS      read-create
    STATUS          current
    DESCRIPTION     
            "The row status for the npgwMTP3Registrations table"
    ::= { ptnpgwMTP3RegistrationsEntry 254 }

ptnpgwMTP3RegistrationsIndex OBJECT-TYPE
    SYNTAX          Integer32 (-2147483648..2147483647)
    MAX-ACCESS      not-accessible
    STATUS          current
    DESCRIPTION     
            "The row number for the npgwMTP3Registrations table"
    ::= { ptnpgwMTP3RegistrationsEntry 255 }

ptnpgwMTP3Registration OBJECT IDENTIFIER
    ::= { ptnpgwMTP3Registrations 1606 }

ptnpgwMTP3RegistrationTable OBJECT-TYPE
    SYNTAX          SEQUENCE OF PtnpgwMTP3RegistrationEntry
    MAX-ACCESS      not-accessible
    STATUS          current
    DESCRIPTION     
            "No description supplied in the proxy config file."
    ::= { ptnpgwMTP3Registration 1 }

ptnpgwMTP3RegistrationEntry OBJECT-TYPE
    SYNTAX          PtnpgwMTP3RegistrationEntry
    MAX-ACCESS      not-accessible
    STATUS          current
    DESCRIPTION     
            "A sequence of npgwMTP3Registration attributes."
    INDEX           { ptConnGroupIndex, 
                      ptnpgwMTP3RegistrationMTP3RegistrationsIndex, 
                      ptnpgwMTP3RegistrationIndex }
    ::= { ptnpgwMTP3RegistrationTable 1 }

PtnpgwMTP3RegistrationEntry ::=
    SEQUENCE {
        ptnpgwMTP3RegistrationNA        Integer32,
        ptnpgwMTP3RegistrationApplicationID   DisplayString,
        ptnpgwMTP3RegistrationStatus    INTEGER,
        ptnpgwMTP3RegistrationMTP3RegistrationsIndex            Integer32,
        ptnpgwMTP3RegistrationParentOID OBJECT IDENTIFIER,
        ptnpgwMTP3RegistrationRowStatus RowStatus,
        ptnpgwMTP3RegistrationIndex     Integer32
    }

ptnpgwMTP3RegistrationNA OBJECT-TYPE
    SYNTAX          Integer32 (-2147483648..2147483647)
    MAX-ACCESS      read-only
    STATUS          current
    DESCRIPTION     
            "Network Appearance of the NPGW MTP3 service registration"
    ::= { ptnpgwMTP3RegistrationEntry 1 }

ptnpgwMTP3RegistrationApplicationID OBJECT-TYPE
    SYNTAX          DisplayString (SIZE(0..255))
    MAX-ACCESS      read-only
    STATUS          current
    DESCRIPTION     
            "Application ID of the NPGW MTP3 service registration. \nAssociated with the GWST redirection feature. \nValid values: alphanumeric string with - and _ with a maximum of 16 characters (including the null terminating character)."
    ::= { ptnpgwMTP3RegistrationEntry 2 }

ptnpgwMTP3RegistrationStatus OBJECT-TYPE
    SYNTAX          INTEGER { notRegistered(0), partiallyRegistered(1), 
                        registered(2) }
    MAX-ACCESS      read-only
    STATUS          current
    DESCRIPTION     
            "Status of the Application ID registration. \nFully registered when all MTP3 connections have successfully registered the Application ID. \nValid values: NOT REGISTERED, PARTIALLY REGISTERED, REGISTERED."
    ::= { ptnpgwMTP3RegistrationEntry 3 }

ptnpgwMTP3RegistrationMTP3RegistrationsIndex OBJECT-TYPE
    SYNTAX          Integer32 (-2147483648..2147483647)
    MAX-ACCESS      not-accessible
    STATUS          current
    DESCRIPTION     
            "This is the index of the parent type for this object.
             This parent type is MTP3Registrations."
    ::= { ptnpgwMTP3RegistrationEntry 242 }

ptnpgwMTP3RegistrationParentOID OBJECT-TYPE
    SYNTAX          OBJECT IDENTIFIER
    MAX-ACCESS      read-create
    STATUS          current
    DESCRIPTION     
            "The OID of the parent object for this instance"
    ::= { ptnpgwMTP3RegistrationEntry 253 }

ptnpgwMTP3RegistrationRowStatus OBJECT-TYPE
    SYNTAX          RowStatus
    MAX-ACCESS      read-create
    STATUS          current
    DESCRIPTION     
            "The row status for the npgwMTP3Registration table"
    ::= { ptnpgwMTP3RegistrationEntry 254 }

ptnpgwMTP3RegistrationIndex OBJECT-TYPE
    SYNTAX          Integer32 (-2147483648..2147483647)
    MAX-ACCESS      not-accessible
    STATUS          current
    DESCRIPTION     
            "The row number for the npgwMTP3Registration table"
    ::= { ptnpgwMTP3RegistrationEntry 255 }

ptnpgwSCCPNAs OBJECT IDENTIFIER
    ::= { ptConnGroup 1607 }

ptnpgwSCCPNAsTable OBJECT-TYPE
    SYNTAX          SEQUENCE OF PtnpgwSCCPNAsEntry
    MAX-ACCESS      not-accessible
    STATUS          current
    DESCRIPTION     
            "No description supplied in the proxy config file."
    ::= { ptnpgwSCCPNAs 1 }

ptnpgwSCCPNAsEntry OBJECT-TYPE
    SYNTAX          PtnpgwSCCPNAsEntry
    MAX-ACCESS      not-accessible
    STATUS          current
    DESCRIPTION     
            "A sequence of npgwSCCPNAs attributes."
    INDEX           { ptConnGroupIndex, ptnpgwSCCPNAsIndex }
    ::= { ptnpgwSCCPNAsTable 1 }

PtnpgwSCCPNAsEntry ::=
    SEQUENCE {
        ptnpgwSCCPNAsParentOID          OBJECT IDENTIFIER,
        ptnpgwSCCPNAsRowStatus          RowStatus,
        ptnpgwSCCPNAsIndex              Integer32
    }

ptnpgwSCCPNAsParentOID OBJECT-TYPE
    SYNTAX          OBJECT IDENTIFIER
    MAX-ACCESS      read-create
    STATUS          current
    DESCRIPTION     
            "The OID of the parent object for this instance"
    ::= { ptnpgwSCCPNAsEntry 253 }

ptnpgwSCCPNAsRowStatus OBJECT-TYPE
    SYNTAX          RowStatus
    MAX-ACCESS      read-create
    STATUS          current
    DESCRIPTION     
            "The row status for the npgwSCCPNAs table"
    ::= { ptnpgwSCCPNAsEntry 254 }

ptnpgwSCCPNAsIndex OBJECT-TYPE
    SYNTAX          Integer32 (-2147483648..2147483647)
    MAX-ACCESS      not-accessible
    STATUS          current
    DESCRIPTION     
            "The row number for the npgwSCCPNAs table"
    ::= { ptnpgwSCCPNAsEntry 255 }

ptnpgwSCCPNA OBJECT IDENTIFIER
    ::= { ptnpgwSCCPNAs 1608 }

ptnpgwSCCPNATable OBJECT-TYPE
    SYNTAX          SEQUENCE OF PtnpgwSCCPNAEntry
    MAX-ACCESS      not-accessible
    STATUS          current
    DESCRIPTION     
            "No description supplied in the proxy config file."
    ::= { ptnpgwSCCPNA 1 }

ptnpgwSCCPNAEntry OBJECT-TYPE
    SYNTAX          PtnpgwSCCPNAEntry
    MAX-ACCESS      not-accessible
    STATUS          current
    DESCRIPTION     
            "A sequence of npgwSCCPNA attributes."
    INDEX           { ptConnGroupIndex, ptnpgwSCCPNASCCPNAsIndex, 
                      ptnpgwSCCPNAIndex }
    ::= { ptnpgwSCCPNATable 1 }

PtnpgwSCCPNAEntry ::=
    SEQUENCE {
        ptnpgwSCCPNANA                  Integer32,
        ptnpgwSCCPNAStatus              INTEGER,
        ptnpgwSCCPNASCCPNAsIndex        Integer32,
        ptnpgwSCCPNAActions             INTEGER,
        ptnpgwSCCPNAParentOID           OBJECT IDENTIFIER,
        ptnpgwSCCPNARowStatus           RowStatus,
        ptnpgwSCCPNAIndex               Integer32
    }

ptnpgwSCCPNANA OBJECT-TYPE
    SYNTAX          Integer32 (1..99)
    MAX-ACCESS      read-only
    STATUS          current
    DESCRIPTION     
            "SCCP Network Appearance"
    ::= { ptnpgwSCCPNAEntry 1 }

ptnpgwSCCPNAStatus OBJECT-TYPE
    SYNTAX          INTEGER { inactive(0), notConnected(1), connected(2), 
                        partiallyConnected(3) }
    MAX-ACCESS      read-only
    STATUS          current
    DESCRIPTION     
            "SCCP NA connectivity status (INACTIVE, NOT CONNECTED, CONNECTED). \nBased on the per NA connection connectivity status. CONNECTED will be displayed as soon as an SCCP NA connection is connected. \nAssociated to alarm 1603 (NPGW SCCP NA Down)."
    ::= { ptnpgwSCCPNAEntry 2 }

ptnpgwSCCPNASCCPNAsIndex OBJECT-TYPE
    SYNTAX          Integer32 (-2147483648..2147483647)
    MAX-ACCESS      not-accessible
    STATUS          current
    DESCRIPTION     
            "This is the index of the parent type for this object.
             This parent type is SCCPNAs."
    ::= { ptnpgwSCCPNAEntry 242 }

ptnpgwSCCPNAActions OBJECT-TYPE
    SYNTAX          INTEGER { activate(1), deactivate(2) }
    MAX-ACCESS      read-create
    STATUS          current
    DESCRIPTION     
            "The OID of all possible actions for this instance"
    ::= { ptnpgwSCCPNAEntry 252 }

ptnpgwSCCPNAParentOID OBJECT-TYPE
    SYNTAX          OBJECT IDENTIFIER
    MAX-ACCESS      read-create
    STATUS          current
    DESCRIPTION     
            "The OID of the parent object for this instance"
    ::= { ptnpgwSCCPNAEntry 253 }

ptnpgwSCCPNARowStatus OBJECT-TYPE
    SYNTAX          RowStatus
    MAX-ACCESS      read-create
    STATUS          current
    DESCRIPTION     
            "The row status for the npgwSCCPNA table"
    ::= { ptnpgwSCCPNAEntry 254 }

ptnpgwSCCPNAIndex OBJECT-TYPE
    SYNTAX          Integer32 (-2147483648..2147483647)
    MAX-ACCESS      not-accessible
    STATUS          current
    DESCRIPTION     
            "The row number for the npgwSCCPNA table"
    ::= { ptnpgwSCCPNAEntry 255 }

ptnpgwSCCPNAConnection OBJECT IDENTIFIER
    ::= { ptnpgwSCCPNA 1609 }

ptnpgwSCCPNAConnectionTable OBJECT-TYPE
    SYNTAX          SEQUENCE OF PtnpgwSCCPNAConnectionEntry
    MAX-ACCESS      not-accessible
    STATUS          current
    DESCRIPTION     
            "No description supplied in the proxy config file."
    ::= { ptnpgwSCCPNAConnection 1 }

ptnpgwSCCPNAConnectionEntry OBJECT-TYPE
    SYNTAX          PtnpgwSCCPNAConnectionEntry
    MAX-ACCESS      not-accessible
    STATUS          current
    DESCRIPTION     
            "A sequence of npgwSCCPNAConnection attributes."
    INDEX           { ptConnGroupIndex, 
                      ptnpgwSCCPNAConnectionSCCPNAsIndex, 
                      ptnpgwSCCPNAConnectionSCCPNAIndex, 
                      ptnpgwSCCPNAConnectionIndex }
    ::= { ptnpgwSCCPNAConnectionTable 1 }

PtnpgwSCCPNAConnectionEntry ::=
    SEQUENCE {
        ptnpgwSCCPNAConnectionSlot      Integer32,
        ptnpgwSCCPNAConnectionStatus    INTEGER,
        ptnpgwSCCPNAConnectionSCCPNAsIndex  Integer32,
        ptnpgwSCCPNAConnectionSCCPNAIndex Integer32,
        ptnpgwSCCPNAConnectionParentOID OBJECT IDENTIFIER,
        ptnpgwSCCPNAConnectionRowStatus RowStatus,
        ptnpgwSCCPNAConnectionIndex     Integer32
    }

ptnpgwSCCPNAConnectionSlot OBJECT-TYPE
    SYNTAX          Integer32 (-2147483648..2147483647)
    MAX-ACCESS      read-only
    STATUS          current
    DESCRIPTION     
            "Associated slot of the routing CPU for this SCCP NA connection."
    ::= { ptnpgwSCCPNAConnectionEntry 1 }

ptnpgwSCCPNAConnectionStatus OBJECT-TYPE
    SYNTAX          INTEGER { inactive(0), notConnected(1), connected(2), 
                        partiallyConnected(3) }
    MAX-ACCESS      read-only
    STATUS          current
    DESCRIPTION     
            "SCCP connectivity status (INACTIVE, NOT CONNECTED, CONNECTED). \nBased on the per slot connectivity status. CONNECTED will be displayed as soon as an SCCP connection on any slot is connected. \nAssociated to alarm 1605 (NPGW SCCP NA Connection Down)."
    ::= { ptnpgwSCCPNAConnectionEntry 2 }

ptnpgwSCCPNAConnectionSCCPNAsIndex OBJECT-TYPE
    SYNTAX          Integer32 (-2147483648..2147483647)
    MAX-ACCESS      not-accessible
    STATUS          current
    DESCRIPTION     
            "This is the index of the parent type for this object.
             This parent type is SCCPNAs."
    ::= { ptnpgwSCCPNAConnectionEntry 242 }

ptnpgwSCCPNAConnectionSCCPNAIndex OBJECT-TYPE
    SYNTAX          Integer32 (-2147483648..2147483647)
    MAX-ACCESS      not-accessible
    STATUS          current
    DESCRIPTION     
            "This is the index of the parent type for this object.
             This parent type is SCCPNA."
    ::= { ptnpgwSCCPNAConnectionEntry 243 }

ptnpgwSCCPNAConnectionParentOID OBJECT-TYPE
    SYNTAX          OBJECT IDENTIFIER
    MAX-ACCESS      read-create
    STATUS          current
    DESCRIPTION     
            "The OID of the parent object for this instance"
    ::= { ptnpgwSCCPNAConnectionEntry 253 }

ptnpgwSCCPNAConnectionRowStatus OBJECT-TYPE
    SYNTAX          RowStatus
    MAX-ACCESS      read-create
    STATUS          current
    DESCRIPTION     
            "The row status for the npgwSCCPNAConnection table"
    ::= { ptnpgwSCCPNAConnectionEntry 254 }

ptnpgwSCCPNAConnectionIndex OBJECT-TYPE
    SYNTAX          Integer32 (-2147483648..2147483647)
    MAX-ACCESS      not-accessible
    STATUS          current
    DESCRIPTION     
            "The row number for the npgwSCCPNAConnection table"
    ::= { ptnpgwSCCPNAConnectionEntry 255 }

ptnpgwSCCPRegistrations OBJECT IDENTIFIER
    ::= { ptConnGroup 1610 }

ptnpgwSCCPRegistrationsTable OBJECT-TYPE
    SYNTAX          SEQUENCE OF PtnpgwSCCPRegistrationsEntry
    MAX-ACCESS      not-accessible
    STATUS          current
    DESCRIPTION     
            "No description supplied in the proxy config file."
    ::= { ptnpgwSCCPRegistrations 1 }

ptnpgwSCCPRegistrationsEntry OBJECT-TYPE
    SYNTAX          PtnpgwSCCPRegistrationsEntry
    MAX-ACCESS      not-accessible
    STATUS          current
    DESCRIPTION     
            "A sequence of npgwSCCPRegistrations attributes."
    INDEX           { ptConnGroupIndex, ptnpgwSCCPRegistrationsIndex }
    ::= { ptnpgwSCCPRegistrationsTable 1 }

PtnpgwSCCPRegistrationsEntry ::=
    SEQUENCE {
        ptnpgwSCCPRegistrationsParentOID OBJECT IDENTIFIER,
        ptnpgwSCCPRegistrationsRowStatus RowStatus,
        ptnpgwSCCPRegistrationsIndex    Integer32
    }

ptnpgwSCCPRegistrationsParentOID OBJECT-TYPE
    SYNTAX          OBJECT IDENTIFIER
    MAX-ACCESS      read-create
    STATUS          current
    DESCRIPTION     
            "The OID of the parent object for this instance"
    ::= { ptnpgwSCCPRegistrationsEntry 253 }

ptnpgwSCCPRegistrationsRowStatus OBJECT-TYPE
    SYNTAX          RowStatus
    MAX-ACCESS      read-create
    STATUS          current
    DESCRIPTION     
            "The row status for the npgwSCCPRegistrations table"
    ::= { ptnpgwSCCPRegistrationsEntry 254 }

ptnpgwSCCPRegistrationsIndex OBJECT-TYPE
    SYNTAX          Integer32 (-2147483648..2147483647)
    MAX-ACCESS      not-accessible
    STATUS          current
    DESCRIPTION     
            "The row number for the npgwSCCPRegistrations table"
    ::= { ptnpgwSCCPRegistrationsEntry 255 }

ptnpgwSCCPPCSSNRegistration OBJECT IDENTIFIER
    ::= { ptnpgwSCCPRegistrations 1611 }

ptnpgwSCCPPCSSNRegistrationTable OBJECT-TYPE
    SYNTAX          SEQUENCE OF PtnpgwSCCPPCSSNRegistrationEntry
    MAX-ACCESS      not-accessible
    STATUS          current
    DESCRIPTION     
            "No description supplied in the proxy config file."
    ::= { ptnpgwSCCPPCSSNRegistration 1 }

ptnpgwSCCPPCSSNRegistrationEntry OBJECT-TYPE
    SYNTAX          PtnpgwSCCPPCSSNRegistrationEntry
    MAX-ACCESS      not-accessible
    STATUS          current
    DESCRIPTION     
            "A sequence of npgwSCCPPCSSNRegistration attributes."
    INDEX           { ptConnGroupIndex, 
                      ptnpgwSCCPPCSSNRegistrationSCCPRegistrationsIndex, 
                      ptnpgwSCCPPCSSNRegistrationIndex }
    ::= { ptnpgwSCCPPCSSNRegistrationTable 1 }

PtnpgwSCCPPCSSNRegistrationEntry ::=
    SEQUENCE {
        ptnpgwSCCPPCSSNRegistrationNA   Integer32,
        ptnpgwSCCPPCSSNRegistrationPC   Integer32,
        ptnpgwSCCPPCSSNRegistrationSSN  Integer32,
        ptnpgwSCCPPCSSNRegistrationStatus INTEGER,
        ptnpgwSCCPPCSSNRegistrationSCCPRegistrationsIndex                 Integer32,
        ptnpgwSCCPPCSSNRegistrationParentOID    OBJECT IDENTIFIER,
        ptnpgwSCCPPCSSNRegistrationRowStatus    RowStatus,
        ptnpgwSCCPPCSSNRegistrationIndex Integer32
    }

ptnpgwSCCPPCSSNRegistrationNA OBJECT-TYPE
    SYNTAX          Integer32 (-2147483648..2147483647)
    MAX-ACCESS      read-only
    STATUS          current
    DESCRIPTION     
            "Network Appearance of the NPGW SCCP service registration"
    ::= { ptnpgwSCCPPCSSNRegistrationEntry 1 }

ptnpgwSCCPPCSSNRegistrationPC OBJECT-TYPE
    SYNTAX          Integer32 (-2147483648..2147483647)
    MAX-ACCESS      read-only
    STATUS          current
    DESCRIPTION     
            "Pointcode of the NPGW SCCP service registration."
    ::= { ptnpgwSCCPPCSSNRegistrationEntry 2 }

ptnpgwSCCPPCSSNRegistrationSSN OBJECT-TYPE
    SYNTAX          Integer32 (2..255)
    MAX-ACCESS      read-only
    STATUS          current
    DESCRIPTION     
            "Subsystem number of the NPGW SCCP service registration (2 to 255). \nSome standard SSN as per latest specifications Q.0713 (ITU) and GR-246 (ANSI) include: 5 (MAP), 6 (HLR), 7 (VLR), 8 (MSC)."
    ::= { ptnpgwSCCPPCSSNRegistrationEntry 3 }

ptnpgwSCCPPCSSNRegistrationStatus OBJECT-TYPE
    SYNTAX          INTEGER { notRegistered(0), partiallyRegistered(1), 
                        registered(2) }
    MAX-ACCESS      read-only
    STATUS          current
    DESCRIPTION     
            "Status of the PC-SSN registration. \nFully registered when all SCCP connections have successfully registered the PC-SSN. \nValid values: NOT REGISTERED, PARTIALLY REGISTERED, REGISTERED."
    ::= { ptnpgwSCCPPCSSNRegistrationEntry 4 }

ptnpgwSCCPPCSSNRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptnpgwSCCPPCSSNRegistrationEntry 242 }

ptnpgwSCCPPCSSNRegistrationParentOID OBJECT-TYPE
    SYNTAX          OBJECT IDENTIFIER
    MAX-ACCESS      read-create
    STATUS          current
    DESCRIPTION     
            "The OID of the parent object for this instance"
    ::= { ptnpgwSCCPPCSSNRegistrationEntry 253 }

ptnpgwSCCPPCSSNRegistrationRowStatus OBJECT-TYPE
    SYNTAX          RowStatus
    MAX-ACCESS      read-create
    STATUS          current
    DESCRIPTION     
            "The row status for the npgwSCCPPCSSNRegistration table"
    ::= { ptnpgwSCCPPCSSNRegistrationEntry 254 }

ptnpgwSCCPPCSSNRegistrationIndex OBJECT-TYPE
    SYNTAX          Integer32 (-2147483648..2147483647)
    MAX-ACCESS      not-accessible
    STATUS          current
    DESCRIPTION     
            "The row number for the npgwSCCPPCSSNRegistration table"
    ::= { ptnpgwSCCPPCSSNRegistrationEntry 255 }

ptnpgwSCCPAppIDRegistration OBJECT IDENTIFIER
    ::= { ptnpgwSCCPRegistrations 1612 }

ptnpgwSCCPAppIDRegistrationTable OBJECT-TYPE
    SYNTAX          SEQUENCE OF PtnpgwSCCPAppIDRegistrationEntry
    MAX-ACCESS      not-accessible
    STATUS          current
    DESCRIPTION     
            "No description supplied in the proxy config file."
    ::= { ptnpgwSCCPAppIDRegistration 1 }

ptnpgwSCCPAppIDRegistrationEntry OBJECT-TYPE
    SYNTAX          PtnpgwSCCPAppIDRegistrationEntry
    MAX-ACCESS      not-accessible
    STATUS          current
    DESCRIPTION     
            "A sequence of npgwSCCPAppIDRegistration attributes."
    INDEX           { ptConnGroupIndex, 
                      ptnpgwSCCPAppIDRegistrationSCCPRegistrationsIndex, 
                      ptnpgwSCCPAppIDRegistrationIndex }
    ::= { ptnpgwSCCPAppIDRegistrationTable 1 }

PtnpgwSCCPAppIDRegistrationEntry ::=
    SEQUENCE {
        ptnpgwSCCPAppIDRegistrationNA   Integer32,
        ptnpgwSCCPAppIDRegistrationApplicationID        DisplayString,
        ptnpgwSCCPAppIDRegistrationStatus INTEGER,
        ptnpgwSCCPAppIDRegistrationSCCPRegistrationsIndex                 Integer32,
        ptnpgwSCCPAppIDRegistrationParentOID    OBJECT IDENTIFIER,
        ptnpgwSCCPAppIDRegistrationRowStatus    RowStatus,
        ptnpgwSCCPAppIDRegistrationIndex Integer32
    }

ptnpgwSCCPAppIDRegistrationNA OBJECT-TYPE
    SYNTAX          Integer32 (-2147483648..2147483647)
    MAX-ACCESS      read-only
    STATUS          current
    DESCRIPTION     
            "Network Appearance of the NPGW SCCP service registration"
    ::= { ptnpgwSCCPAppIDRegistrationEntry 1 }

ptnpgwSCCPAppIDRegistrationApplicationID OBJECT-TYPE
    SYNTAX          DisplayString (SIZE(0..255))
    MAX-ACCESS      read-only
    STATUS          current
    DESCRIPTION     
            "Application ID of the NPGW SCCP service registration. \nAssociated with the GWST redirection feature. \nValid values: alphanumeric string with - and _ with a maximum of 16 characters (including the null terminating character)."
    ::= { ptnpgwSCCPAppIDRegistrationEntry 2 }

ptnpgwSCCPAppIDRegistrationStatus OBJECT-TYPE
    SYNTAX          INTEGER { notRegistered(0), partiallyRegistered(1), 
                        registered(2) }
    MAX-ACCESS      read-only
    STATUS          current
    DESCRIPTION     
            "Status of the Application ID registration. \nFully registered when all SCCP connections have successfully registered the Application ID. \nValid values: NOT REGISTERED, PARTIALLY REGISTERED, REGISTERED."
    ::= { ptnpgwSCCPAppIDRegistrationEntry 3 }

ptnpgwSCCPAppIDRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptnpgwSCCPAppIDRegistrationEntry 242 }

ptnpgwSCCPAppIDRegistrationParentOID OBJECT-TYPE
    SYNTAX          OBJECT IDENTIFIER
    MAX-ACCESS      read-create
    STATUS          current
    DESCRIPTION     
            "The OID of the parent object for this instance"
    ::= { ptnpgwSCCPAppIDRegistrationEntry 253 }

ptnpgwSCCPAppIDRegistrationRowStatus OBJECT-TYPE
    SYNTAX          RowStatus
    MAX-ACCESS      read-create
    STATUS          current
    DESCRIPTION     
            "The row status for the npgwSCCPAppIDRegistration table"
    ::= { ptnpgwSCCPAppIDRegistrationEntry 254 }

ptnpgwSCCPAppIDRegistrationIndex OBJECT-TYPE
    SYNTAX          Integer32 (-2147483648..2147483647)
    MAX-ACCESS      not-accessible
    STATUS          current
    DESCRIPTION     
            "The row number for the npgwSCCPAppIDRegistration table"
    ::= { ptnpgwSCCPAppIDRegistrationEntry 255 }

ptnpgwINAPExternalNPs OBJECT IDENTIFIER
    ::= { ptConnGroup 1613 }

ptnpgwINAPExternalNPsTable OBJECT-TYPE
    SYNTAX          SEQUENCE OF PtnpgwINAPExternalNPsEntry
    MAX-ACCESS      not-accessible
    STATUS          current
    DESCRIPTION     
            "No description supplied in the proxy config file."
    ::= { ptnpgwINAPExternalNPs 1 }

ptnpgwINAPExternalNPsEntry OBJECT-TYPE
    SYNTAX          PtnpgwINAPExternalNPsEntry
    MAX-ACCESS      not-accessible
    STATUS          current
    DESCRIPTION     
            "A sequence of npgwINAPExternalNPs attributes."
    INDEX           { ptConnGroupIndex, ptnpgwINAPExternalNPsIndex }
    ::= { ptnpgwINAPExternalNPsTable 1 }

PtnpgwINAPExternalNPsEntry ::=
    SEQUENCE {
        ptnpgwINAPExternalNPsParentOID  OBJECT IDENTIFIER,
        ptnpgwINAPExternalNPsRowStatus  RowStatus,
        ptnpgwINAPExternalNPsIndex      Integer32
    }

ptnpgwINAPExternalNPsParentOID OBJECT-TYPE
    SYNTAX          OBJECT IDENTIFIER
    MAX-ACCESS      read-create
    STATUS          current
    DESCRIPTION     
            "The OID of the parent object for this instance"
    ::= { ptnpgwINAPExternalNPsEntry 253 }

ptnpgwINAPExternalNPsRowStatus OBJECT-TYPE
    SYNTAX          RowStatus
    MAX-ACCESS      read-create
    STATUS          current
    DESCRIPTION     
            "The row status for the npgwINAPExternalNPs table"
    ::= { ptnpgwINAPExternalNPsEntry 254 }

ptnpgwINAPExternalNPsIndex OBJECT-TYPE
    SYNTAX          Integer32 (-2147483648..2147483647)
    MAX-ACCESS      not-accessible
    STATUS          current
    DESCRIPTION     
            "The row number for the npgwINAPExternalNPs table"
    ::= { ptnpgwINAPExternalNPsEntry 255 }

ptnpgwINAPExternalNP OBJECT IDENTIFIER
    ::= { ptnpgwINAPExternalNPs 1614 }

ptnpgwINAPExternalNPTable OBJECT-TYPE
    SYNTAX          SEQUENCE OF PtnpgwINAPExternalNPEntry
    MAX-ACCESS      not-accessible
    STATUS          current
    DESCRIPTION     
            "No description supplied in the proxy config file."
    ::= { ptnpgwINAPExternalNP 1 }

ptnpgwINAPExternalNPEntry OBJECT-TYPE
    SYNTAX          PtnpgwINAPExternalNPEntry
    MAX-ACCESS      not-accessible
    STATUS          current
    DESCRIPTION     
            "A sequence of npgwINAPExternalNP attributes."
    INDEX           { ptConnGroupIndex, 
                      ptnpgwINAPExternalNPINAPExternalNPsIndex, 
                      ptnpgwINAPExternalNPIndex }
    ::= { ptnpgwINAPExternalNPTable 1 }

PtnpgwINAPExternalNPEntry ::=
    SEQUENCE {
        ptnpgwINAPExternalNPApplicationID DisplayString,
        ptnpgwINAPExternalNPNA          Integer32,
        ptnpgwINAPExternalNPExternalNPE164  DisplayString,
        ptnpgwINAPExternalNPInitialDPSSN Integer32,
        ptnpgwINAPExternalNPInitialDPApplicationContext               DisplayString,
        ptnpgwINAPExternalNPInitialDPServiceKey       Integer32,
        ptnpgwINAPExternalNPInitialDPE164Calling        DisplayString,
        ptnpgwINAPExternalNPInitialDPEDPSupport       INTEGER,
        ptnpgwINAPExternalNPINAPContinuePrefix      DisplayString,
        ptnpgwINAPExternalNPINAPExternalNPsIndex        Integer32,
        ptnpgwINAPExternalNPParentOID   OBJECT IDENTIFIER,
        ptnpgwINAPExternalNPRowStatus   RowStatus,
        ptnpgwINAPExternalNPIndex       Integer32
    }

ptnpgwINAPExternalNPApplicationID OBJECT-TYPE
    SYNTAX          DisplayString (SIZE(0..255))
    MAX-ACCESS      read-only
    STATUS          current
    DESCRIPTION     
            "Application ID representing the INAP External NP. \nAssociated with the GWST redirection feature. \nValid values: alphanumeric string with - and _ with a maximum of 16 characters."
    ::= { ptnpgwINAPExternalNPEntry 1 }

ptnpgwINAPExternalNPNA OBJECT-TYPE
    SYNTAX          Integer32 (1..99)
    MAX-ACCESS      read-create
    STATUS          current
    DESCRIPTION     
            "INAP External NP associated network appearance. \nCorresponding SCCP NA must be defined."
    ::= { ptnpgwINAPExternalNPEntry 2 }

ptnpgwINAPExternalNPExternalNPE164 OBJECT-TYPE
    SYNTAX          DisplayString (SIZE(0..255))
    MAX-ACCESS      read-create
    STATUS          current
    DESCRIPTION     
            "INAP External NP E.164 number. \nGT routed INAP queries are sent to this address."
    ::= { ptnpgwINAPExternalNPEntry 3 }

ptnpgwINAPExternalNPInitialDPSSN OBJECT-TYPE
    SYNTAX          Integer32
    MAX-ACCESS      read-create
    STATUS          current
    DESCRIPTION     
            "INAP Initial-DP SCCP Called & Calling Subsystem Number. \nDefault of 12 (INAP)."
    ::= { ptnpgwINAPExternalNPEntry 4 }

ptnpgwINAPExternalNPInitialDPApplicationContext OBJECT-TYPE
    SYNTAX          DisplayString (SIZE(0..255))
    MAX-ACCESS      read-create
    STATUS          current
    DESCRIPTION     
            "INAP Initial-DP Dialogue Portion Application Context. \nOID formatted string. \nDefault of 0.3.144.12.1.1.1.0."
    ::= { ptnpgwINAPExternalNPEntry 5 }

ptnpgwINAPExternalNPInitialDPServiceKey OBJECT-TYPE
    SYNTAX          Integer32
    MAX-ACCESS      read-create
    STATUS          current
    DESCRIPTION     
            "INAP Initial-DP mandatory Service Key parameter. \nDefault of 15."
    ::= { ptnpgwINAPExternalNPEntry 6 }

ptnpgwINAPExternalNPInitialDPE164Calling OBJECT-TYPE
    SYNTAX          DisplayString (SIZE(0..255))
    MAX-ACCESS      read-create
    STATUS          current
    DESCRIPTION     
            "INAP Initial-DP Calling Party Number E.164 signals. \nThe generated INAP Initial-DP query will include these E.164 digits with the International nature of address in the Calling Party Number parameter."
    ::= { ptnpgwINAPExternalNPEntry 7 }

ptnpgwINAPExternalNPInitialDPEDPSupport OBJECT-TYPE
    SYNTAX          INTEGER { disabled(0), enabled(1) }
    MAX-ACCESS      read-create
    STATUS          current
    DESCRIPTION     
            "INAP Initial-DP optional EDP parameter support. \nIf ENABLED, the EventTypeBCSM parameter (tag 0x9c) is added with LI of 1 and value of analyzedInformation (0x03). \nDefault of DISABLED."
    ::= { ptnpgwINAPExternalNPEntry 8 }

ptnpgwINAPExternalNPINAPContinuePrefix OBJECT-TYPE
    SYNTAX          DisplayString (SIZE(0..255))
    MAX-ACCESS      read-create
    STATUS          current
    DESCRIPTION     
            "Prefix added to the MTP3 Called Party Address signals for GT routing of the intercepted message based on an INAP Continue response. \nMaximum size is 6 digits. Hexadecimal values supported."
    ::= { ptnpgwINAPExternalNPEntry 9 }

ptnpgwINAPExternalNPINAPExternalNPsIndex OBJECT-TYPE
    SYNTAX          Integer32 (-2147483648..2147483647)
    MAX-ACCESS      not-accessible
    STATUS          current
    DESCRIPTION     
            "This is the index of the parent type for this object.
             This parent type is INAPExternalNPs."
    ::= { ptnpgwINAPExternalNPEntry 242 }

ptnpgwINAPExternalNPParentOID OBJECT-TYPE
    SYNTAX          OBJECT IDENTIFIER
    MAX-ACCESS      read-create
    STATUS          current
    DESCRIPTION     
            "The OID of the parent object for this instance"
    ::= { ptnpgwINAPExternalNPEntry 253 }

ptnpgwINAPExternalNPRowStatus OBJECT-TYPE
    SYNTAX          RowStatus
    MAX-ACCESS      read-create
    STATUS          current
    DESCRIPTION     
            "The row status for the npgwINAPExternalNP table"
    ::= { ptnpgwINAPExternalNPEntry 254 }

ptnpgwINAPExternalNPIndex OBJECT-TYPE
    SYNTAX          Integer32 (-2147483648..2147483647)
    MAX-ACCESS      not-accessible
    STATUS          current
    DESCRIPTION     
            "The row number for the npgwINAPExternalNP table"
    ::= { ptnpgwINAPExternalNPEntry 255 }

ptnpgwPSXNPServices OBJECT IDENTIFIER
    ::= { ptConnGroup 1615 }

ptnpgwPSXNPServicesTable OBJECT-TYPE
    SYNTAX          SEQUENCE OF PtnpgwPSXNPServicesEntry
    MAX-ACCESS      not-accessible
    STATUS          current
    DESCRIPTION     
            "No description supplied in the proxy config file."
    ::= { ptnpgwPSXNPServices 1 }

ptnpgwPSXNPServicesEntry OBJECT-TYPE
    SYNTAX          PtnpgwPSXNPServicesEntry
    MAX-ACCESS      not-accessible
    STATUS          current
    DESCRIPTION     
            "A sequence of npgwPSXNPServices attributes."
    INDEX           { ptConnGroupIndex, ptnpgwPSXNPServicesIndex }
    ::= { ptnpgwPSXNPServicesTable 1 }

PtnpgwPSXNPServicesEntry ::=
    SEQUENCE {
        ptnpgwPSXNPServicesParentOID    OBJECT IDENTIFIER,
        ptnpgwPSXNPServicesRowStatus    RowStatus,
        ptnpgwPSXNPServicesIndex        Integer32
    }

ptnpgwPSXNPServicesParentOID OBJECT-TYPE
    SYNTAX          OBJECT IDENTIFIER
    MAX-ACCESS      read-create
    STATUS          current
    DESCRIPTION     
            "The OID of the parent object for this instance"
    ::= { ptnpgwPSXNPServicesEntry 253 }

ptnpgwPSXNPServicesRowStatus OBJECT-TYPE
    SYNTAX          RowStatus
    MAX-ACCESS      read-create
    STATUS          current
    DESCRIPTION     
            "The row status for the npgwPSXNPServices table"
    ::= { ptnpgwPSXNPServicesEntry 254 }

ptnpgwPSXNPServicesIndex OBJECT-TYPE
    SYNTAX          Integer32 (-2147483648..2147483647)
    MAX-ACCESS      not-accessible
    STATUS          current
    DESCRIPTION     
            "The row number for the npgwPSXNPServices table"
    ::= { ptnpgwPSXNPServicesEntry 255 }

ptnpgwPSXNPService OBJECT IDENTIFIER
    ::= { ptnpgwPSXNPServices 1616 }

ptnpgwPSXNPServiceTable OBJECT-TYPE
    SYNTAX          SEQUENCE OF PtnpgwPSXNPServiceEntry
    MAX-ACCESS      not-accessible
    STATUS          current
    DESCRIPTION     
            "No description supplied in the proxy config file."
    ::= { ptnpgwPSXNPService 1 }

ptnpgwPSXNPServiceEntry OBJECT-TYPE
    SYNTAX          PtnpgwPSXNPServiceEntry
    MAX-ACCESS      not-accessible
    STATUS          current
    DESCRIPTION     
            "A sequence of npgwPSXNPService attributes."
    INDEX           { ptConnGroupIndex, 
                      ptnpgwPSXNPServicePSXNPServicesIndex, 
                      ptnpgwPSXNPServiceIndex }
    ::= { ptnpgwPSXNPServiceTable 1 }

PtnpgwPSXNPServiceEntry ::=
    SEQUENCE {
        ptnpgwPSXNPServiceServiceType   INTEGER,
        ptnpgwPSXNPServiceApplicationID DisplayString,
        ptnpgwPSXNPServicePrimaryPSXName DisplayString,
        ptnpgwPSXNPServiceSecondaryPSXName  DisplayString,
        ptnpgwPSXNPServicePSXNPServicesIndex    Integer32,
        ptnpgwPSXNPServiceParentOID     OBJECT IDENTIFIER,
        ptnpgwPSXNPServiceRowStatus     RowStatus,
        ptnpgwPSXNPServiceIndex         Integer32
    }

ptnpgwPSXNPServiceServiceType OBJECT-TYPE
    SYNTAX          INTEGER { triggerlessIsup(0) }
    MAX-ACCESS      read-only
    STATUS          current
    DESCRIPTION     
            "PSX NP Service Type (ISUP TRIGGERLESS)"
    ::= { ptnpgwPSXNPServiceEntry 1 }

ptnpgwPSXNPServiceApplicationID OBJECT-TYPE
    SYNTAX          DisplayString (SIZE(0..255))
    MAX-ACCESS      read-only
    STATUS          current
    DESCRIPTION     
            "Application ID representing the PSX NP. \nAssociated with the GWST redirection feature. \nValid values: alphanumeric string with - and _ with a maximum of 16 characters."
    ::= { ptnpgwPSXNPServiceEntry 2 }

ptnpgwPSXNPServicePrimaryPSXName OBJECT-TYPE
    SYNTAX          DisplayString (SIZE(0..255))
    MAX-ACCESS      read-create
    STATUS          current
    DESCRIPTION     
            "Primary PSX Name used for PSX connections. \nThe PSX Host Connections will be used in a round-robin implementation for query handling. \nIf the primary PSX is unavailable, congested, or licensed full, the secondary PSX is used if defined, else error handling is applied. \nValid values: existing PSX Name attribute value."
    ::= { ptnpgwPSXNPServiceEntry 3 }

ptnpgwPSXNPServiceSecondaryPSXName OBJECT-TYPE
    SYNTAX          DisplayString (SIZE(0..255))
    MAX-ACCESS      read-create
    STATUS          current
    DESCRIPTION     
            "Secondary PSX Name used for PSX connections. \nOptional PSX to handle traffic if primary PSX is unavailable, congested, or licensed full. Set to an empty string to disable the backup PSX. \nValid values: empty string or existing PSX Name attribute value."
    ::= { ptnpgwPSXNPServiceEntry 4 }

ptnpgwPSXNPServicePSXNPServicesIndex OBJECT-TYPE
    SYNTAX          Integer32 (-2147483648..2147483647)
    MAX-ACCESS      not-accessible
    STATUS          current
    DESCRIPTION     
            "This is the index of the parent type for this object.
             This parent type is PSXNPServices."
    ::= { ptnpgwPSXNPServiceEntry 242 }

ptnpgwPSXNPServiceParentOID OBJECT-TYPE
    SYNTAX          OBJECT IDENTIFIER
    MAX-ACCESS      read-create
    STATUS          current
    DESCRIPTION     
            "The OID of the parent object for this instance"
    ::= { ptnpgwPSXNPServiceEntry 253 }

ptnpgwPSXNPServiceRowStatus OBJECT-TYPE
    SYNTAX          RowStatus
    MAX-ACCESS      read-create
    STATUS          current
    DESCRIPTION     
            "The row status for the npgwPSXNPService table"
    ::= { ptnpgwPSXNPServiceEntry 254 }

ptnpgwPSXNPServiceIndex OBJECT-TYPE
    SYNTAX          Integer32 (-2147483648..2147483647)
    MAX-ACCESS      not-accessible
    STATUS          current
    DESCRIPTION     
            "The row number for the npgwPSXNPService table"
    ::= { ptnpgwPSXNPServiceEntry 255 }

ptnpgwPSXs OBJECT IDENTIFIER
    ::= { ptConnGroup 1617 }

ptnpgwPSXsTable OBJECT-TYPE
    SYNTAX          SEQUENCE OF PtnpgwPSXsEntry
    MAX-ACCESS      not-accessible
    STATUS          current
    DESCRIPTION     
            "No description supplied in the proxy config file."
    ::= { ptnpgwPSXs 1 }

ptnpgwPSXsEntry OBJECT-TYPE
    SYNTAX          PtnpgwPSXsEntry
    MAX-ACCESS      not-accessible
    STATUS          current
    DESCRIPTION     
            "A sequence of npgwPSXs attributes."
    INDEX           { ptConnGroupIndex, ptnpgwPSXsIndex }
    ::= { ptnpgwPSXsTable 1 }

PtnpgwPSXsEntry ::=
    SEQUENCE {
        ptnpgwPSXsParentOID             OBJECT IDENTIFIER,
        ptnpgwPSXsRowStatus             RowStatus,
        ptnpgwPSXsIndex                 Integer32
    }

ptnpgwPSXsParentOID OBJECT-TYPE
    SYNTAX          OBJECT IDENTIFIER
    MAX-ACCESS      read-create
    STATUS          current
    DESCRIPTION     
            "The OID of the parent object for this instance"
    ::= { ptnpgwPSXsEntry 253 }

ptnpgwPSXsRowStatus OBJECT-TYPE
    SYNTAX          RowStatus
    MAX-ACCESS      read-create
    STATUS          current
    DESCRIPTION     
            "The row status for the npgwPSXs table"
    ::= { ptnpgwPSXsEntry 254 }

ptnpgwPSXsIndex OBJECT-TYPE
    SYNTAX          Integer32 (-2147483648..2147483647)
    MAX-ACCESS      not-accessible
    STATUS          current
    DESCRIPTION     
            "The row number for the npgwPSXs table"
    ::= { ptnpgwPSXsEntry 255 }

ptnpgwPSX OBJECT IDENTIFIER
    ::= { ptnpgwPSXs 1618 }

ptnpgwPSXTable OBJECT-TYPE
    SYNTAX          SEQUENCE OF PtnpgwPSXEntry
    MAX-ACCESS      not-accessible
    STATUS          current
    DESCRIPTION     
            "No description supplied in the proxy config file."
    ::= { ptnpgwPSX 1 }

ptnpgwPSXEntry OBJECT-TYPE
    SYNTAX          PtnpgwPSXEntry
    MAX-ACCESS      not-accessible
    STATUS          current
    DESCRIPTION     
            "A sequence of npgwPSX attributes."
    INDEX           { ptConnGroupIndex, ptnpgwPSXPSXsIndex, 
                      ptnpgwPSXIndex }
    ::= { ptnpgwPSXTable 1 }

PtnpgwPSXEntry ::=
    SEQUENCE {
        ptnpgwPSXName                   DisplayString,
        ptnpgwPSXCongestion             INTEGER,
        ptnpgwPSXStatus                 INTEGER,
        ptnpgwPSXUserActivated          INTEGER,
        ptnpgwPSXPSXsIndex              Integer32,
        ptnpgwPSXActions                INTEGER,
        ptnpgwPSXParentOID              OBJECT IDENTIFIER,
        ptnpgwPSXRowStatus              RowStatus,
        ptnpgwPSXIndex                  Integer32
    }

ptnpgwPSXName OBJECT-TYPE
    SYNTAX          DisplayString (SIZE(0..255))
    MAX-ACCESS      read-only
    STATUS          current
    DESCRIPTION     
            "Name of the PSX. \nUsed to associate a PSX connection setup to a PSX NP Service. \nValid values: alphanumeric string with - and _ with a maximum of 16 characters."
    ::= { ptnpgwPSXEntry 1 }

ptnpgwPSXCongestion OBJECT-TYPE
    SYNTAX          INTEGER { notCongested(0), congested(1) }
    MAX-ACCESS      read-only
    STATUS          current
    DESCRIPTION     
            "Congestion status of the PSX. \nSet to highest severity if at least one of the PSX Hosts is in that state. \nValid values: NOT CONGESTED, CONGESTED."
    ::= { ptnpgwPSXEntry 2 }

ptnpgwPSXStatus OBJECT-TYPE
    SYNTAX          INTEGER { inactive(0), notConnected(1), connected(2), 
                        partiallyConnected(3) }
    MAX-ACCESS      read-only
    STATUS          current
    DESCRIPTION     
            "Connection status of the PSX. \nSet based on the PSX Host status. \nValid values: INACTIVE, NOT CONNECTED, CONNECTED, and PARTIALLY CONNECTED"
    ::= { ptnpgwPSXEntry 3 }

ptnpgwPSXUserActivated OBJECT-TYPE
    SYNTAX          INTEGER { disabled(0), enabled(1) }
    MAX-ACCESS      read-only
    STATUS          current
    DESCRIPTION     
            "Activation state configured by the Activate and Deactivate actions. \nValid values: ENABLED and DISABLED."
    ::= { ptnpgwPSXEntry 4 }

ptnpgwPSXPSXsIndex OBJECT-TYPE
    SYNTAX          Integer32 (-2147483648..2147483647)
    MAX-ACCESS      not-accessible
    STATUS          current
    DESCRIPTION     
            "This is the index of the parent type for this object.
             This parent type is PSXs."
    ::= { ptnpgwPSXEntry 242 }

ptnpgwPSXActions OBJECT-TYPE
    SYNTAX          INTEGER { activate(1), deactivate(2), stats(3), 
                        resetStats(4) }
    MAX-ACCESS      read-create
    STATUS          current
    DESCRIPTION     
            "The OID of all possible actions for this instance"
    ::= { ptnpgwPSXEntry 252 }

ptnpgwPSXParentOID OBJECT-TYPE
    SYNTAX          OBJECT IDENTIFIER
    MAX-ACCESS      read-create
    STATUS          current
    DESCRIPTION     
            "The OID of the parent object for this instance"
    ::= { ptnpgwPSXEntry 253 }

ptnpgwPSXRowStatus OBJECT-TYPE
    SYNTAX          RowStatus
    MAX-ACCESS      read-create
    STATUS          current
    DESCRIPTION     
            "The row status for the npgwPSX table"
    ::= { ptnpgwPSXEntry 254 }

ptnpgwPSXIndex OBJECT-TYPE
    SYNTAX          Integer32 (-2147483648..2147483647)
    MAX-ACCESS      not-accessible
    STATUS          current
    DESCRIPTION     
            "The row number for the npgwPSX table"
    ::= { ptnpgwPSXEntry 255 }

ptnpgwPSXHost OBJECT IDENTIFIER
    ::= { ptnpgwPSX 1619 }

ptnpgwPSXHostTable OBJECT-TYPE
    SYNTAX          SEQUENCE OF PtnpgwPSXHostEntry
    MAX-ACCESS      not-accessible
    STATUS          current
    DESCRIPTION     
            "No description supplied in the proxy config file."
    ::= { ptnpgwPSXHost 1 }

ptnpgwPSXHostEntry OBJECT-TYPE
    SYNTAX          PtnpgwPSXHostEntry
    MAX-ACCESS      not-accessible
    STATUS          current
    DESCRIPTION     
            "A sequence of npgwPSXHost attributes."
    INDEX           { ptConnGroupIndex, ptnpgwPSXHostPSXsIndex, 
                      ptnpgwPSXHostPSXIndex, ptnpgwPSXHostIndex }
    ::= { ptnpgwPSXHostTable 1 }

PtnpgwPSXHostEntry ::=
    SEQUENCE {
        ptnpgwPSXHostHost               DisplayString,
        ptnpgwPSXHostPort               Integer32,
        ptnpgwPSXHostCongestion         INTEGER,
        ptnpgwPSXHostStatus             INTEGER,
        ptnpgwPSXHostGatewayName        DisplayString,
        ptnpgwPSXHostUserActivated      INTEGER,
        ptnpgwPSXHostKeepAliveTimer     Integer32,
        ptnpgwPSXHostPSXsIndex          Integer32,
        ptnpgwPSXHostPSXIndex           Integer32,
        ptnpgwPSXHostActions            INTEGER,
        ptnpgwPSXHostParentOID          OBJECT IDENTIFIER,
        ptnpgwPSXHostRowStatus          RowStatus,
        ptnpgwPSXHostIndex              Integer32
    }

ptnpgwPSXHostHost OBJECT-TYPE
    SYNTAX          DisplayString (SIZE(0..255))
    MAX-ACCESS      read-only
    STATUS          current
    DESCRIPTION     
            "Host name for the PSX Host. \nValid values: Hostname or IP address."
    ::= { ptnpgwPSXHostEntry 1 }

ptnpgwPSXHostPort OBJECT-TYPE
    SYNTAX          Integer32 (-2147483648..2147483647)
    MAX-ACCESS      read-only
    STATUS          current
    DESCRIPTION     
            "Port for the PSX Host. \nValid values: 1 to 65535."
    ::= { ptnpgwPSXHostEntry 2 }

ptnpgwPSXHostCongestion OBJECT-TYPE
    SYNTAX          INTEGER { notCongested(0), congested(1) }
    MAX-ACCESS      read-only
    STATUS          current
    DESCRIPTION     
            "Congestion status of the PSX Host. \nValid values: NOT CONGESTED, CONGESTED."
    ::= { ptnpgwPSXHostEntry 3 }

ptnpgwPSXHostStatus OBJECT-TYPE
    SYNTAX          INTEGER { inactive(0), notConnected(1), connected(2), 
                        partiallyConnected(3) }
    MAX-ACCESS      read-only
    STATUS          current
    DESCRIPTION     
            "Connectivity status of the PSX Host. \nSet based on the PSX Host Connections status. \nValid values: INACTIVE, NOT CONNECTED, CONNECTED, and PARTIALLY CONNECTED"
    ::= { ptnpgwPSXHostEntry 4 }

ptnpgwPSXHostGatewayName OBJECT-TYPE
    SYNTAX          DisplayString (SIZE(0..255))
    MAX-ACCESS      read-only
    STATUS          current
    DESCRIPTION     
            "Gateway name for the PSX Host. \nUsed by the PSX Host Connection with slot distinction to register with the PSX. \nValid values: alphanumeric string with - and _ with a maximum of 22 characters."
    ::= { ptnpgwPSXHostEntry 5 }

ptnpgwPSXHostUserActivated OBJECT-TYPE
    SYNTAX          INTEGER { disabled(0), enabled(1) }
    MAX-ACCESS      read-only
    STATUS          current
    DESCRIPTION     
            "Activation state configured by the Activate and Deactivate actions. \nValid values: ENABLED and DISABLED."
    ::= { ptnpgwPSXHostEntry 6 }

ptnpgwPSXHostKeepAliveTimer OBJECT-TYPE
    SYNTAX          Integer32 (500..5000)
    MAX-ACCESS      read-create
    STATUS          current
    DESCRIPTION     
            "Keep alive timer for the PSX Host connections (500-5000ms). \nDefault value: 1000 ms."
    ::= { ptnpgwPSXHostEntry 7 }

ptnpgwPSXHostPSXsIndex OBJECT-TYPE
    SYNTAX          Integer32 (-2147483648..2147483647)
    MAX-ACCESS      not-accessible
    STATUS          current
    DESCRIPTION     
            "This is the index of the parent type for this object.
             This parent type is PSXs."
    ::= { ptnpgwPSXHostEntry 242 }

ptnpgwPSXHostPSXIndex OBJECT-TYPE
    SYNTAX          Integer32 (-2147483648..2147483647)
    MAX-ACCESS      not-accessible
    STATUS          current
    DESCRIPTION     
            "This is the index of the parent type for this object.
             This parent type is PSX."
    ::= { ptnpgwPSXHostEntry 243 }

ptnpgwPSXHostActions OBJECT-TYPE
    SYNTAX          INTEGER { activate(1), deactivate(2) }
    MAX-ACCESS      read-create
    STATUS          current
    DESCRIPTION     
            "The OID of all possible actions for this instance"
    ::= { ptnpgwPSXHostEntry 252 }

ptnpgwPSXHostParentOID OBJECT-TYPE
    SYNTAX          OBJECT IDENTIFIER
    MAX-ACCESS      read-create
    STATUS          current
    DESCRIPTION     
            "The OID of the parent object for this instance"
    ::= { ptnpgwPSXHostEntry 253 }

ptnpgwPSXHostRowStatus OBJECT-TYPE
    SYNTAX          RowStatus
    MAX-ACCESS      read-create
    STATUS          current
    DESCRIPTION     
            "The row status for the npgwPSXHost table"
    ::= { ptnpgwPSXHostEntry 254 }

ptnpgwPSXHostIndex OBJECT-TYPE
    SYNTAX          Integer32 (-2147483648..2147483647)
    MAX-ACCESS      not-accessible
    STATUS          current
    DESCRIPTION     
            "The row number for the npgwPSXHost table"
    ::= { ptnpgwPSXHostEntry 255 }

ptnpgwPSXHostConnection OBJECT IDENTIFIER
    ::= { ptnpgwPSXHost 1620 }

ptnpgwPSXHostConnectionTable OBJECT-TYPE
    SYNTAX          SEQUENCE OF PtnpgwPSXHostConnectionEntry
    MAX-ACCESS      not-accessible
    STATUS          current
    DESCRIPTION     
            "No description supplied in the proxy config file."
    ::= { ptnpgwPSXHostConnection 1 }

ptnpgwPSXHostConnectionEntry OBJECT-TYPE
    SYNTAX          PtnpgwPSXHostConnectionEntry
    MAX-ACCESS      not-accessible
    STATUS          current
    DESCRIPTION     
            "A sequence of npgwPSXHostConnection attributes."
    INDEX           { ptConnGroupIndex, ptnpgwPSXHostConnectionPSXsIndex, 
                      ptnpgwPSXHostConnectionPSXIndex, 
                      ptnpgwPSXHostConnectionPSXHostIndex, 
                      ptnpgwPSXHostConnectionIndex }
    ::= { ptnpgwPSXHostConnectionTable 1 }

PtnpgwPSXHostConnectionEntry ::=
    SEQUENCE {
        ptnpgwPSXHostConnectionSlot     Integer32,
        ptnpgwPSXHostConnectionStatus   INTEGER,
        ptnpgwPSXHostConnectionGatewayName  DisplayString,
        ptnpgwPSXHostConnectionCongestion INTEGER,
        ptnpgwPSXHostConnectionLocalHost DisplayString,
        ptnpgwPSXHostConnectionLocalPort Integer32,
        ptnpgwPSXHostConnectionPSXsIndex Integer32,
        ptnpgwPSXHostConnectionPSXIndex Integer32,
        ptnpgwPSXHostConnectionPSXHostIndex   Integer32,
        ptnpgwPSXHostConnectionParentOID OBJECT IDENTIFIER,
        ptnpgwPSXHostConnectionRowStatus RowStatus,
        ptnpgwPSXHostConnectionIndex    Integer32
    }

ptnpgwPSXHostConnectionSlot OBJECT-TYPE
    SYNTAX          Integer32 (-2147483648..2147483647)
    MAX-ACCESS      read-only
    STATUS          current
    DESCRIPTION     
            "Slot of the PSX Host Connection."
    ::= { ptnpgwPSXHostConnectionEntry 1 }

ptnpgwPSXHostConnectionStatus OBJECT-TYPE
    SYNTAX          INTEGER { inactive(0), notConnected(1), connected(2), 
                        partiallyConnected(3) }
    MAX-ACCESS      read-only
    STATUS          current
    DESCRIPTION     
            "Connection status of the PSX Host Connection. \nValid values: INACTIVE, NOT CONNECTED, and CONNECTED"
    ::= { ptnpgwPSXHostConnectionEntry 2 }

ptnpgwPSXHostConnectionGatewayName OBJECT-TYPE
    SYNTAX          DisplayString (SIZE(0..255))
    MAX-ACCESS      read-only
    STATUS          current
    DESCRIPTION     
            "Gateway name for the PSX Host Connection. \nDefined in the PSX Host with slot distinction to register with the PSX."
    ::= { ptnpgwPSXHostConnectionEntry 3 }

ptnpgwPSXHostConnectionCongestion OBJECT-TYPE
    SYNTAX          INTEGER { notCongested(0), congested(1) }
    MAX-ACCESS      read-only
    STATUS          current
    DESCRIPTION     
            "Congestion status of the PSX Host Connection. \nValid values: NOT CONGESTED, CONGESTED."
    ::= { ptnpgwPSXHostConnectionEntry 4 }

ptnpgwPSXHostConnectionLocalHost OBJECT-TYPE
    SYNTAX          DisplayString (SIZE(0..255))
    MAX-ACCESS      read-only
    STATUS          current
    DESCRIPTION     
            "Local address used by the PSX Host Connection. \nThis value is assigned by the operating system based on the remote host and the IP routing configured on the slot. \nThis string will be empty if the local address is not assigned or the connection is inactive. \nValid values: IP address and empty string."
    ::= { ptnpgwPSXHostConnectionEntry 7 }

ptnpgwPSXHostConnectionLocalPort OBJECT-TYPE
    SYNTAX          Integer32 (-2147483648..2147483647)
    MAX-ACCESS      read-only
    STATUS          current
    DESCRIPTION     
            "Local port for the PSX Host Connection. \nEphemeral value provided by the operating system. \nThe valus will be 0 if the local port is not assigned or the connection is inactive. \nValid values: 0 to 65535."
    ::= { ptnpgwPSXHostConnectionEntry 8 }

ptnpgwPSXHostConnectionPSXsIndex OBJECT-TYPE
    SYNTAX          Integer32 (-2147483648..2147483647)
    MAX-ACCESS      not-accessible
    STATUS          current
    DESCRIPTION     
            "This is the index of the parent type for this object.
             This parent type is PSXs."
    ::= { ptnpgwPSXHostConnectionEntry 242 }

ptnpgwPSXHostConnectionPSXIndex OBJECT-TYPE
    SYNTAX          Integer32 (-2147483648..2147483647)
    MAX-ACCESS      not-accessible
    STATUS          current
    DESCRIPTION     
            "This is the index of the parent type for this object.
             This parent type is PSX."
    ::= { ptnpgwPSXHostConnectionEntry 243 }

ptnpgwPSXHostConnectionPSXHostIndex OBJECT-TYPE
    SYNTAX          Integer32 (-2147483648..2147483647)
    MAX-ACCESS      not-accessible
    STATUS          current
    DESCRIPTION     
            "This is the index of the parent type for this object.
             This parent type is PSXHost."
    ::= { ptnpgwPSXHostConnectionEntry 244 }

ptnpgwPSXHostConnectionParentOID OBJECT-TYPE
    SYNTAX          OBJECT IDENTIFIER
    MAX-ACCESS      read-create
    STATUS          current
    DESCRIPTION     
            "The OID of the parent object for this instance"
    ::= { ptnpgwPSXHostConnectionEntry 253 }

ptnpgwPSXHostConnectionRowStatus OBJECT-TYPE
    SYNTAX          RowStatus
    MAX-ACCESS      read-create
    STATUS          current
    DESCRIPTION     
            "The row status for the npgwPSXHostConnection table"
    ::= { ptnpgwPSXHostConnectionEntry 254 }

ptnpgwPSXHostConnectionIndex OBJECT-TYPE
    SYNTAX          Integer32 (-2147483648..2147483647)
    MAX-ACCESS      not-accessible
    STATUS          current
    DESCRIPTION     
            "The row number for the npgwPSXHostConnection table"
    ::= { ptnpgwPSXHostConnectionEntry 255 }

ptDSCDSC OBJECT IDENTIFIER
    ::= { ptConnGroup 1801 }

ptDSCDSCTable OBJECT-TYPE
    SYNTAX          SEQUENCE OF PtDSCDSCEntry
    MAX-ACCESS      not-accessible
    STATUS          current
    DESCRIPTION     
            "No description supplied in the proxy config file."
    ::= { ptDSCDSC 1 }

ptDSCDSCEntry OBJECT-TYPE
    SYNTAX          PtDSCDSCEntry
    MAX-ACCESS      not-accessible
    STATUS          current
    DESCRIPTION     
            "A sequence of DSCDSC attributes."
    INDEX           { ptConnGroupIndex, ptDSCDSCIndex }
    ::= { ptDSCDSCTable 1 }

PtDSCDSCEntry ::=
    SEQUENCE {
        ptDSCDSCDSCName                 DisplayString,
        ptDSCDSCDSCInstanceID           Integer32,
        ptDSCDSCDSCVersion              DisplayString,
        ptDSCDSCEncryptionPackage       DisplayString,
        ptDSCDSCParentOID               OBJECT IDENTIFIER,
        ptDSCDSCRowStatus               RowStatus,
        ptDSCDSCIndex                   Integer32
    }

ptDSCDSCDSCName OBJECT-TYPE
    SYNTAX          DisplayString (SIZE(0..255))
    MAX-ACCESS      read-create
    STATUS          current
    DESCRIPTION     
            "Name used to logically identify the DSC Instance. \nIf more than one DSC Instance is defined, it is recommended that the name be updated to a short and unique value to facilitate logs, alarms, and statistics correlation. \nValid values: alphanumeric characters, dashes, and underscores (maximum size of 64). \nDefault value: DSC_X, where X is the DSC Instance ID."
    ::= { ptDSCDSCEntry 1 }

ptDSCDSCDSCInstanceID OBJECT-TYPE
    SYNTAX          Integer32 (-2147483648..2147483647)
    MAX-ACCESS      read-only
    STATUS          current
    DESCRIPTION     
            "DSC Instance Identifier (1 to 99). \nIf more than one DSC Instance is defined, the value is overwritten by the associated command line argument on startup. \nDefault value: 1."
    ::= { ptDSCDSCEntry 2 }

ptDSCDSCDSCVersion OBJECT-TYPE
    SYNTAX          DisplayString (SIZE(0..255))
    MAX-ACCESS      read-only
    STATUS          current
    DESCRIPTION     
            "Current DSC application version. \nThis is a hardcoded value as per the DSC application."
    ::= { ptDSCDSCEntry 3 }

ptDSCDSCEncryptionPackage OBJECT-TYPE
    SYNTAX          DisplayString (SIZE(0..255))
    MAX-ACCESS      read-only
    STATUS          current
    DESCRIPTION     
            "DSC Encryption Provider \nThis product includes software developed by the OpenSSL Project for use in the OpenSSL Toolkit (http://www.openssl.org/)"
    ::= { ptDSCDSCEntry 4 }

ptDSCDSCParentOID OBJECT-TYPE
    SYNTAX          OBJECT IDENTIFIER
    MAX-ACCESS      read-create
    STATUS          current
    DESCRIPTION     
            "The OID of the parent object for this instance"
    ::= { ptDSCDSCEntry 253 }

ptDSCDSCRowStatus OBJECT-TYPE
    SYNTAX          RowStatus
    MAX-ACCESS      read-create
    STATUS          current
    DESCRIPTION     
            "The row status for the DSCDSC table"
    ::= { ptDSCDSCEntry 254 }

ptDSCDSCIndex OBJECT-TYPE
    SYNTAX          Integer32 (-2147483648..2147483647)
    MAX-ACCESS      not-accessible
    STATUS          current
    DESCRIPTION     
            "The row number for the DSCDSC table"
    ::= { ptDSCDSCEntry 255 }

ptDSCDSCNodes OBJECT IDENTIFIER
    ::= { ptDSCDSC 1802 }

ptDSCDSCNodesTable OBJECT-TYPE
    SYNTAX          SEQUENCE OF PtDSCDSCNodesEntry
    MAX-ACCESS      not-accessible
    STATUS          current
    DESCRIPTION     
            "No description supplied in the proxy config file."
    ::= { ptDSCDSCNodes 1 }

ptDSCDSCNodesEntry OBJECT-TYPE
    SYNTAX          PtDSCDSCNodesEntry
    MAX-ACCESS      not-accessible
    STATUS          current
    DESCRIPTION     
            "A sequence of DSCDSCNodes attributes."
    INDEX           { ptConnGroupIndex, ptDSCDSCNodesDSCIndex, 
                      ptDSCDSCNodesIndex }
    ::= { ptDSCDSCNodesTable 1 }

PtDSCDSCNodesEntry ::=
    SEQUENCE {
        ptDSCDSCNodesRoutingHopCounter  Integer32,
        ptDSCDSCNodesDSCLicense         INTEGER,
        ptDSCDSCNodesErrors             INTEGER,
        ptDSCDSCNodesSetupManagement    INTEGER,
        ptDSCDSCNodesDistributionManagement   INTEGER,
        ptDSCDSCNodesMaximumQueuedKBytes Integer32,
        ptDSCDSCNodesCapacityParameterSet DisplayString,
        ptDSCDSCNodesRequestLifespan    Integer32,
        ptDSCDSCNodesIMFLicense         INTEGER,
        ptDSCDSCNodesTPSLicense         Integer32,
        ptDSCDSCNodesTopologyMappingLicense   INTEGER,
        ptDSCDSCNodesRetransmitLimit    INTEGER,
        ptDSCDSCNodesSystemTPSLicense   Integer32,
        ptDSCDSCNodesCurrentDaySystemTPSHighWaterMark             Integer32,
        ptDSCDSCNodesCurrentWeekSystemTPSHighWaterMark              Integer32,
        ptDSCDSCNodesCurrentMonthSystemTPSHighWaterMark               Integer32,
        ptDSCDSCNodesCurrentYearSystemTPSHighWaterMark              Integer32,
        ptDSCDSCNodesPreviousDaySystemTPSHighWaterMark              Integer32,
        ptDSCDSCNodesPreviousWeekSystemTPSHighWaterMark               Integer32,
        ptDSCDSCNodesPreviousMonthSystemTPSHighWaterMark                Integer32,
        ptDSCDSCNodesPreviousYearSystemTPSHighWaterMark               Integer32,
        ptDSCDSCNodesRealmStatsName     INTEGER,
        ptDSCDSCNodesLocalOverloadParameters    DisplayString,
        ptDSCDSCNodesLDLDebugLevel      INTEGER,
        ptDSCDSCNodesQueueSize          INTEGER,
        ptDSCDSCNodesQueueUsageThreshold1 Integer32,
        ptDSCDSCNodesQueueUsageThreshold2 Integer32,
        ptDSCDSCNodesQueueUsageThreshold3 Integer32,
        ptDSCDSCNodesDefaultRoutingReturnPrimaryError             INTEGER,
        ptDSCDSCNodesDSCIndex           Integer32,
        ptDSCDSCNodesActions            INTEGER,
        ptDSCDSCNodesParentOID          OBJECT IDENTIFIER,
        ptDSCDSCNodesRowStatus          RowStatus,
        ptDSCDSCNodesIndex              Integer32
    }

ptDSCDSCNodesRoutingHopCounter OBJECT-TYPE
    SYNTAX          Integer32 (1..15)
    MAX-ACCESS      read-create
    STATUS          current
    DESCRIPTION     
            "Routing Hop Counter (1 to 15). \nIf a request is processed by more than the defined DSC and/or UA Nodes, it is discarded as unroutable."
    ::= { ptDSCDSCNodesEntry 1 }

ptDSCDSCNodesDSCLicense OBJECT-TYPE
    SYNTAX          INTEGER { unlicensed(0), licensed(1) }
    MAX-ACCESS      read-only
    STATUS          current
    DESCRIPTION     
            "DSC license (UNLICENSED/LICENSED). \nThis license must be available to configure the DSC functionality."
    ::= { ptDSCDSCNodesEntry 2 }

ptDSCDSCNodesErrors OBJECT-TYPE
    SYNTAX          INTEGER { notLogged(0), logged(1) }
    MAX-ACCESS      read-create
    STATUS          current
    DESCRIPTION     
            "Enable or disable the logging of DSC Nodes error messages to the debuglog (NOT LOGGED/LOGGED). \nThe logging of DSC Nodes errors should be set to LOGGED for all production systems. \nDefault value: LOGGED."
    ::= { ptDSCDSCNodesEntry 3 }

ptDSCDSCNodesSetupManagement OBJECT-TYPE
    SYNTAX          INTEGER { notLogged(0), logged(1) }
    MAX-ACCESS      read-create
    STATUS          current
    DESCRIPTION     
            "Enable or disable the logging of startup and setup information to the debuglog (NOT LOGGED/LOGGED). \nThese logs are not related to traffic processing and have no impact on the performance of a running system. \nThe logging of DSC startup and setup information should be set to LOGGED for most production systems. \nDefault value: LOGGED."
    ::= { ptDSCDSCNodesEntry 4 }

ptDSCDSCNodesDistributionManagement OBJECT-TYPE
    SYNTAX          INTEGER { notLogged(0), logged(1) }
    MAX-ACCESS      read-create
    STATUS          current
    DESCRIPTION     
            "Enable or disable the logging of inter-DSC process communication to the debuglog (NOT LOGGED/LOGGED). \nThe resultant log messages are intended for Sonus Networks engineering staff and are not intended for customer use. \nThe logging of DSC inter-process information should be set to NOT_LOGGED on all production systems so that the CPU is not unduly taxed. Default value: NOT LOGGED."
    ::= { ptDSCDSCNodesEntry 5 }

ptDSCDSCNodesMaximumQueuedKBytes OBJECT-TYPE
    SYNTAX          Integer32 (2000..8000000)
    MAX-ACCESS      read-create
    STATUS          current
    DESCRIPTION     
            "Maximum number of message bytes in all queues in a DSC process. \nObsolete as of release 17.0, but unused and hidden prior to that. \nExcludes overhead such as list of nodes and routing information. \nRange: 2000-8000000 with default is 2000000 (~2GB)."
    ::= { ptDSCDSCNodesEntry 6 }

ptDSCDSCNodesCapacityParameterSet OBJECT-TYPE
    SYNTAX          DisplayString (SIZE(0..255))
    MAX-ACCESS      read-create
    STATUS          current
    DESCRIPTION     
            "Capacity parameter set for nodal congestion."
    ::= { ptDSCDSCNodesEntry 7 }

ptDSCDSCNodesRequestLifespan OBJECT-TYPE
    SYNTAX          Integer32 (10..240)
    MAX-ACCESS      read-create
    STATUS          current
    DESCRIPTION     
            "Request message lifespan in seconds with return error on expiry. \nRegardless of how many times the request may have been retransmitted, on lifespan expiry, an answer with error UNABLE_TO_DELIVER is returned. \nValid values: 10 to 240 seconds. \nDefault value: 60 seconds."
    ::= { ptDSCDSCNodesEntry 9 }

ptDSCDSCNodesIMFLicense OBJECT-TYPE
    SYNTAX          INTEGER { unlicensed(0), licensed(1) }
    MAX-ACCESS      read-only
    STATUS          current
    DESCRIPTION     
            "IMF license (UNLICENSED/LICENSED). \nThis license must be available to configure the IMF functionality on a per ADN basis."
    ::= { ptDSCDSCNodesEntry 10 }

ptDSCDSCNodesTPSLicense OBJECT-TYPE
    SYNTAX          Integer32 (-2147483648..2147483647)
    MAX-ACCESS      read-only
    STATUS          current
    DESCRIPTION     
            "Transactions Per Second license (count). \nThe TPS license has an associated MSA for threshold alarms."
    ::= { ptDSCDSCNodesEntry 11 }

ptDSCDSCNodesTopologyMappingLicense OBJECT-TYPE
    SYNTAX          INTEGER { unlicensed(0), licensed(1) }
    MAX-ACCESS      read-only
    STATUS          current
    DESCRIPTION     
            "Topology Mapping license (UNLICENSED/LICENSED). \nThis license must be available to configure the Topology Mapping functionality on a per DSC Node basis."
    ::= { ptDSCDSCNodesEntry 12 }

ptDSCDSCNodesRetransmitLimit OBJECT-TYPE
    SYNTAX          INTEGER { unlimited(-1) }
    MAX-ACCESS      read-create
    STATUS          current
    DESCRIPTION     
            "Limit to retry individual node messages upon encountering a failure condition (not including redirect attempts). \nValid values: UNLIMITED (-1), 0 to 50 attempts. \nDefault value: 10 attempts. \nChoosing 0 does not allow for any retries. \nChoosing UNLIMITED provides an unlimited number of retries."
    ::= { ptDSCDSCNodesEntry 13 }

ptDSCDSCNodesSystemTPSLicense OBJECT-TYPE
    SYNTAX          Integer32 (-2147483648..2147483647)
    MAX-ACCESS      read-only
    STATUS          current
    DESCRIPTION     
            "System Transactions Per Second license (count). \nThe System TPS license has an associated System TPS MSA for threshold alarms."
    ::= { ptDSCDSCNodesEntry 15 }

ptDSCDSCNodesCurrentDaySystemTPSHighWaterMark OBJECT-TYPE
    SYNTAX          Integer32 (-2147483648..2147483647)
    MAX-ACCESS      read-only
    STATUS          current
    DESCRIPTION     
            "Current Day System Transactions Per Second High Water Mark (count). \nThe current System TPS daily data will be moved to previous day data and then reset at 12:00 a.m. every day."
    ::= { ptDSCDSCNodesEntry 16 }

ptDSCDSCNodesCurrentWeekSystemTPSHighWaterMark OBJECT-TYPE
    SYNTAX          Integer32 (-2147483648..2147483647)
    MAX-ACCESS      read-only
    STATUS          current
    DESCRIPTION     
            "Current Week System Transactions Per Second High Water Mark (count) from Sunday to Saturday. \nThe current System TPS weekly data will be moved to previous week data and reset at 12:00 a.m. every Sunday morning."
    ::= { ptDSCDSCNodesEntry 17 }

ptDSCDSCNodesCurrentMonthSystemTPSHighWaterMark OBJECT-TYPE
    SYNTAX          Integer32 (-2147483648..2147483647)
    MAX-ACCESS      read-only
    STATUS          current
    DESCRIPTION     
            "Current Month System Transactions Per Second High Water Mark (count). \nThe current System TPS monthly data will be moved to previous month data and reset on the 1st day of each month."
    ::= { ptDSCDSCNodesEntry 18 }

ptDSCDSCNodesCurrentYearSystemTPSHighWaterMark OBJECT-TYPE
    SYNTAX          Integer32 (-2147483648..2147483647)
    MAX-ACCESS      read-only
    STATUS          current
    DESCRIPTION     
            "Current Year System Transactions Per Second High Water Mark (count). \nThe current System TPS yearly data will be moved to previous year and reset on the 1st day of each year."
    ::= { ptDSCDSCNodesEntry 19 }

ptDSCDSCNodesPreviousDaySystemTPSHighWaterMark OBJECT-TYPE
    SYNTAX          Integer32 (-2147483648..2147483647)
    MAX-ACCESS      read-only
    STATUS          current
    DESCRIPTION     
            "Previous Day System Transactions Per Second High Water Mark (count). \nThe previous System TPS daily data will be updated with current daily data at 12:00 a.m. every day. If today is Tuesday, this will represent Monday TPS high water mark data."
    ::= { ptDSCDSCNodesEntry 20 }

ptDSCDSCNodesPreviousWeekSystemTPSHighWaterMark OBJECT-TYPE
    SYNTAX          Integer32 (-2147483648..2147483647)
    MAX-ACCESS      read-only
    STATUS          current
    DESCRIPTION     
            "Previous Week System Transactions Per Second High Water Mark (count) from Sunday to Saturday. \nThe previous System TPS weekly data will be updated with current weekly data at 12:00 a.m. every Sunday morning."
    ::= { ptDSCDSCNodesEntry 21 }

ptDSCDSCNodesPreviousMonthSystemTPSHighWaterMark OBJECT-TYPE
    SYNTAX          Integer32 (-2147483648..2147483647)
    MAX-ACCESS      read-only
    STATUS          current
    DESCRIPTION     
            "Previous Month System Transactions Per Second High Water Mark (count). \nThe previous System TPS monthly data will be updated with current monthly data on the 1st day of each month."
    ::= { ptDSCDSCNodesEntry 22 }

ptDSCDSCNodesPreviousYearSystemTPSHighWaterMark OBJECT-TYPE
    SYNTAX          Integer32 (-2147483648..2147483647)
    MAX-ACCESS      read-only
    STATUS          current
    DESCRIPTION     
            "Previous Year System Transactions Per Second High Water Mark (count). \nThe previous System TPS yearly data will be updated with current yearly data on the 1st day of each year."
    ::= { ptDSCDSCNodesEntry 23 }

ptDSCDSCNodesRealmStatsName OBJECT-TYPE
    SYNTAX          INTEGER { name(0), alias(1) }
    MAX-ACCESS      read-create
    STATUS          current
    DESCRIPTION     
            "Realm information used to form the Instances name in statistics files. \nThe Alias is used for configuration purposes and by default will also be used in Realm Accounting statistics reporting. Since the Realm Name is typically more static in nature, some customers may prefer to use the that value, especially in cases where scripts are used to monitor the data for other purposes. \nValid values: NAME (0), ALIAS (1). \nDefault value: ALIAS"
    ::= { ptDSCDSCNodesEntry 25 }

ptDSCDSCNodesLocalOverloadParameters OBJECT-TYPE
    SYNTAX          DisplayString (SIZE(0..255))
    MAX-ACCESS      read-create
    STATUS          current
    DESCRIPTION     
            "Capacity parameter set for general Local Overload detection. \nThe indicated capacity parameter set specifies the message delay \nand queue size limits for the incoming messages that are used to \ndefine the severify levels of the local overload condition. \nThe fields used are: \n Queue Size in Seconds \n Queue Size in Messages \n Congestion Onset 1,2,3 \n Congestion Abatement 1,2,3 \n Overload Handling 1,2,3 \nValid values: Empty (disabled) or existing Capacity Parameter Set \nDefault value: Empty."
    ::= { ptDSCDSCNodesEntry 26 }

ptDSCDSCNodesLDLDebugLevel OBJECT-TYPE
    SYNTAX          INTEGER { notLogged(0) }
    MAX-ACCESS      read-create
    STATUS          current
    DESCRIPTION     
            "The LDL Debug Level should be set to 2 (default) or lower on all production systems, unless directed by support. Otherwise the system performance may be impacted by an undue amount of time logging messages. Valid range is (0 [NOT LOGGED], 1 to 10)."
    ::= { ptDSCDSCNodesEntry 27 }

ptDSCDSCNodesQueueSize OBJECT-TYPE
    SYNTAX          INTEGER { auto(0) }
    MAX-ACCESS      read-create
    STATUS          current
    DESCRIPTION     
            "Queue Size in megabytes. \nThe maximum number of message bytes that may be queued, measured in megabytes. \nRange: 1 to 50000."
    ::= { ptDSCDSCNodesEntry 28 }

ptDSCDSCNodesQueueUsageThreshold1 OBJECT-TYPE
    SYNTAX          Integer32
    MAX-ACCESS      read-create
    STATUS          current
    DESCRIPTION     
            "Queue Usage Alarm Threshold 1. \nIf the message queue is used more than this percentage an alarm is raised. \nRange: 1 to 100."
    ::= { ptDSCDSCNodesEntry 29 }

ptDSCDSCNodesQueueUsageThreshold2 OBJECT-TYPE
    SYNTAX          Integer32
    MAX-ACCESS      read-create
    STATUS          current
    DESCRIPTION     
            "Queue Usage Alarm Threshold 2. \nIf the message queue is used more than this percentage an alarm is raised. \nRange: 1 to 100."
    ::= { ptDSCDSCNodesEntry 30 }

ptDSCDSCNodesQueueUsageThreshold3 OBJECT-TYPE
    SYNTAX          Integer32
    MAX-ACCESS      read-create
    STATUS          current
    DESCRIPTION     
            "Queue Usage Alarm Threshold 3. \nIf the message queue is used more than this percentage an alarm is raised. \nRange: 1 to 100."
    ::= { ptDSCDSCNodesEntry 31 }

ptDSCDSCNodesDefaultRoutingReturnPrimaryError OBJECT-TYPE
    SYNTAX          INTEGER { disabled(0), enabled(1) }
    MAX-ACCESS      read-create
    STATUS          current
    DESCRIPTION     
            "The attribute is used in the event that during default \nrouting, routing to all candidates fails. \nIf enabled and the error is a 3xxx series error \nthen the error received from the first routing candidate is returned to message originator. \nWhen disabled the error that is received from the final routing candidate is returned to the originator. \nDefault value: Disabled"
    ::= { ptDSCDSCNodesEntry 32 }

ptDSCDSCNodesDSCIndex OBJECT-TYPE
    SYNTAX          Integer32 (-2147483648..2147483647)
    MAX-ACCESS      not-accessible
    STATUS          current
    DESCRIPTION     
            "This is the index of the parent type for this object.
             This parent type is DSC."
    ::= { ptDSCDSCNodesEntry 242 }

ptDSCDSCNodesActions OBJECT-TYPE
    SYNTAX          INTEGER { restoreDebugDefaults(1) }
    MAX-ACCESS      read-create
    STATUS          current
    DESCRIPTION     
            "The OID of all possible actions for this instance"
    ::= { ptDSCDSCNodesEntry 252 }

ptDSCDSCNodesParentOID OBJECT-TYPE
    SYNTAX          OBJECT IDENTIFIER
    MAX-ACCESS      read-create
    STATUS          current
    DESCRIPTION     
            "The OID of the parent object for this instance"
    ::= { ptDSCDSCNodesEntry 253 }

ptDSCDSCNodesRowStatus OBJECT-TYPE
    SYNTAX          RowStatus
    MAX-ACCESS      read-create
    STATUS          current
    DESCRIPTION     
            "The row status for the DSCDSCNodes table"
    ::= { ptDSCDSCNodesEntry 254 }

ptDSCDSCNodesIndex OBJECT-TYPE
    SYNTAX          Integer32 (-2147483648..2147483647)
    MAX-ACCESS      not-accessible
    STATUS          current
    DESCRIPTION     
            "The row number for the DSCDSCNodes table"
    ::= { ptDSCDSCNodesEntry 255 }

ptDSCDSCNode OBJECT IDENTIFIER
    ::= { ptDSCDSCNodes 1805 }

ptDSCDSCNodeTable OBJECT-TYPE
    SYNTAX          SEQUENCE OF PtDSCDSCNodeEntry
    MAX-ACCESS      not-accessible
    STATUS          current
    DESCRIPTION     
            "No description supplied in the proxy config file."
    ::= { ptDSCDSCNode 1 }

ptDSCDSCNodeEntry OBJECT-TYPE
    SYNTAX          PtDSCDSCNodeEntry
    MAX-ACCESS      not-accessible
    STATUS          current
    DESCRIPTION     
            "A sequence of DSCDSCNode attributes."
    INDEX           { ptConnGroupIndex, ptDSCDSCNodeDSCIndex, 
                      ptDSCDSCNodeDSCNodesIndex, ptDSCDSCNodeIndex }
    ::= { ptDSCDSCNodeTable 1 }

PtDSCDSCNodeEntry ::=
    SEQUENCE {
        ptDSCDSCNodeNodeDiameterID      DisplayString,
        ptDSCDSCNodeRealm               DisplayString,
        ptDSCDSCNodeStatus              INTEGER,
        ptDSCDSCNodeInternalID          Integer32,
        ptDSCDSCNodeInitialRoutingTableName   DisplayString,
        ptDSCDSCNodeMaximumRoutingDepth Integer32,
        ptDSCDSCNodeAcceptUnknownADNs   INTEGER,
        ptDSCDSCNodeRoundTripAccounting INTEGER,
        ptDSCDSCNodeMaxTracingPerInterval Integer32,
        ptDSCDSCNodeTracingInterval     INTEGER,
        ptDSCDSCNodeErrors              INTEGER,
        ptDSCDSCNodeSetupManagement     INTEGER,
        ptDSCDSCNodeExecutionTrace      INTEGER,
        ptDSCDSCNodeNodeCommunication   INTEGER,
        ptDSCDSCNodeDistributionManagement  INTEGER,
        ptDSCDSCNodeTracingMsgHex       INTEGER,
        ptDSCDSCNodeRealmRoutingTableName DisplayString,
        ptDSCDSCNodeIngressFiltering    INTEGER,
        ptDSCDSCNodeDIDHost             DisplayString,
        ptDSCDSCNodeTopologyMappingTableName    DisplayString,
        ptDSCDSCNodeRealmAccounting     INTEGER,
        ptDSCDSCNodeName                DisplayString,
        ptDSCDSCNodeReceiveRealmRedirectIndications           INTEGER,
        ptDSCDSCNodeRealmAccountingFormat INTEGER,
        ptDSCDSCNodeDSCIndex            Integer32,
        ptDSCDSCNodeDSCNodesIndex       Integer32,
        ptDSCDSCNodeActions             INTEGER,
        ptDSCDSCNodeParentOID           OBJECT IDENTIFIER,
        ptDSCDSCNodeRowStatus           RowStatus,
        ptDSCDSCNodeIndex               Integer32
    }

ptDSCDSCNodeNodeDiameterID OBJECT-TYPE
    SYNTAX          DisplayString (SIZE(0..255))
    MAX-ACCESS      read-create
    STATUS          current
    DESCRIPTION     
            "DSC Node unique Diameter ID. \nThe attribute is optional when creating an DSC Node with a DID Host. \nIf not specified, the value will be set to a concatenation of the DID Host and Realm. \nValid values: FQDN format or empty string."
    ::= { ptDSCDSCNodeEntry 1 }

ptDSCDSCNodeRealm OBJECT-TYPE
    SYNTAX          DisplayString (SIZE(0..255))
    MAX-ACCESS      read-create
    STATUS          current
    DESCRIPTION     
            "DSC Node associated realm. \nIf a FQDN is specified, a Realm Definition will be automatically created if none exists. If a Realm Definition is already defined, the FQDN value will be replaced by the associated Alias. \nValid values: FQDN format or existing Realm Definition Alias."
    ::= { ptDSCDSCNodeEntry 2 }

ptDSCDSCNodeStatus OBJECT-TYPE
    SYNTAX          INTEGER { down(0), up(1), inactive(2), 
                        partiallyUp(3) }
    MAX-ACCESS      read-only
    STATUS          current
    DESCRIPTION     
            "Status of the DSC Node (UP/DOWN/INACTIVE). \nDSC Node status is set to UP when at least one non-DSC INTERNAL and non-DSC DB ADN is UP."
    ::= { ptDSCDSCNodeEntry 4 }

ptDSCDSCNodeInternalID OBJECT-TYPE
    SYNTAX          Integer32 (-2147483648..2147483647)
    MAX-ACCESS      read-only
    STATUS          current
    DESCRIPTION     
            "Node unique internal ID. \nReserved for internal use."
    ::= { ptDSCDSCNodeEntry 5 }

ptDSCDSCNodeInitialRoutingTableName OBJECT-TYPE
    SYNTAX          DisplayString (SIZE(0..255))
    MAX-ACCESS      read-create
    STATUS          current
    DESCRIPTION     
            "Node Initial Routing Table Name. \nMessage incoming from the DSC Node will be routed based on this routing table or use default routing if set to dsc_default. \nValid values: dsc_default or an existing Routing Table name. \nDefault value: dsc_default."
    ::= { ptDSCDSCNodeEntry 6 }

ptDSCDSCNodeMaximumRoutingDepth OBJECT-TYPE
    SYNTAX          Integer32 (10..50)
    MAX-ACCESS      read-create
    STATUS          current
    DESCRIPTION     
            "Maximum Routing Depth (10 to 50). \nWhen using explicit routing tables, this attribute limits the number of routing tables that may be used to route a single message. If this limit is exceeded, the message is returned as an error. This feature is a protection against loops in the routing tables causing undue processor usage. \nDefault value: 10."
    ::= { ptDSCDSCNodeEntry 7 }

ptDSCDSCNodeAcceptUnknownADNs OBJECT-TYPE
    SYNTAX          INTEGER { disabled(0), enabled(1) }
    MAX-ACCESS      read-create
    STATUS          current
    DESCRIPTION     
            "Accept incoming connections from unknown/unconfigured adjacent nodes (ENABLED/DISABLED)."
    ::= { ptDSCDSCNodeEntry 8 }

ptDSCDSCNodeRoundTripAccounting OBJECT-TYPE
    SYNTAX          INTEGER { disabled(0), enabled(1) }
    MAX-ACCESS      read-create
    STATUS          current
    DESCRIPTION     
            "Round Trip Accounting feature (DISABLED/ENABLED). \nIf enabled, round trip delays on outbound transactions are calculated and organized according to destination and command type. \nStandard statistics intervals apply (5 minutes, 30 minutes, and 1 day). \nDefault value: DISABLED."
    ::= { ptDSCDSCNodeEntry 9 }

ptDSCDSCNodeMaxTracingPerInterval OBJECT-TYPE
    SYNTAX          Integer32 (0..99)
    MAX-ACCESS      read-create
    STATUS          current
    DESCRIPTION     
            "Maximum number of traced MSUs logged in the given interval (0 to 99). \nMSU tracing, if enabled, assigns a unique identifier to incoming messages matching a Modification trace record. The message can then be traced throughout the Routing Tables for debugging purposes. \nSet to 0 to disable message tracing. \nDefault value: 10."
    ::= { ptDSCDSCNodeEntry 10 }

ptDSCDSCNodeTracingInterval OBJECT-TYPE
    SYNTAX          INTEGER { five(300000), ten(600000), fifteen(900000), 
                        twenty(1200000), thirty(1800000) }
    MAX-ACCESS      read-create
    STATUS          current
    DESCRIPTION     
            "Message Tracing logging interval [5, 10, 15, 20, or 30 minutes]. \nDefault value: 5 minutes."
    ::= { ptDSCDSCNodeEntry 11 }

ptDSCDSCNodeErrors OBJECT-TYPE
    SYNTAX          INTEGER { notLogged(0), logged(1) }
    MAX-ACCESS      read-create
    STATUS          current
    DESCRIPTION     
            "Enable or disable the logging of DSC Node error messages to the debuglog (NOT LOGGED/LOGGED). \nThe logging of DSC Node errors should be set to LOGGED for all production systems. Default value: LOGGED."
    ::= { ptDSCDSCNodeEntry 14 }

ptDSCDSCNodeSetupManagement OBJECT-TYPE
    SYNTAX          INTEGER { notLogged(0), logged(1) }
    MAX-ACCESS      read-create
    STATUS          current
    DESCRIPTION     
            "Enable or disable the logging of startup and setup information to the debuglog (NOT LOGGED/LOGGED). \nThese logs are not related to traffic processing and have no impact on the performance of a running system. \nThe logging of DSC Node startup and setup information should be set to LOGGED for most production systems. \nDefault value: LOGGED."
    ::= { ptDSCDSCNodeEntry 15 }

ptDSCDSCNodeExecutionTrace OBJECT-TYPE
    SYNTAX          INTEGER { notLogged(0), logged(1) }
    MAX-ACCESS      read-create
    STATUS          current
    DESCRIPTION     
            "Enable or disable the logging of internal execution of the DSC traffic to the debuglog (NOT LOGGED/LOGGED). \nThe resultant messages are intended for Sonus Networks engineering staff and are not intended for customer use. \nThe logging of execution trace must be set to NOT LOGGED on all production systems so that the CPU is not unduly taxed. \nDefault value: NOT LOGGED."
    ::= { ptDSCDSCNodeEntry 16 }

ptDSCDSCNodeNodeCommunication OBJECT-TYPE
    SYNTAX          INTEGER { notLogged(0), logged(1) }
    MAX-ACCESS      read-create
    STATUS          current
    DESCRIPTION     
            "Enable or disable the logging of inter-node communication to the debuglog (NOT LOGGED/LOGGED). \nThe resultant messages are intended for Sonus Networks engineering staff and are not intended for customer use. \nThe logging of node communication must be set to NOT LOGGED on all production systems so that the CPU is not unduly taxed. \nDefault value: NOT LOGGED."
    ::= { ptDSCDSCNodeEntry 17 }

ptDSCDSCNodeDistributionManagement OBJECT-TYPE
    SYNTAX          INTEGER { notLogged(0), logged(1) }
    MAX-ACCESS      read-create
    STATUS          current
    DESCRIPTION     
            "Enable or disable the logging of inter-DSC process communication to the debuglog (NOT LOGGED/LOGGED). \nThe resultant messages are intended for Sonus Networks engineering staff and are not intended for customer use. \nThe logging of inter-process communication must be set to NOT LOGGED on all production systems so that the CPU is not unduly taxed. \nDefault value: NOT LOGGED."
    ::= { ptDSCDSCNodeEntry 18 }

ptDSCDSCNodeTracingMsgHex OBJECT-TYPE
    SYNTAX          INTEGER { incoming(0), incomingAndOutgoing(1) }
    MAX-ACCESS      read-create
    STATUS          current
    DESCRIPTION     
            "Message Tracing logging of hexadecimal [INCOMING, INCOMING AND OUTGOING]. \nHexadecimal representation of the message (up to 500 bytes). \nDefault value: INCOMING."
    ::= { ptDSCDSCNodeEntry 19 }

ptDSCDSCNodeRealmRoutingTableName OBJECT-TYPE
    SYNTAX          DisplayString (SIZE(0..255))
    MAX-ACCESS      read-create
    STATUS          current
    DESCRIPTION     
            "Node Realm Routing Table Name. \nMessage incoming from the DSC Node will be routed based on this realm routing table. \nValid values: Existing Realm Routing table name or empty string to disable."
    ::= { ptDSCDSCNodeEntry 20 }

ptDSCDSCNodeIngressFiltering OBJECT-TYPE
    SYNTAX          INTEGER { disabled(0), originRealm(1) }
    MAX-ACCESS      read-create
    STATUS          current
    DESCRIPTION     
            "Node Ingress Filtering (DISABLED/ORIGIN REALM). \nIngress Filtering compares information about the realm of the Incoming ADN against the contents of the Origin-Realm AVP in the request message. If the Origin-Realm is the same as Incoming Realm, then the message passes ingress filtering. If a message fails ingress filtering, an answer is returned with error ERROR_UNABLE_TO_DELIVER"
    ::= { ptDSCDSCNodeEntry 21 }

ptDSCDSCNodeDIDHost OBJECT-TYPE
    SYNTAX          DisplayString (SIZE(0..255))
    MAX-ACCESS      read-create
    STATUS          current
    DESCRIPTION     
            "DSC Node Host within the realm. \nThis attribute is optional when creating a DSC Node with a Node Diameter ID. \nIf specified, the value will be prepended to the Realm to create the Node Diameter ID. \nValid values: FQDN format or empty string."
    ::= { ptDSCDSCNodeEntry 22 }

ptDSCDSCNodeTopologyMappingTableName OBJECT-TYPE
    SYNTAX          DisplayString (SIZE(0..255))
    MAX-ACCESS      read-create
    STATUS          current
    DESCRIPTION     
            "Topology Mapping Table to be applied to Nodes in the DSC realm. \nValid values: Existing Topology Mapping table name or empty string to disable."
    ::= { ptDSCDSCNodeEntry 23 }

ptDSCDSCNodeRealmAccounting OBJECT-TYPE
    SYNTAX          INTEGER { disabled(0), enabled(1) }
    MAX-ACCESS      read-create
    STATUS          current
    DESCRIPTION     
            "Realm Accounting feature (DISABLED/ENABLED). \nIf enabled, traffic statistics are gathered based on incoming and outgoing realms as well as on associated ADNs where relevant. \nStandard statistics intervals apply (5 minutes, 30 minutes, and 1 day). \nDefault value: DISABLED."
    ::= { ptDSCDSCNodeEntry 24 }

ptDSCDSCNodeName OBJECT-TYPE
    SYNTAX          DisplayString (SIZE(0..255))
    MAX-ACCESS      read-create
    STATUS          current
    DESCRIPTION     
            "Name used to logically identify the DSC Node. \nThe Name must be unique within the DSC Instance. \nIt is recommended that the name be set to a short and unique value to facilitate logs and alarms correlation. \nIf no Name is entered on creation, or if the Name is modified to an empty string, the Node Diameter ID will be used. \nValid values: alphanumeric characters, dashes, and underscores (maximum size of 32). The name is allowed to contain dots (.) and exceed maximum size only when it matches the Node Diameter ID."
    ::= { ptDSCDSCNodeEntry 31 }

ptDSCDSCNodeReceiveRealmRedirectIndications OBJECT-TYPE
    SYNTAX          INTEGER { disabled(0), rfc7075(1), passthrough(2) }
    MAX-ACCESS      read-create
    STATUS          current
    DESCRIPTION     
            "Receive Realm Redirect Indications Attribute is used to specify how DSC handles the Realm Redirect Indications. Allowed Value: DISABLED, or PASSTHROUGH, RFC7075. \n \nIf the Receive-Realm-Redirect-Indications attribute is set to DISABLED, then the received DIAMETER_REALM_REDIRECT_INDICATION is treated like a DIAMETER_UNABLE_TO_DELIVER. \n \nIf the Receive-Realm-Redirect-Indications attribute is set to PASSTHROUGH, then the received DIAMETER_REALM_REDIRECT_INDICATION is forwarded to the incoming ADN with the appropriate hop-by-hop id. The Origin-Host and Origin-Realm AVPs in the REALM_REDIRECT_INDICATION are unchanged. \n \nIf the Receive-Realm-Redirect-Indications attribute is set to RFC7075, then the received DIAMETER_REALM_REDIRECT_INDICATION is handled as specified in RFC7075 where the DSC will forward the original request using the realms provided in the INDICATION message. \n \nDefault value is DISABLED."
    ::= { ptDSCDSCNodeEntry 40 }

ptDSCDSCNodeRealmAccountingFormat OBJECT-TYPE
    SYNTAX          INTEGER { version1(1), version2(2) }
    MAX-ACCESS      read-create
    STATUS          current
    DESCRIPTION     
            "Realm Accounting Format (VERSION 1/VERSION 2). \n- Default value: VERSION 1. \n- This attribute will take effect only if Realm Accounting attribute is ENABLED. \n- Realm accounting is a feature that counts some details of Diameter transactions and writes the counters to a Comma Separated Values (CSV) file. The Instance column contains a formatted string that includes the Incoming ADN, Outgoing ADN, Originating Realm and Destination Realm. In some cases not all fields are relevant. For example, if a message cannot be routed there is no Outgoing ADN. \n \n If this attribute is set to VERSION 1 then the format of the Instance column is the format used in release 16.1.0 and earlier releases, namely: \n - <DSC Instance Name> <DSC Node Name> <Originating Realm of the incoming request>: <Name of the incoming ADN>:<Destination Realm of the incoming request>: <Name of the ADN from which the answer is received>, \n \n If this attribute is set to VERSION 2 then the Instance column contains the Instance string from VERSION 1 plus the Application Id, Command Code and Destination-Realm of the outgoing request. Specifically, the format is: \n - <DSC Instance Name> <DSC Node Name> <Originating Realm of the incoming request>:<Name of the incoming ADN>:<Destination Realm of the incoming request>:<Name of the ADN from which the answer is received>:<Application-Id>:<Command-Code>:<Destination-Realm of the outgoing Request> \n \n If the request is rejected by the DSC without being sent to an outgoing ADN then the <Destination-Realm of the outgoing Request> is set to (null). \n \n For any of the realm components of the instance, the Alias of an associated Realm Definition is used if it exists. Otherwise, the realm component uses the contents of the appropriate AVP, normalized to lower case and escaped: any character other than alphanumeric, dash or underscore is replaced with '%' followed by two hex digits representing the encoded octet. \n \n If the Application-Id in the message is defined as an Application ID Definition then <Application-Id> is the Application ID Definition Name, otherwise <Application-Id> is a string representing the numeric value of the Application-Id. \n \n If the Command-Code in the message is defined as an Command-Code Definition then <Command-Code> is the Command Code Definition Name, otherwise <Command-Code> is a string representing the numeric value of the Command-Code. \n \n Using VERSION 2 includes more granularity in the Instance strings, so it is possible to hit the overflow limit of 50000 distinct Instance strings more easily."
    ::= { ptDSCDSCNodeEntry 41 }

ptDSCDSCNodeDSCIndex OBJECT-TYPE
    SYNTAX          Integer32 (-2147483648..2147483647)
    MAX-ACCESS      not-accessible
    STATUS          current
    DESCRIPTION     
            "This is the index of the parent type for this object.
             This parent type is DSC."
    ::= { ptDSCDSCNodeEntry 242 }

ptDSCDSCNodeDSCNodesIndex OBJECT-TYPE
    SYNTAX          Integer32 (-2147483648..2147483647)
    MAX-ACCESS      not-accessible
    STATUS          current
    DESCRIPTION     
            "This is the index of the parent type for this object.
             This parent type is DSCNodes."
    ::= { ptDSCDSCNodeEntry 243 }

ptDSCDSCNodeActions OBJECT-TYPE
    SYNTAX          INTEGER { activate(1), deactivate(2), 
                        resetTracing(3), resetIMF(4), 
                        restoreDebugDefaults(5) }
    MAX-ACCESS      read-create
    STATUS          current
    DESCRIPTION     
            "The OID of all possible actions for this instance"
    ::= { ptDSCDSCNodeEntry 252 }

ptDSCDSCNodeParentOID OBJECT-TYPE
    SYNTAX          OBJECT IDENTIFIER
    MAX-ACCESS      read-create
    STATUS          current
    DESCRIPTION     
            "The OID of the parent object for this instance"
    ::= { ptDSCDSCNodeEntry 253 }

ptDSCDSCNodeRowStatus OBJECT-TYPE
    SYNTAX          RowStatus
    MAX-ACCESS      read-create
    STATUS          current
    DESCRIPTION     
            "The row status for the DSCDSCNode table"
    ::= { ptDSCDSCNodeEntry 254 }

ptDSCDSCNodeIndex OBJECT-TYPE
    SYNTAX          Integer32 (-2147483648..2147483647)
    MAX-ACCESS      not-accessible
    STATUS          current
    DESCRIPTION     
            "The row number for the DSCDSCNode table"
    ::= { ptDSCDSCNodeEntry 255 }

ptDSCAdjacentDiameterNodes OBJECT IDENTIFIER
    ::= { ptDSCDSCNode 1806 }

ptDSCAdjacentDiameterNodesTable OBJECT-TYPE
    SYNTAX          SEQUENCE OF PtDSCAdjacentDiameterNodesEntry
    MAX-ACCESS      not-accessible
    STATUS          current
    DESCRIPTION     
            "No description supplied in the proxy config file."
    ::= { ptDSCAdjacentDiameterNodes 1 }

ptDSCAdjacentDiameterNodesEntry OBJECT-TYPE
    SYNTAX          PtDSCAdjacentDiameterNodesEntry
    MAX-ACCESS      not-accessible
    STATUS          current
    DESCRIPTION     
            "A sequence of DSCAdjacentDiameterNodes attributes."
    INDEX           { ptConnGroupIndex, 
                      ptDSCAdjacentDiameterNodesDSCIndex, 
                      ptDSCAdjacentDiameterNodesDSCNodesIndex, 
                      ptDSCAdjacentDiameterNodesDSCNodeIndex, 
                      ptDSCAdjacentDiameterNodesIndex }
    ::= { ptDSCAdjacentDiameterNodesTable 1 }

PtDSCAdjacentDiameterNodesEntry ::=
    SEQUENCE {
        ptDSCAdjacentDiameterNodesDSCIndex  Integer32,
        ptDSCAdjacentDiameterNodesDSCNodesIndex       Integer32,
        ptDSCAdjacentDiameterNodesDSCNodeIndex      Integer32,
        ptDSCAdjacentDiameterNodesParentOID   OBJECT IDENTIFIER,
        ptDSCAdjacentDiameterNodesRowStatus   RowStatus,
        ptDSCAdjacentDiameterNodesIndex Integer32
    }

ptDSCAdjacentDiameterNodesDSCIndex OBJECT-TYPE
    SYNTAX          Integer32 (-2147483648..2147483647)
    MAX-ACCESS      not-accessible
    STATUS          current
    DESCRIPTION     
            "This is the index of the parent type for this object.
             This parent type is DSC."
    ::= { ptDSCAdjacentDiameterNodesEntry 242 }

ptDSCAdjacentDiameterNodesDSCNodesIndex OBJECT-TYPE
    SYNTAX          Integer32 (-2147483648..2147483647)
    MAX-ACCESS      not-accessible
    STATUS          current
    DESCRIPTION     
            "This is the index of the parent type for this object.
             This parent type is DSCNodes."
    ::= { ptDSCAdjacentDiameterNodesEntry 243 }

ptDSCAdjacentDiameterNodesDSCNodeIndex OBJECT-TYPE
    SYNTAX          Integer32 (-2147483648..2147483647)
    MAX-ACCESS      not-accessible
    STATUS          current
    DESCRIPTION     
            "This is the index of the parent type for this object.
             This parent type is DSCNode."
    ::= { ptDSCAdjacentDiameterNodesEntry 244 }

ptDSCAdjacentDiameterNodesParentOID OBJECT-TYPE
    SYNTAX          OBJECT IDENTIFIER
    MAX-ACCESS      read-create
    STATUS          current
    DESCRIPTION     
            "The OID of the parent object for this instance"
    ::= { ptDSCAdjacentDiameterNodesEntry 253 }

ptDSCAdjacentDiameterNodesRowStatus OBJECT-TYPE
    SYNTAX          RowStatus
    MAX-ACCESS      read-create
    STATUS          current
    DESCRIPTION     
            "The row status for the DSCAdjacentDiameterNodes table"
    ::= { ptDSCAdjacentDiameterNodesEntry 254 }

ptDSCAdjacentDiameterNodesIndex OBJECT-TYPE
    SYNTAX          Integer32 (-2147483648..2147483647)
    MAX-ACCESS      not-accessible
    STATUS          current
    DESCRIPTION     
            "The row number for the DSCAdjacentDiameterNodes table"
    ::= { ptDSCAdjacentDiameterNodesEntry 255 }

ptDSCAdjacentDiameterNode OBJECT IDENTIFIER
    ::= { ptDSCAdjacentDiameterNodes 1807 }

ptDSCAdjacentDiameterNodeTable OBJECT-TYPE
    SYNTAX          SEQUENCE OF PtDSCAdjacentDiameterNodeEntry
    MAX-ACCESS      not-accessible
    STATUS          current
    DESCRIPTION     
            "No description supplied in the proxy config file."
    ::= { ptDSCAdjacentDiameterNode 1 }

ptDSCAdjacentDiameterNodeEntry OBJECT-TYPE
    SYNTAX          PtDSCAdjacentDiameterNodeEntry
    MAX-ACCESS      not-accessible
    STATUS          current
    DESCRIPTION     
            "A sequence of DSCAdjacentDiameterNode attributes."
    INDEX           { ptConnGroupIndex, 
                      ptDSCAdjacentDiameterNodeDSCIndex, 
                      ptDSCAdjacentDiameterNodeDSCNodesIndex, 
                      ptDSCAdjacentDiameterNodeDSCNodeIndex, 
                      ptDSCAdjacentDiameterNodeAdjacentDiameterNodesIndex, 
                      ptDSCAdjacentDiameterNodeIndex }
    ::= { ptDSCAdjacentDiameterNodeTable 1 }

PtDSCAdjacentDiameterNodeEntry ::=
    SEQUENCE {
        ptDSCAdjacentDiameterNodeType   INTEGER,
        ptDSCAdjacentDiameterNodeAdjacentDiameterID           DisplayString,
        ptDSCAdjacentDiameterNodeStatus INTEGER,
        ptDSCAdjacentDiameterNodeRealm  DisplayString,
        ptDSCAdjacentDiameterNodeTwTimer INTEGER,
        ptDSCAdjacentDiameterNodeStrictApplicationIDMatching                    INTEGER,
        ptDSCAdjacentDiameterNodeInternalID   Integer32,
        ptDSCAdjacentDiameterNodeTcTimer Integer32,
        ptDSCAdjacentDiameterNodeIMFSupport   INTEGER,
        ptDSCAdjacentDiameterNodeRemoteIPValidation           INTEGER,
        ptDSCAdjacentDiameterNodeDIDHost DisplayString,
        ptDSCAdjacentDiameterNodeName   DisplayString,
        ptDSCAdjacentDiameterNodeDPRDisconnectCause           INTEGER,
        ptDSCAdjacentDiameterNodeDiameterProtocolParameterSet                     DisplayString,
        ptDSCAdjacentDiameterNodeOutgoingAnswerRoutingTable                   DisplayString,
        ptDSCAdjacentDiameterNodeMaximumAcceptedAdvertisedCapabilities                              INTEGER,
        ptDSCAdjacentDiameterNodeOutgoingRequestRoutingTable                    DisplayString,
        ptDSCAdjacentDiameterNodeDSCIndex Integer32,
        ptDSCAdjacentDiameterNodeDSCNodesIndex      Integer32,
        ptDSCAdjacentDiameterNodeDSCNodeIndex     Integer32,
        ptDSCAdjacentDiameterNodeAdjacentDiameterNodesIndex                   Integer32,
        ptDSCAdjacentDiameterNodeActions INTEGER,
        ptDSCAdjacentDiameterNodeParentOID  OBJECT IDENTIFIER,
        ptDSCAdjacentDiameterNodeRowStatus  RowStatus,
        ptDSCAdjacentDiameterNodeIndex  Integer32
    }

ptDSCAdjacentDiameterNodeType OBJECT-TYPE
    SYNTAX          INTEGER { dscInternal(0), ua(1), diameter(2), 
                        uaXml(3), dscDb(4) }
    MAX-ACCESS      read-create
    STATUS          current
    DESCRIPTION     
            "Adjacent Diameter Node Type (DSC INTERNAL, UA, DIAMETER, UA XML, DSC DB). \nThe type is required to specify traffic restriction to the ADN. \nDIAMETER type is used for standard DSC Node connectivity. \nUA type is used for Sonus applications accepting PT enterprise AVPs such as the Sonus IWF feature. \nUA XML type is used for applications using the Sonus DSC XML protocol which may be configured to accept PT enterprise AVPs. \nDSC DB type is reserved for Diameter databases such as the Sonus DRA feature. \nDSC INTERNAL type is reserved for inter-process communication."
    ::= { ptDSCAdjacentDiameterNodeEntry 1 }

ptDSCAdjacentDiameterNodeAdjacentDiameterID OBJECT-TYPE
    SYNTAX          DisplayString (SIZE(0..255))
    MAX-ACCESS      read-create
    STATUS          current
    DESCRIPTION     
            "Adjacent Diameter Node ID. \nThe attribute is optional when creating an Adjacent Diameter Node with a DID Host. \nIf not specified, the value will be set to a concatenation of the DID Host and Realm. \nNote: This is the value set in the Origin-Host/Destination-Host AVPs. \nValid values: FQDN format or empty string."
    ::= { ptDSCAdjacentDiameterNodeEntry 2 }

ptDSCAdjacentDiameterNodeStatus OBJECT-TYPE
    SYNTAX          INTEGER { down(0), up(1), inactive(2), 
                        partiallyUp(3) }
    MAX-ACCESS      read-only
    STATUS          current
    DESCRIPTION     
            "Status of the Adjacent Diameter Node (UP/DOWN/INACTIVE). \nADN status is set to UP when at least one ADN connection is UP."
    ::= { ptDSCAdjacentDiameterNodeEntry 3 }

ptDSCAdjacentDiameterNodeRealm OBJECT-TYPE
    SYNTAX          DisplayString (SIZE(0..255))
    MAX-ACCESS      read-create
    STATUS          current
    DESCRIPTION     
            "Adjacent Diameter Node associated realm. \nIf a FQDN is specified, a Realm Definition will be automatically created if none exists. If a Realm Definition is already defined, the FQDN value will be replaced by the associated alias. \nValid values: FQDN format or existing Realm Definition alias."
    ::= { ptDSCAdjacentDiameterNodeEntry 6 }

ptDSCAdjacentDiameterNodeTwTimer OBJECT-TYPE
    SYNTAX          INTEGER { disabled(0) }
    MAX-ACCESS      read-create
    STATUS          current
    DESCRIPTION     
            "Device Watchdog Request timer initial value (DISABLED (0), 6000 to 120000 ms). \Initial timer value as per RFC3539. The value is adjusted internally higher or lower by a small random amount. \nSet to 0 to disable. If disabled, received DWR are still answered. \nDefault value: 30000 ms."
    ::= { ptDSCAdjacentDiameterNodeEntry 7 }

ptDSCAdjacentDiameterNodeStrictApplicationIDMatching OBJECT-TYPE
    SYNTAX          INTEGER { disabled(0), enabled(1) }
    MAX-ACCESS      read-create
    STATUS          current
    DESCRIPTION     
            "Validate application ID of incoming request messages (DISABLED/ENABLED). \nIf enabled, only send requests to peers for whom the application ID is authorized. \nIf the validation fails, an answer message is returned with error UNABLE_TO_DELIVER. \nDefault value: ENABLED."
    ::= { ptDSCAdjacentDiameterNodeEntry 8 }

ptDSCAdjacentDiameterNodeInternalID OBJECT-TYPE
    SYNTAX          Integer32 (-2147483648..2147483647)
    MAX-ACCESS      read-only
    STATUS          current
    DESCRIPTION     
            "Adjacent Diameter Node unique internal ID. \nReserved for internal use."
    ::= { ptDSCAdjacentDiameterNodeEntry 9 }

ptDSCAdjacentDiameterNodeTcTimer OBJECT-TYPE
    SYNTAX          Integer32 (1000..60000)
    MAX-ACCESS      read-create
    STATUS          current
    DESCRIPTION     
            "Reconnect timer initial value (1000 to 60000 ms). \Initial timer value as per RFC6733 Section 2.1. The value is adjusted internally higher or lower by a small random amount. \nDefault value: 30000 ms."
    ::= { ptDSCAdjacentDiameterNodeEntry 10 }

ptDSCAdjacentDiameterNodeIMFSupport OBJECT-TYPE
    SYNTAX          INTEGER { disabled(0), enabled(1) }
    MAX-ACCESS      read-create
    STATUS          current
    DESCRIPTION     
            "Integrated Monitoring Feed feature support for DSC (DISABLED/ENABLED). \nIMF must be licensed to enable this attribute. \nDefault value: DISABLED."
    ::= { ptDSCAdjacentDiameterNodeEntry 11 }

ptDSCAdjacentDiameterNodeRemoteIPValidation OBJECT-TYPE
    SYNTAX          INTEGER { disabled(0), enabled(1) }
    MAX-ACCESS      read-create
    STATUS          current
    DESCRIPTION     
            "Validate remote IP addresses of incoming connections (DISABLED/ENABLED). \nIf enabled, the resolved values of the Remote Host of the ADN Connection must \nmatch the source address(es) of received TCP or SCTP packets. If that fails \nthen an answer message is returned with error DIAMETER_UNKNOWN_PEER. \nDefault value: ENABLED."
    ::= { ptDSCAdjacentDiameterNodeEntry 12 }

ptDSCAdjacentDiameterNodeDIDHost OBJECT-TYPE
    SYNTAX          DisplayString (SIZE(0..255))
    MAX-ACCESS      read-create
    STATUS          current
    DESCRIPTION     
            "DSC Node Host within the realm. \nThis attribute is optional when creating an Adjacent Diameter Node with a Adjacent Diameter Node ID. \nIf specified, the value will be prepended to the Realm to create the Adjacent Node Diameter ID. \nValid values: FQDN format or empty string."
    ::= { ptDSCAdjacentDiameterNodeEntry 13 }

ptDSCAdjacentDiameterNodeName OBJECT-TYPE
    SYNTAX          DisplayString (SIZE(0..255))
    MAX-ACCESS      read-create
    STATUS          current
    DESCRIPTION     
            "Name used to logically identify the Adjacent Diameter Node. \nThe name must be unique within the DSC Instance. \nIt is recommended that the name be set to a short and unique value to facilitate logs and alarms correlation. \nIf no Name is entered on creation, or if the Name is modified to an empty string, the Adjacent Diameter ID will be used. \nValid values: alphanumeric characters, dashes, and underscores (maximum size of 32). The name is allowed to contain dots (.) and exceed maximum size only when it matches the Adjacent Diameter ID."
    ::= { ptDSCAdjacentDiameterNodeEntry 14 }

ptDSCAdjacentDiameterNodeDPRDisconnectCause OBJECT-TYPE
    SYNTAX          INTEGER { rebooting(0), busy(1), 
                        doNotWantToTalkToYou(2) }
    MAX-ACCESS      read-create
    STATUS          current
    DESCRIPTION     
            "Disconnect-Cause AVP value sent within the Disconnect-Peer-Request (as per [RFC6733]). \nThe RFC specifies the following values: REBOOTING (0), BUSY (1), DO NOT WANT TO TALK TO YOU (2) \nDefault value is: BUSY (1) \nValid values: Integer in the range 0-32"
    ::= { ptDSCAdjacentDiameterNodeEntry 15 }

ptDSCAdjacentDiameterNodeDiameterProtocolParameterSet OBJECT-TYPE
    SYNTAX          DisplayString (SIZE(0..255))
    MAX-ACCESS      read-create
    STATUS          current
    DESCRIPTION     
            "Diameter Protocol Parameter Set associated with this ADN. \nValid values: Existing Diameter Protocol Parameter Set. \nDefault value: default."
    ::= { ptDSCAdjacentDiameterNodeEntry 16 }

ptDSCAdjacentDiameterNodeOutgoingAnswerRoutingTable OBJECT-TYPE
    SYNTAX          DisplayString (SIZE(0..255))
    MAX-ACCESS      read-create
    STATUS          current
    DESCRIPTION     
            "Associated optional Routing Table to be applied to the answer message. \nRFC6733 states that a relay or a proxy agent MUST NOT modify the contents of an answer Result-Code AVP indicating a failure. \nIt is recommended to not change this attribute from the default value of dsc_default. \nValid values: dsc_default and an existing Routing Table name. \nDefault value: dsc_default."
    ::= { ptDSCAdjacentDiameterNodeEntry 17 }

ptDSCAdjacentDiameterNodeMaximumAcceptedAdvertisedCapabilities OBJECT-TYPE
    SYNTAX          INTEGER { unlimited(-1) }
    MAX-ACCESS      read-create
    STATUS          current
    DESCRIPTION     
            "Maximum number of Accepted Advertised Capabilities associated with this ADN. \nValid values: (200 to UNLIMITED). \nDefault value: 200"
    ::= { ptDSCAdjacentDiameterNodeEntry 18 }

ptDSCAdjacentDiameterNodeOutgoingRequestRoutingTable OBJECT-TYPE
    SYNTAX          DisplayString (SIZE(0..255))
    MAX-ACCESS      read-create
    STATUS          current
    DESCRIPTION     
            "Outgoing Request Routing Table \nOutgoing request messages to the ADN will be processed based on this table before topology mapping. To bypass set to dsc_default. \nValid values: dsc_default or an existing Routing Table name. \nDefault value: dsc_default."
    ::= { ptDSCAdjacentDiameterNodeEntry 19 }

ptDSCAdjacentDiameterNodeDSCIndex OBJECT-TYPE
    SYNTAX          Integer32 (-2147483648..2147483647)
    MAX-ACCESS      not-accessible
    STATUS          current
    DESCRIPTION     
            "This is the index of the parent type for this object.
             This parent type is DSC."
    ::= { ptDSCAdjacentDiameterNodeEntry 242 }

ptDSCAdjacentDiameterNodeDSCNodesIndex OBJECT-TYPE
    SYNTAX          Integer32 (-2147483648..2147483647)
    MAX-ACCESS      not-accessible
    STATUS          current
    DESCRIPTION     
            "This is the index of the parent type for this object.
             This parent type is DSCNodes."
    ::= { ptDSCAdjacentDiameterNodeEntry 243 }

ptDSCAdjacentDiameterNodeDSCNodeIndex OBJECT-TYPE
    SYNTAX          Integer32 (-2147483648..2147483647)
    MAX-ACCESS      not-accessible
    STATUS          current
    DESCRIPTION     
            "This is the index of the parent type for this object.
             This parent type is DSCNode."
    ::= { ptDSCAdjacentDiameterNodeEntry 244 }

ptDSCAdjacentDiameterNodeAdjacentDiameterNodesIndex OBJECT-TYPE
    SYNTAX          Integer32 (-2147483648..2147483647)
    MAX-ACCESS      not-accessible
    STATUS          current
    DESCRIPTION     
            "This is the index of the parent type for this object.
             This parent type is AdjacentDiameterNodes."
    ::= { ptDSCAdjacentDiameterNodeEntry 245 }

ptDSCAdjacentDiameterNodeActions OBJECT-TYPE
    SYNTAX          INTEGER { activate(1), deactivate(2) }
    MAX-ACCESS      read-create
    STATUS          current
    DESCRIPTION     
            "The OID of all possible actions for this instance"
    ::= { ptDSCAdjacentDiameterNodeEntry 252 }

ptDSCAdjacentDiameterNodeParentOID OBJECT-TYPE
    SYNTAX          OBJECT IDENTIFIER
    MAX-ACCESS      read-create
    STATUS          current
    DESCRIPTION     
            "The OID of the parent object for this instance"
    ::= { ptDSCAdjacentDiameterNodeEntry 253 }

ptDSCAdjacentDiameterNodeRowStatus OBJECT-TYPE
    SYNTAX          RowStatus
    MAX-ACCESS      read-create
    STATUS          current
    DESCRIPTION     
            "The row status for the DSCAdjacentDiameterNode table"
    ::= { ptDSCAdjacentDiameterNodeEntry 254 }

ptDSCAdjacentDiameterNodeIndex OBJECT-TYPE
    SYNTAX          Integer32 (-2147483648..2147483647)
    MAX-ACCESS      not-accessible
    STATUS          current
    DESCRIPTION     
            "The row number for the DSCAdjacentDiameterNode table"
    ::= { ptDSCAdjacentDiameterNodeEntry 255 }

ptDSCADNConnection OBJECT IDENTIFIER
    ::= { ptDSCAdjacentDiameterNode 1840 }

ptDSCADNConnectionTable OBJECT-TYPE
    SYNTAX          SEQUENCE OF PtDSCADNConnectionEntry
    MAX-ACCESS      not-accessible
    STATUS          current
    DESCRIPTION     
            "No description supplied in the proxy config file."
    ::= { ptDSCADNConnection 1 }

ptDSCADNConnectionEntry OBJECT-TYPE
    SYNTAX          PtDSCADNConnectionEntry
    MAX-ACCESS      not-accessible
    STATUS          current
    DESCRIPTION     
            "A sequence of DSCADNConnection attributes."
    INDEX           { ptConnGroupIndex, ptDSCADNConnectionDSCIndex, 
                      ptDSCADNConnectionDSCNodesIndex, 
                      ptDSCADNConnectionDSCNodeIndex, 
                      ptDSCADNConnectionAdjacentDiameterNodesIndex, 
                      ptDSCADNConnectionAdjacentDiameterNodeIndex, 
                      ptDSCADNConnectionIndex }
    ::= { ptDSCADNConnectionTable 1 }

PtDSCADNConnectionEntry ::=
    SEQUENCE {
        ptDSCADNConnectionSlot          INTEGER,
        ptDSCADNConnectionTransportType INTEGER,
        ptDSCADNConnectionLocalHost     DisplayString,
        ptDSCADNConnectionRemoteHost    DisplayString,
        ptDSCADNConnectionRemotePort    Integer32,
        ptDSCADNConnectionStatus        INTEGER,
        ptDSCADNConnectionSecurityParameterSet      DisplayString,
        ptDSCADNConnectionCapacityParameterSet      DisplayString,
        ptDSCADNConnectionSCTPParameterSet  DisplayString,
        ptDSCADNConnectionCERParameterSet DisplayString,
        ptDSCADNConnectionRxMessageCount Integer32,
        ptDSCADNConnectionTxMessageCount Integer32,
        ptDSCADNConnectionInternalID    Integer32,
        ptDSCADNConnectionUserActivation INTEGER,
        ptDSCADNConnectionLocalPort     INTEGER,
        ptDSCADNConnectionEncryption    DisplayString,
        ptDSCADNConnectionVendorID      DisplayString,
        ptDSCADNConnectionProductName   DisplayString,
        ptDSCADNConnectionFirmwareRevision  Integer32,
        ptDSCADNConnectionDSCIndex      Integer32,
        ptDSCADNConnectionDSCNodesIndex Integer32,
        ptDSCADNConnectionDSCNodeIndex  Integer32,
        ptDSCADNConnectionAdjacentDiameterNodesIndex            Integer32,
        ptDSCADNConnectionAdjacentDiameterNodeIndex           Integer32,
        ptDSCADNConnectionActions       INTEGER,
        ptDSCADNConnectionParentOID     OBJECT IDENTIFIER,
        ptDSCADNConnectionRowStatus     RowStatus,
        ptDSCADNConnectionIndex         Integer32
    }

ptDSCADNConnectionSlot OBJECT-TYPE
    SYNTAX          INTEGER { any(0) }
    MAX-ACCESS      read-only
    STATUS          current
    DESCRIPTION     
            "Adjacent Diameter Node associated DSC slot. \nValid values: Available routing CPU slot number and ANY (0). \nWhen set to ANY, the Adjacent Diameter Node will be associated with any one of the available routing CPU slots that the Local Host attribute can resolve to. All the available routing slots will attempt to bring the connection UP depending on the Transport Type attribute. Once the connection is successful on one of the routing CPUs, the other routing CPUs will stop attempting to bring the connection in service. \nWhen the Lcoal host attribute is set to a hostname that resolves to multiple IP addresses defined on different routing CPUs, then the first routing CPU that is able to bring the connection UP is chosen. Other routing CPUs close their connection and stop initiating and accepting connections. \nIt is not possible to create more than one Adjacent Diameter Node Connection when the Slot attribute is set to ANY."
    ::= { ptDSCADNConnectionEntry 1 }

ptDSCADNConnectionTransportType OBJECT-TYPE
    SYNTAX          INTEGER { sctp(0), tcp(1), tipc(2), serverOnly(100) }
    MAX-ACCESS      read-create
    STATUS          current
    DESCRIPTION     
            "Transport Type (SCTP, TCP, TIPC, SERVER ONLY) \nSet to the transport type between the DSC Node and the ADN. \nThe TCP and SCTP types indicate the transport type that will be used for the outgoing connections. Incoming connections may still be accepted by transport servers of either protocol. \nThe TIPC type is reserved for DSC INTERNAL ADNs. \nIf setting the SERVER ONLY option, no outgoing transport connections will be attempted. Make sure an associated Transport Server object is available. \nNote: 3GPP specifications such as TS 29.272 (S6a, S6d, S13, S7, ...) require the use of SCTP. Default value: SCTP."
    ::= { ptDSCADNConnectionEntry 2 }

ptDSCADNConnectionLocalHost OBJECT-TYPE
    SYNTAX          DisplayString (SIZE(0..255))
    MAX-ACCESS      read-create
    STATUS          current
    DESCRIPTION     
            "Local host for the Adjacent Diameter Node connection. \nMandatory or optional based on the connection and transport types. \nValid values: Hostname or IP address. Ignored for TIPC & TCP Transport Types. \nDefault value: slot<Slot>.<DSC Node.Node Diameter ID>"
    ::= { ptDSCADNConnectionEntry 3 }

ptDSCADNConnectionRemoteHost OBJECT-TYPE
    SYNTAX          DisplayString (SIZE(0..255))
    MAX-ACCESS      read-create
    STATUS          current
    DESCRIPTION     
            "Remote host for the Adjacent Diameter Node connection. \nValid values: Hostname or IP address. Ignored for TIPC and SERVER ONLY Transport Types. \nDefault value: ADN.Adjacent Diameter ID."
    ::= { ptDSCADNConnectionEntry 4 }

ptDSCADNConnectionRemotePort OBJECT-TYPE
    SYNTAX          Integer32
    MAX-ACCESS      read-create
    STATUS          current
    DESCRIPTION     
            "Remote port for the Adjacent Diameter Node connection (1 to 65535). \nDefault value: 3868."
    ::= { ptDSCADNConnectionEntry 5 }

ptDSCADNConnectionStatus OBJECT-TYPE
    SYNTAX          INTEGER { down(0), up(1), inactive(2), 
                        partiallyUp(3) }
    MAX-ACCESS      read-only
    STATUS          current
    DESCRIPTION     
            "Status of the Adjacent Diameter Node connection (UP/DOWN/INACTIVE)."
    ::= { ptDSCADNConnectionEntry 6 }

ptDSCADNConnectionSecurityParameterSet OBJECT-TYPE
    SYNTAX          DisplayString (SIZE(0..255))
    MAX-ACCESS      read-create
    STATUS          current
    DESCRIPTION     
            "Security Parameter Set associated with this ADN Connection. \nValid values: Existing Security Parameter Set. \nDefault value: default."
    ::= { ptDSCADNConnectionEntry 7 }

ptDSCADNConnectionCapacityParameterSet OBJECT-TYPE
    SYNTAX          DisplayString (SIZE(0..255))
    MAX-ACCESS      read-create
    STATUS          current
    DESCRIPTION     
            "Capacity Parameter Set associated with this ADN Connection. \nValid values: Existing Capacity Parameter Set. \nDefault value: default."
    ::= { ptDSCADNConnectionEntry 8 }

ptDSCADNConnectionSCTPParameterSet OBJECT-TYPE
    SYNTAX          DisplayString (SIZE(0..255))
    MAX-ACCESS      read-create
    STATUS          current
    DESCRIPTION     
            "SCTP Parameter Set associated with this ADN Connection. \nValid values: Existing SCTP Parameter Set. \nDefault value: default."
    ::= { ptDSCADNConnectionEntry 9 }

ptDSCADNConnectionCERParameterSet OBJECT-TYPE
    SYNTAX          DisplayString (SIZE(0..255))
    MAX-ACCESS      read-create
    STATUS          current
    DESCRIPTION     
            "CER Parameter Set associated with this ADN Connection. \nValid values: Existing CER Parameter Set. \nDefault value: default."
    ::= { ptDSCADNConnectionEntry 10 }

ptDSCADNConnectionRxMessageCount OBJECT-TYPE
    SYNTAX          Integer32 (-2147483648..2147483647)
    MAX-ACCESS      read-only
    STATUS          current
    DESCRIPTION     
            "Received message count, per second."
    ::= { ptDSCADNConnectionEntry 11 }

ptDSCADNConnectionTxMessageCount OBJECT-TYPE
    SYNTAX          Integer32 (-2147483648..2147483647)
    MAX-ACCESS      read-only
    STATUS          current
    DESCRIPTION     
            "Transmitted message count, per second."
    ::= { ptDSCADNConnectionEntry 12 }

ptDSCADNConnectionInternalID OBJECT-TYPE
    SYNTAX          Integer32 (-2147483648..2147483647)
    MAX-ACCESS      read-only
    STATUS          current
    DESCRIPTION     
            "Adjacent Diameter Node Connection unique internal ID. \nReserved for internal use."
    ::= { ptDSCADNConnectionEntry 13 }

ptDSCADNConnectionUserActivation OBJECT-TYPE
    SYNTAX          INTEGER { disabled(0), enabled(1) }
    MAX-ACCESS      read-only
    STATUS          current
    DESCRIPTION     
            "User activation (ENABLED/DISABLED). \nThe ADN Connection can be activated while the ADN itself is inactive. In this scenario, the connection remains INACTIVE but the User Activation attribute is set to ENABLED. When the ADN is activated, the user activated ADN Connections will also be activated. \nDefault value: DISABLED."
    ::= { ptDSCADNConnectionEntry 14 }

ptDSCADNConnectionLocalPort OBJECT-TYPE
    SYNTAX          INTEGER { ephemeral(0) }
    MAX-ACCESS      read-create
    STATUS          current
    DESCRIPTION     
            "Local port for the Adjacent Diameter Node connection (EPHEMERAL, 1 to 65535). \nOnly applicable to Transport Type SCTP. For all other types, the value is set to EPHEMERAL and cannot be modified. \nOnly applicable to outgoing connections, and has no relation to the server used to accept incoming connections. \nDefault value: EPHEMERAL."
    ::= { ptDSCADNConnectionEntry 15 }

ptDSCADNConnectionEncryption OBJECT-TYPE
    SYNTAX          DisplayString (SIZE(0..255))
    MAX-ACCESS      read-only
    STATUS          current
    DESCRIPTION     
            "Encryption currently used for this ADN Connection."
    ::= { ptDSCADNConnectionEntry 16 }

ptDSCADNConnectionVendorID OBJECT-TYPE
    SYNTAX          DisplayString (SIZE(0..255))
    MAX-ACCESS      read-only
    STATUS          current
    DESCRIPTION     
            "Diameter Software Vendor ID as extracted from the Capabilities Exchange Request (CE-R) or Answer (CE-A) message. \nIf the Vendor-Id AVP received has a value 0 or it was not received, this field will be set to Invalid (0)."
    ::= { ptDSCADNConnectionEntry 19 }

ptDSCADNConnectionProductName OBJECT-TYPE
    SYNTAX          DisplayString (SIZE(0..255))
    MAX-ACCESS      read-only
    STATUS          current
    DESCRIPTION     
            "Vendor-assigned name for the product extracted from the Capabilities Exchange Request (CE-R) or Answer (CE-A) message. \nIf no Product-Name AVP is received, this field will be empty."
    ::= { ptDSCADNConnectionEntry 20 }

ptDSCADNConnectionFirmwareRevision OBJECT-TYPE
    SYNTAX          Integer32 (-2147483648..2147483647)
    MAX-ACCESS      read-only
    STATUS          current
    DESCRIPTION     
            "Firmware revision of the issuing device extracted from the Capabilities Exchange Request (CE-R) or Answer (CE-A) message. \nIf no Firmware-Revision AVP is received, this field will be 0."
    ::= { ptDSCADNConnectionEntry 21 }

ptDSCADNConnectionDSCIndex OBJECT-TYPE
    SYNTAX          Integer32 (-2147483648..2147483647)
    MAX-ACCESS      not-accessible
    STATUS          current
    DESCRIPTION     
            "This is the index of the parent type for this object.
             This parent type is DSC."
    ::= { ptDSCADNConnectionEntry 242 }

ptDSCADNConnectionDSCNodesIndex OBJECT-TYPE
    SYNTAX          Integer32 (-2147483648..2147483647)
    MAX-ACCESS      not-accessible
    STATUS          current
    DESCRIPTION     
            "This is the index of the parent type for this object.
             This parent type is DSCNodes."
    ::= { ptDSCADNConnectionEntry 243 }

ptDSCADNConnectionDSCNodeIndex OBJECT-TYPE
    SYNTAX          Integer32 (-2147483648..2147483647)
    MAX-ACCESS      not-accessible
    STATUS          current
    DESCRIPTION     
            "This is the index of the parent type for this object.
             This parent type is DSCNode."
    ::= { ptDSCADNConnectionEntry 244 }

ptDSCADNConnectionAdjacentDiameterNodesIndex OBJECT-TYPE
    SYNTAX          Integer32 (-2147483648..2147483647)
    MAX-ACCESS      not-accessible
    STATUS          current
    DESCRIPTION     
            "This is the index of the parent type for this object.
             This parent type is AdjacentDiameterNodes."
    ::= { ptDSCADNConnectionEntry 245 }

ptDSCADNConnectionAdjacentDiameterNodeIndex OBJECT-TYPE
    SYNTAX          Integer32 (-2147483648..2147483647)
    MAX-ACCESS      not-accessible
    STATUS          current
    DESCRIPTION     
            "This is the index of the parent type for this object.
             This parent type is AdjacentDiameterNode."
    ::= { ptDSCADNConnectionEntry 246 }

ptDSCADNConnectionActions OBJECT-TYPE
    SYNTAX          INTEGER { activate(1), deactivate(2) }
    MAX-ACCESS      read-create
    STATUS          current
    DESCRIPTION     
            "The OID of all possible actions for this instance"
    ::= { ptDSCADNConnectionEntry 252 }

ptDSCADNConnectionParentOID OBJECT-TYPE
    SYNTAX          OBJECT IDENTIFIER
    MAX-ACCESS      read-create
    STATUS          current
    DESCRIPTION     
            "The OID of the parent object for this instance"
    ::= { ptDSCADNConnectionEntry 253 }

ptDSCADNConnectionRowStatus OBJECT-TYPE
    SYNTAX          RowStatus
    MAX-ACCESS      read-create
    STATUS          current
    DESCRIPTION     
            "The row status for the DSCADNConnection table"
    ::= { ptDSCADNConnectionEntry 254 }

ptDSCADNConnectionIndex OBJECT-TYPE
    SYNTAX          Integer32 (-2147483648..2147483647)
    MAX-ACCESS      not-accessible
    STATUS          current
    DESCRIPTION     
            "The row number for the DSCADNConnection table"
    ::= { ptDSCADNConnectionEntry 255 }

ptDSCAdvertisedCapabilities OBJECT IDENTIFIER
    ::= { ptDSCADNConnection 1834 }

ptDSCAdvertisedCapabilitiesTable OBJECT-TYPE
    SYNTAX          SEQUENCE OF PtDSCAdvertisedCapabilitiesEntry
    MAX-ACCESS      not-accessible
    STATUS          current
    DESCRIPTION     
            "No description supplied in the proxy config file."
    ::= { ptDSCAdvertisedCapabilities 1 }

ptDSCAdvertisedCapabilitiesEntry OBJECT-TYPE
    SYNTAX          PtDSCAdvertisedCapabilitiesEntry
    MAX-ACCESS      not-accessible
    STATUS          current
    DESCRIPTION     
            "A sequence of DSCAdvertisedCapabilities attributes."
    INDEX           { ptConnGroupIndex, 
                      ptDSCAdvertisedCapabilitiesDSCIndex, 
                      ptDSCAdvertisedCapabilitiesDSCNodesIndex, 
                      ptDSCAdvertisedCapabilitiesDSCNodeIndex, 
                      ptDSCAdvertisedCapabilitiesAdjacentDiameterNodesIndex, 
                      ptDSCAdvertisedCapabilitiesAdjacentDiameterNodeIndex, 
                      ptDSCAdvertisedCapabilitiesADNConnectionIndex, 
                      ptDSCAdvertisedCapabilitiesIndex }
    ::= { ptDSCAdvertisedCapabilitiesTable 1 }

PtDSCAdvertisedCapabilitiesEntry ::=
    SEQUENCE {
        ptDSCAdvertisedCapabilitiesDSCIndex   Integer32,
        ptDSCAdvertisedCapabilitiesDSCNodesIndex        Integer32,
        ptDSCAdvertisedCapabilitiesDSCNodeIndex       Integer32,
        ptDSCAdvertisedCapabilitiesAdjacentDiameterNodesIndex                     Integer32,
        ptDSCAdvertisedCapabilitiesAdjacentDiameterNodeIndex                    Integer32,
        ptDSCAdvertisedCapabilitiesADNConnectionIndex             Integer32,
        ptDSCAdvertisedCapabilitiesParentOID    OBJECT IDENTIFIER,
        ptDSCAdvertisedCapabilitiesRowStatus    RowStatus,
        ptDSCAdvertisedCapabilitiesIndex Integer32
    }

ptDSCAdvertisedCapabilitiesDSCIndex OBJECT-TYPE
    SYNTAX          Integer32 (-2147483648..2147483647)
    MAX-ACCESS      not-accessible
    STATUS          current
    DESCRIPTION     
            "This is the index of the parent type for this object.
             This parent type is DSC."
    ::= { ptDSCAdvertisedCapabilitiesEntry 242 }

ptDSCAdvertisedCapabilitiesDSCNodesIndex OBJECT-TYPE
    SYNTAX          Integer32 (-2147483648..2147483647)
    MAX-ACCESS      not-accessible
    STATUS          current
    DESCRIPTION     
            "This is the index of the parent type for this object.
             This parent type is DSCNodes."
    ::= { ptDSCAdvertisedCapabilitiesEntry 243 }

ptDSCAdvertisedCapabilitiesDSCNodeIndex OBJECT-TYPE
    SYNTAX          Integer32 (-2147483648..2147483647)
    MAX-ACCESS      not-accessible
    STATUS          current
    DESCRIPTION     
            "This is the index of the parent type for this object.
             This parent type is DSCNode."
    ::= { ptDSCAdvertisedCapabilitiesEntry 244 }

ptDSCAdvertisedCapabilitiesAdjacentDiameterNodesIndex OBJECT-TYPE
    SYNTAX          Integer32 (-2147483648..2147483647)
    MAX-ACCESS      not-accessible
    STATUS          current
    DESCRIPTION     
            "This is the index of the parent type for this object.
             This parent type is AdjacentDiameterNodes."
    ::= { ptDSCAdvertisedCapabilitiesEntry 245 }

ptDSCAdvertisedCapabilitiesAdjacentDiameterNodeIndex OBJECT-TYPE
    SYNTAX          Integer32 (-2147483648..2147483647)
    MAX-ACCESS      not-accessible
    STATUS          current
    DESCRIPTION     
            "This is the index of the parent type for this object.
             This parent type is AdjacentDiameterNode."
    ::= { ptDSCAdvertisedCapabilitiesEntry 246 }

ptDSCAdvertisedCapabilitiesADNConnectionIndex OBJECT-TYPE
    SYNTAX          Integer32 (-2147483648..2147483647)
    MAX-ACCESS      not-accessible
    STATUS          current
    DESCRIPTION     
            "This is the index of the parent type for this object.
             This parent type is ADNConnection."
    ::= { ptDSCAdvertisedCapabilitiesEntry 247 }

ptDSCAdvertisedCapabilitiesParentOID OBJECT-TYPE
    SYNTAX          OBJECT IDENTIFIER
    MAX-ACCESS      read-create
    STATUS          current
    DESCRIPTION     
            "The OID of the parent object for this instance"
    ::= { ptDSCAdvertisedCapabilitiesEntry 253 }

ptDSCAdvertisedCapabilitiesRowStatus OBJECT-TYPE
    SYNTAX          RowStatus
    MAX-ACCESS      read-create
    STATUS          current
    DESCRIPTION     
            "The row status for the DSCAdvertisedCapabilities table"
    ::= { ptDSCAdvertisedCapabilitiesEntry 254 }

ptDSCAdvertisedCapabilitiesIndex OBJECT-TYPE
    SYNTAX          Integer32 (-2147483648..2147483647)
    MAX-ACCESS      not-accessible
    STATUS          current
    DESCRIPTION     
            "The row number for the DSCAdvertisedCapabilities table"
    ::= { ptDSCAdvertisedCapabilitiesEntry 255 }

ptDSCAdvertisedCapability OBJECT IDENTIFIER
    ::= { ptDSCAdvertisedCapabilities 1835 }

ptDSCAdvertisedCapabilityTable OBJECT-TYPE
    SYNTAX          SEQUENCE OF PtDSCAdvertisedCapabilityEntry
    MAX-ACCESS      not-accessible
    STATUS          current
    DESCRIPTION     
            "No description supplied in the proxy config file."
    ::= { ptDSCAdvertisedCapability 1 }

ptDSCAdvertisedCapabilityEntry OBJECT-TYPE
    SYNTAX          PtDSCAdvertisedCapabilityEntry
    MAX-ACCESS      not-accessible
    STATUS          current
    DESCRIPTION     
            "A sequence of DSCAdvertisedCapability attributes."
    INDEX           { ptConnGroupIndex, 
                      ptDSCAdvertisedCapabilityDSCIndex, 
                      ptDSCAdvertisedCapabilityDSCNodesIndex, 
                      ptDSCAdvertisedCapabilityDSCNodeIndex, 
                      ptDSCAdvertisedCapabilityAdjacentDiameterNodesIndex, 
                      ptDSCAdvertisedCapabilityAdjacentDiameterNodeIndex, 
                      ptDSCAdvertisedCapabilityADNConnectionIndex, 
                      ptDSCAdvertisedCapabilityAdvertisedCapabilitiesIndex, 
                      ptDSCAdvertisedCapabilityIndex }
    ::= { ptDSCAdvertisedCapabilityTable 1 }

PtDSCAdvertisedCapabilityEntry ::=
    SEQUENCE {
        ptDSCAdvertisedCapabilityVendorID DisplayString,
        ptDSCAdvertisedCapabilityApplicationID      DisplayString,
        ptDSCAdvertisedCapabilityType   INTEGER,
        ptDSCAdvertisedCapabilityDSCIndex Integer32,
        ptDSCAdvertisedCapabilityDSCNodesIndex      Integer32,
        ptDSCAdvertisedCapabilityDSCNodeIndex     Integer32,
        ptDSCAdvertisedCapabilityAdjacentDiameterNodesIndex                   Integer32,
        ptDSCAdvertisedCapabilityAdjacentDiameterNodeIndex                  Integer32,
        ptDSCAdvertisedCapabilityADNConnectionIndex           Integer32,
        ptDSCAdvertisedCapabilityAdvertisedCapabilitiesIndex                    Integer32,
        ptDSCAdvertisedCapabilityParentOID  OBJECT IDENTIFIER,
        ptDSCAdvertisedCapabilityRowStatus  RowStatus,
        ptDSCAdvertisedCapabilityIndex  Integer32
    }

ptDSCAdvertisedCapabilityVendorID OBJECT-TYPE
    SYNTAX          DisplayString (SIZE(0..255))
    MAX-ACCESS      read-only
    STATUS          current
    DESCRIPTION     
            "Supported Vendor ID extracted from the Capacity Exchange Request (CE-R) or Answer (CE-A) message."
    ::= { ptDSCAdvertisedCapabilityEntry 1 }

ptDSCAdvertisedCapabilityApplicationID OBJECT-TYPE
    SYNTAX          DisplayString (SIZE(0..255))
    MAX-ACCESS      read-only
    STATUS          current
    DESCRIPTION     
            "Supported Application ID extracted from the Capacity Exchange Request (CE-R) or Answer (CE-A) message."
    ::= { ptDSCAdvertisedCapabilityEntry 2 }

ptDSCAdvertisedCapabilityType OBJECT-TYPE
    SYNTAX          INTEGER { auth(0), acct(1) }
    MAX-ACCESS      read-only
    STATUS          current
    DESCRIPTION     
            "Advertised Capability Node Type (ACCT/AUTH). \nACCT refers to accounting, whereas AUTH refers to authorization/authentication."
    ::= { ptDSCAdvertisedCapabilityEntry 3 }

ptDSCAdvertisedCapabilityDSCIndex OBJECT-TYPE
    SYNTAX          Integer32 (-2147483648..2147483647)
    MAX-ACCESS      not-accessible
    STATUS          current
    DESCRIPTION     
            "This is the index of the parent type for this object.
             This parent type is DSC."
    ::= { ptDSCAdvertisedCapabilityEntry 242 }

ptDSCAdvertisedCapabilityDSCNodesIndex OBJECT-TYPE
    SYNTAX          Integer32 (-2147483648..2147483647)
    MAX-ACCESS      not-accessible
    STATUS          current
    DESCRIPTION     
            "This is the index of the parent type for this object.
             This parent type is DSCNodes."
    ::= { ptDSCAdvertisedCapabilityEntry 243 }

ptDSCAdvertisedCapabilityDSCNodeIndex OBJECT-TYPE
    SYNTAX          Integer32 (-2147483648..2147483647)
    MAX-ACCESS      not-accessible
    STATUS          current
    DESCRIPTION     
            "This is the index of the parent type for this object.
             This parent type is DSCNode."
    ::= { ptDSCAdvertisedCapabilityEntry 244 }

ptDSCAdvertisedCapabilityAdjacentDiameterNodesIndex OBJECT-TYPE
    SYNTAX          Integer32 (-2147483648..2147483647)
    MAX-ACCESS      not-accessible
    STATUS          current
    DESCRIPTION     
            "This is the index of the parent type for this object.
             This parent type is AdjacentDiameterNodes."
    ::= { ptDSCAdvertisedCapabilityEntry 245 }

ptDSCAdvertisedCapabilityAdjacentDiameterNodeIndex OBJECT-TYPE
    SYNTAX          Integer32 (-2147483648..2147483647)
    MAX-ACCESS      not-accessible
    STATUS          current
    DESCRIPTION     
            "This is the index of the parent type for this object.
             This parent type is AdjacentDiameterNode."
    ::= { ptDSCAdvertisedCapabilityEntry 246 }

ptDSCAdvertisedCapabilityADNConnectionIndex OBJECT-TYPE
    SYNTAX          Integer32 (-2147483648..2147483647)
    MAX-ACCESS      not-accessible
    STATUS          current
    DESCRIPTION     
            "This is the index of the parent type for this object.
             This parent type is ADNConnection."
    ::= { ptDSCAdvertisedCapabilityEntry 247 }

ptDSCAdvertisedCapabilityAdvertisedCapabilitiesIndex OBJECT-TYPE
    SYNTAX          Integer32 (-2147483648..2147483647)
    MAX-ACCESS      not-accessible
    STATUS          current
    DESCRIPTION     
            "This is the index of the parent type for this object.
             This parent type is AdvertisedCapabilities."
    ::= { ptDSCAdvertisedCapabilityEntry 248 }

ptDSCAdvertisedCapabilityParentOID OBJECT-TYPE
    SYNTAX          OBJECT IDENTIFIER
    MAX-ACCESS      read-create
    STATUS          current
    DESCRIPTION     
            "The OID of the parent object for this instance"
    ::= { ptDSCAdvertisedCapabilityEntry 253 }

ptDSCAdvertisedCapabilityRowStatus OBJECT-TYPE
    SYNTAX          RowStatus
    MAX-ACCESS      read-create
    STATUS          current
    DESCRIPTION     
            "The row status for the DSCAdvertisedCapability table"
    ::= { ptDSCAdvertisedCapabilityEntry 254 }

ptDSCAdvertisedCapabilityIndex OBJECT-TYPE
    SYNTAX          Integer32 (-2147483648..2147483647)
    MAX-ACCESS      not-accessible
    STATUS          current
    DESCRIPTION     
            "The row number for the DSCAdvertisedCapability table"
    ::= { ptDSCAdvertisedCapabilityEntry 255 }

ptDSCTransportServers OBJECT IDENTIFIER
    ::= { ptDSCDSCNode 1808 }

ptDSCTransportServersTable OBJECT-TYPE
    SYNTAX          SEQUENCE OF PtDSCTransportServersEntry
    MAX-ACCESS      not-accessible
    STATUS          current
    DESCRIPTION     
            "No description supplied in the proxy config file."
    ::= { ptDSCTransportServers 1 }

ptDSCTransportServersEntry OBJECT-TYPE
    SYNTAX          PtDSCTransportServersEntry
    MAX-ACCESS      not-accessible
    STATUS          current
    DESCRIPTION     
            "A sequence of DSCTransportServers attributes."
    INDEX           { ptConnGroupIndex, ptDSCTransportServersDSCIndex, 
                      ptDSCTransportServersDSCNodesIndex, 
                      ptDSCTransportServersDSCNodeIndex, 
                      ptDSCTransportServersIndex }
    ::= { ptDSCTransportServersTable 1 }

PtDSCTransportServersEntry ::=
    SEQUENCE {
        ptDSCTransportServersDSCIndex   Integer32,
        ptDSCTransportServersDSCNodesIndex  Integer32,
        ptDSCTransportServersDSCNodeIndex Integer32,
        ptDSCTransportServersParentOID  OBJECT IDENTIFIER,
        ptDSCTransportServersRowStatus  RowStatus,
        ptDSCTransportServersIndex      Integer32
    }

ptDSCTransportServersDSCIndex OBJECT-TYPE
    SYNTAX          Integer32 (-2147483648..2147483647)
    MAX-ACCESS      not-accessible
    STATUS          current
    DESCRIPTION     
            "This is the index of the parent type for this object.
             This parent type is DSC."
    ::= { ptDSCTransportServersEntry 242 }

ptDSCTransportServersDSCNodesIndex OBJECT-TYPE
    SYNTAX          Integer32 (-2147483648..2147483647)
    MAX-ACCESS      not-accessible
    STATUS          current
    DESCRIPTION     
            "This is the index of the parent type for this object.
             This parent type is DSCNodes."
    ::= { ptDSCTransportServersEntry 243 }

ptDSCTransportServersDSCNodeIndex OBJECT-TYPE
    SYNTAX          Integer32 (-2147483648..2147483647)
    MAX-ACCESS      not-accessible
    STATUS          current
    DESCRIPTION     
            "This is the index of the parent type for this object.
             This parent type is DSCNode."
    ::= { ptDSCTransportServersEntry 244 }

ptDSCTransportServersParentOID OBJECT-TYPE
    SYNTAX          OBJECT IDENTIFIER
    MAX-ACCESS      read-create
    STATUS          current
    DESCRIPTION     
            "The OID of the parent object for this instance"
    ::= { ptDSCTransportServersEntry 253 }

ptDSCTransportServersRowStatus OBJECT-TYPE
    SYNTAX          RowStatus
    MAX-ACCESS      read-create
    STATUS          current
    DESCRIPTION     
            "The row status for the DSCTransportServers table"
    ::= { ptDSCTransportServersEntry 254 }

ptDSCTransportServersIndex OBJECT-TYPE
    SYNTAX          Integer32 (-2147483648..2147483647)
    MAX-ACCESS      not-accessible
    STATUS          current
    DESCRIPTION     
            "The row number for the DSCTransportServers table"
    ::= { ptDSCTransportServersEntry 255 }

ptDSCTransportServer OBJECT IDENTIFIER
    ::= { ptDSCTransportServers 1809 }

ptDSCTransportServerTable OBJECT-TYPE
    SYNTAX          SEQUENCE OF PtDSCTransportServerEntry
    MAX-ACCESS      not-accessible
    STATUS          current
    DESCRIPTION     
            "No description supplied in the proxy config file."
    ::= { ptDSCTransportServer 1 }

ptDSCTransportServerEntry OBJECT-TYPE
    SYNTAX          PtDSCTransportServerEntry
    MAX-ACCESS      not-accessible
    STATUS          current
    DESCRIPTION     
            "A sequence of DSCTransportServer attributes."
    INDEX           { ptConnGroupIndex, ptDSCTransportServerDSCIndex, 
                      ptDSCTransportServerDSCNodesIndex, 
                      ptDSCTransportServerDSCNodeIndex, 
                      ptDSCTransportServerTransportServersIndex, 
                      ptDSCTransportServerIndex }
    ::= { ptDSCTransportServerTable 1 }

PtDSCTransportServerEntry ::=
    SEQUENCE {
        ptDSCTransportServerSlot        INTEGER,
        ptDSCTransportServerStatus      INTEGER,
        ptDSCTransportServerInternalID  Integer32,
        ptDSCTransportServerTransportType INTEGER,
        ptDSCTransportServerPort        Integer32,
        ptDSCTransportServerHost        DisplayString,
        ptDSCTransportServerADNProtocol INTEGER,
        ptDSCTransportServerSecurityParameterSet        DisplayString,
        ptDSCTransportServerRemoteIPValidation      INTEGER,
        ptDSCTransportServerDSCIndex    Integer32,
        ptDSCTransportServerDSCNodesIndex Integer32,
        ptDSCTransportServerDSCNodeIndex Integer32,
        ptDSCTransportServerTransportServersIndex         Integer32,
        ptDSCTransportServerActions     INTEGER,
        ptDSCTransportServerParentOID   OBJECT IDENTIFIER,
        ptDSCTransportServerRowStatus   RowStatus,
        ptDSCTransportServerIndex       Integer32
    }

ptDSCTransportServerSlot OBJECT-TYPE
    SYNTAX          INTEGER { all(0) }
    MAX-ACCESS      read-only
    STATUS          current
    DESCRIPTION     
            "Transport server associated DSC slot. \nValid values: Available routing CPU slot number and ALL (0). \nWhen set to ALL, the transport server is created on all the available routing CPUs."
    ::= { ptDSCTransportServerEntry 1 }

ptDSCTransportServerStatus OBJECT-TYPE
    SYNTAX          INTEGER { down(0), up(1), inactive(2), 
                        partiallyUp(3) }
    MAX-ACCESS      read-only
    STATUS          current
    DESCRIPTION     
            "Status of the Transport Server (INACTIVE/DOWN/UP/PARTIALLY UP). \nWhen the Slot attribute is set to ALL (0), the PARTIALLY UP status means that one or more slots have port conflicts with existing servers and established ADN Connections and cannot bring this server in service. Please check the server unavailable major alarm (1807) for the list of slots that cannot bring the Transport Server in service locally."
    ::= { ptDSCTransportServerEntry 2 }

ptDSCTransportServerInternalID OBJECT-TYPE
    SYNTAX          Integer32 (-2147483648..2147483647)
    MAX-ACCESS      read-only
    STATUS          current
    DESCRIPTION     
            "Transport Server unique internal ID. \nReserved for internal use."
    ::= { ptDSCTransportServerEntry 3 }

ptDSCTransportServerTransportType OBJECT-TYPE
    SYNTAX          INTEGER { sctp(0), tcp(1) }
    MAX-ACCESS      read-create
    STATUS          current
    DESCRIPTION     
            "Transport Type (TCP/SCTP). \nThe type of transport used for incoming connections. \nTo establish a connection, each ADN connecting to this server requires an associated ADN Connection with matching or SERVER ONLY type. \nDefault value: SCTP."
    ::= { ptDSCTransportServerEntry 4 }

ptDSCTransportServerPort OBJECT-TYPE
    SYNTAX          Integer32
    MAX-ACCESS      read-create
    STATUS          current
    DESCRIPTION     
            "Port used for this server (1 to 65535). \nRFC6733 recommended port values are: \n 3868 for non-encrypted or CE-R/CE-A enabled TLS \n 5868 for full-time TLS/TCP or DTLS/SCTP (as per IANA reserved value)"
    ::= { ptDSCTransportServerEntry 5 }

ptDSCTransportServerHost OBJECT-TYPE
    SYNTAX          DisplayString (SIZE(0..255))
    MAX-ACCESS      read-create
    STATUS          current
    DESCRIPTION     
            "Hostname or IP address of this server. \nIf a hostname is provided, then it may resolve to multiple IP addresses. In this case, a TCP server uses the first IP address, whereas the SCTP server uses all IP addresses. \nThe IP addresses must be provisioned on the card hosting the slot for the server to activate. \nValid values: Hostname or IP address."
    ::= { ptDSCTransportServerEntry 6 }

ptDSCTransportServerADNProtocol OBJECT-TYPE
    SYNTAX          INTEGER { diameter(0), xml(1) }
    MAX-ACCESS      read-create
    STATUS          current
    DESCRIPTION     
            "Protocol used by the ADN Connections associated with the Transport Server (DIAMETER/XML). \nModifiable when the server is inactive. \nA DIAMETER server accepts connections from DIAMETER and UA ADNs. \nA XML server only accepts connections from UA XML ADNs. \nDefault value: DIAMETER."
    ::= { ptDSCTransportServerEntry 7 }

ptDSCTransportServerSecurityParameterSet OBJECT-TYPE
    SYNTAX          DisplayString (SIZE(0..255))
    MAX-ACCESS      read-create
    STATUS          current
    DESCRIPTION     
            "Security Parameter Set associated with this Transport Server. \nSet to default for RFC3588 TLS. \nValid values: Existing Security Parameter Set. \nDefault value: default."
    ::= { ptDSCTransportServerEntry 8 }

ptDSCTransportServerRemoteIPValidation OBJECT-TYPE
    SYNTAX          INTEGER { disabled(0), enabled(1) }
    MAX-ACCESS      read-create
    STATUS          current
    DESCRIPTION     
            "Validate remote IP addresses of incoming connections (DISABLED/ENABLED). \nIf enabled, the resolved values of the Allowed IPs list must match the \nsource address(es) of received TCP or SCTP packets. If the validation \nfails the connection is closed. This value cannot be set to ENABLED if \nno Allowed IP exist. \nDefault value: DISABLED."
    ::= { ptDSCTransportServerEntry 9 }

ptDSCTransportServerDSCIndex OBJECT-TYPE
    SYNTAX          Integer32 (-2147483648..2147483647)
    MAX-ACCESS      not-accessible
    STATUS          current
    DESCRIPTION     
            "This is the index of the parent type for this object.
             This parent type is DSC."
    ::= { ptDSCTransportServerEntry 242 }

ptDSCTransportServerDSCNodesIndex OBJECT-TYPE
    SYNTAX          Integer32 (-2147483648..2147483647)
    MAX-ACCESS      not-accessible
    STATUS          current
    DESCRIPTION     
            "This is the index of the parent type for this object.
             This parent type is DSCNodes."
    ::= { ptDSCTransportServerEntry 243 }

ptDSCTransportServerDSCNodeIndex OBJECT-TYPE
    SYNTAX          Integer32 (-2147483648..2147483647)
    MAX-ACCESS      not-accessible
    STATUS          current
    DESCRIPTION     
            "This is the index of the parent type for this object.
             This parent type is DSCNode."
    ::= { ptDSCTransportServerEntry 244 }

ptDSCTransportServerTransportServersIndex OBJECT-TYPE
    SYNTAX          Integer32 (-2147483648..2147483647)
    MAX-ACCESS      not-accessible
    STATUS          current
    DESCRIPTION     
            "This is the index of the parent type for this object.
             This parent type is TransportServers."
    ::= { ptDSCTransportServerEntry 245 }

ptDSCTransportServerActions OBJECT-TYPE
    SYNTAX          INTEGER { activate(1), deactivate(2) }
    MAX-ACCESS      read-create
    STATUS          current
    DESCRIPTION     
            "The OID of all possible actions for this instance"
    ::= { ptDSCTransportServerEntry 252 }

ptDSCTransportServerParentOID OBJECT-TYPE
    SYNTAX          OBJECT IDENTIFIER
    MAX-ACCESS      read-create
    STATUS          current
    DESCRIPTION     
            "The OID of the parent object for this instance"
    ::= { ptDSCTransportServerEntry 253 }

ptDSCTransportServerRowStatus OBJECT-TYPE
    SYNTAX          RowStatus
    MAX-ACCESS      read-create
    STATUS          current
    DESCRIPTION     
            "The row status for the DSCTransportServer table"
    ::= { ptDSCTransportServerEntry 254 }

ptDSCTransportServerIndex OBJECT-TYPE
    SYNTAX          Integer32 (-2147483648..2147483647)
    MAX-ACCESS      not-accessible
    STATUS          current
    DESCRIPTION     
            "The row number for the DSCTransportServer table"
    ::= { ptDSCTransportServerEntry 255 }

ptDSCAllowedIP OBJECT IDENTIFIER
    ::= { ptDSCTransportServer 1854 }

ptDSCAllowedIPTable OBJECT-TYPE
    SYNTAX          SEQUENCE OF PtDSCAllowedIPEntry
    MAX-ACCESS      not-accessible
    STATUS          current
    DESCRIPTION     
            "No description supplied in the proxy config file."
    ::= { ptDSCAllowedIP 1 }

ptDSCAllowedIPEntry OBJECT-TYPE
    SYNTAX          PtDSCAllowedIPEntry
    MAX-ACCESS      not-accessible
    STATUS          current
    DESCRIPTION     
            "A sequence of DSCAllowedIP attributes."
    INDEX           { ptConnGroupIndex, ptDSCAllowedIPDSCIndex, 
                      ptDSCAllowedIPDSCNodesIndex, 
                      ptDSCAllowedIPDSCNodeIndex, 
                      ptDSCAllowedIPTransportServersIndex, 
                      ptDSCAllowedIPTransportServerIndex, 
                      ptDSCAllowedIPIndex }
    ::= { ptDSCAllowedIPTable 1 }

PtDSCAllowedIPEntry ::=
    SEQUENCE {
        ptDSCAllowedIPHost              DisplayString,
        ptDSCAllowedIPPort              INTEGER,
        ptDSCAllowedIPDSCIndex          Integer32,
        ptDSCAllowedIPDSCNodesIndex     Integer32,
        ptDSCAllowedIPDSCNodeIndex      Integer32,
        ptDSCAllowedIPTransportServersIndex   Integer32,
        ptDSCAllowedIPTransportServerIndex  Integer32,
        ptDSCAllowedIPParentOID         OBJECT IDENTIFIER,
        ptDSCAllowedIPRowStatus         RowStatus,
        ptDSCAllowedIPIndex             Integer32
    }

ptDSCAllowedIPHost OBJECT-TYPE
    SYNTAX          DisplayString (SIZE(0..255))
    MAX-ACCESS      read-create
    STATUS          current
    DESCRIPTION     
            "Host or IPv4 address or IPv6 address."
    ::= { ptDSCAllowedIPEntry 1 }

ptDSCAllowedIPPort OBJECT-TYPE
    SYNTAX          INTEGER { any(0) }
    MAX-ACCESS      read-create
    STATUS          current
    DESCRIPTION     
            "Remote Port value to accept connection from. \nThis value may be 0 which indicates that any port is accepted."
    ::= { ptDSCAllowedIPEntry 2 }

ptDSCAllowedIPDSCIndex OBJECT-TYPE
    SYNTAX          Integer32 (-2147483648..2147483647)
    MAX-ACCESS      not-accessible
    STATUS          current
    DESCRIPTION     
            "This is the index of the parent type for this object.
             This parent type is DSC."
    ::= { ptDSCAllowedIPEntry 242 }

ptDSCAllowedIPDSCNodesIndex OBJECT-TYPE
    SYNTAX          Integer32 (-2147483648..2147483647)
    MAX-ACCESS      not-accessible
    STATUS          current
    DESCRIPTION     
            "This is the index of the parent type for this object.
             This parent type is DSCNodes."
    ::= { ptDSCAllowedIPEntry 243 }

ptDSCAllowedIPDSCNodeIndex OBJECT-TYPE
    SYNTAX          Integer32 (-2147483648..2147483647)
    MAX-ACCESS      not-accessible
    STATUS          current
    DESCRIPTION     
            "This is the index of the parent type for this object.
             This parent type is DSCNode."
    ::= { ptDSCAllowedIPEntry 244 }

ptDSCAllowedIPTransportServersIndex OBJECT-TYPE
    SYNTAX          Integer32 (-2147483648..2147483647)
    MAX-ACCESS      not-accessible
    STATUS          current
    DESCRIPTION     
            "This is the index of the parent type for this object.
             This parent type is TransportServers."
    ::= { ptDSCAllowedIPEntry 245 }

ptDSCAllowedIPTransportServerIndex OBJECT-TYPE
    SYNTAX          Integer32 (-2147483648..2147483647)
    MAX-ACCESS      not-accessible
    STATUS          current
    DESCRIPTION     
            "This is the index of the parent type for this object.
             This parent type is TransportServer."
    ::= { ptDSCAllowedIPEntry 246 }

ptDSCAllowedIPParentOID OBJECT-TYPE
    SYNTAX          OBJECT IDENTIFIER
    MAX-ACCESS      read-create
    STATUS          current
    DESCRIPTION     
            "The OID of the parent object for this instance"
    ::= { ptDSCAllowedIPEntry 253 }

ptDSCAllowedIPRowStatus OBJECT-TYPE
    SYNTAX          RowStatus
    MAX-ACCESS      read-create
    STATUS          current
    DESCRIPTION     
            "The row status for the DSCAllowedIP table"
    ::= { ptDSCAllowedIPEntry 254 }

ptDSCAllowedIPIndex OBJECT-TYPE
    SYNTAX          Integer32 (-2147483648..2147483647)
    MAX-ACCESS      not-accessible
    STATUS          current
    DESCRIPTION     
            "The row number for the DSCAllowedIP table"
    ::= { ptDSCAllowedIPEntry 255 }

ptDSCServerPools OBJECT IDENTIFIER
    ::= { ptDSCDSCNode 1841 }

ptDSCServerPoolsTable OBJECT-TYPE
    SYNTAX          SEQUENCE OF PtDSCServerPoolsEntry
    MAX-ACCESS      not-accessible
    STATUS          current
    DESCRIPTION     
            "No description supplied in the proxy config file."
    ::= { ptDSCServerPools 1 }

ptDSCServerPoolsEntry OBJECT-TYPE
    SYNTAX          PtDSCServerPoolsEntry
    MAX-ACCESS      not-accessible
    STATUS          current
    DESCRIPTION     
            "A sequence of DSCServerPools attributes."
    INDEX           { ptConnGroupIndex, ptDSCServerPoolsDSCIndex, 
                      ptDSCServerPoolsDSCNodesIndex, 
                      ptDSCServerPoolsDSCNodeIndex, 
                      ptDSCServerPoolsIndex }
    ::= { ptDSCServerPoolsTable 1 }

PtDSCServerPoolsEntry ::=
    SEQUENCE {
        ptDSCServerPoolsDSCIndex        Integer32,
        ptDSCServerPoolsDSCNodesIndex   Integer32,
        ptDSCServerPoolsDSCNodeIndex    Integer32,
        ptDSCServerPoolsParentOID       OBJECT IDENTIFIER,
        ptDSCServerPoolsRowStatus       RowStatus,
        ptDSCServerPoolsIndex           Integer32
    }

ptDSCServerPoolsDSCIndex OBJECT-TYPE
    SYNTAX          Integer32 (-2147483648..2147483647)
    MAX-ACCESS      not-accessible
    STATUS          current
    DESCRIPTION     
            "This is the index of the parent type for this object.
             This parent type is DSC."
    ::= { ptDSCServerPoolsEntry 242 }

ptDSCServerPoolsDSCNodesIndex OBJECT-TYPE
    SYNTAX          Integer32 (-2147483648..2147483647)
    MAX-ACCESS      not-accessible
    STATUS          current
    DESCRIPTION     
            "This is the index of the parent type for this object.
             This parent type is DSCNodes."
    ::= { ptDSCServerPoolsEntry 243 }

ptDSCServerPoolsDSCNodeIndex OBJECT-TYPE
    SYNTAX          Integer32 (-2147483648..2147483647)
    MAX-ACCESS      not-accessible
    STATUS          current
    DESCRIPTION     
            "This is the index of the parent type for this object.
             This parent type is DSCNode."
    ::= { ptDSCServerPoolsEntry 244 }

ptDSCServerPoolsParentOID OBJECT-TYPE
    SYNTAX          OBJECT IDENTIFIER
    MAX-ACCESS      read-create
    STATUS          current
    DESCRIPTION     
            "The OID of the parent object for this instance"
    ::= { ptDSCServerPoolsEntry 253 }

ptDSCServerPoolsRowStatus OBJECT-TYPE
    SYNTAX          RowStatus
    MAX-ACCESS      read-create
    STATUS          current
    DESCRIPTION     
            "The row status for the DSCServerPools table"
    ::= { ptDSCServerPoolsEntry 254 }

ptDSCServerPoolsIndex OBJECT-TYPE
    SYNTAX          Integer32 (-2147483648..2147483647)
    MAX-ACCESS      not-accessible
    STATUS          current
    DESCRIPTION     
            "The row number for the DSCServerPools table"
    ::= { ptDSCServerPoolsEntry 255 }

ptDSCServerPool OBJECT IDENTIFIER
    ::= { ptDSCServerPools 1842 }

ptDSCServerPoolTable OBJECT-TYPE
    SYNTAX          SEQUENCE OF PtDSCServerPoolEntry
    MAX-ACCESS      not-accessible
    STATUS          current
    DESCRIPTION     
            "No description supplied in the proxy config file."
    ::= { ptDSCServerPool 1 }

ptDSCServerPoolEntry OBJECT-TYPE
    SYNTAX          PtDSCServerPoolEntry
    MAX-ACCESS      not-accessible
    STATUS          current
    DESCRIPTION     
            "A sequence of DSCServerPool attributes."
    INDEX           { ptConnGroupIndex, ptDSCServerPoolDSCIndex, 
                      ptDSCServerPoolDSCNodesIndex, 
                      ptDSCServerPoolDSCNodeIndex, 
                      ptDSCServerPoolServerPoolsIndex, 
                      ptDSCServerPoolIndex }
    ::= { ptDSCServerPoolTable 1 }

PtDSCServerPoolEntry ::=
    SEQUENCE {
        ptDSCServerPoolName             DisplayString,
        ptDSCServerPoolSessionBinding   INTEGER,
        ptDSCServerPoolRoutingTableName DisplayString,
        ptDSCServerPoolStatus           INTEGER,
        ptDSCServerPoolLoadBalancing    INTEGER,
        ptDSCServerPoolInternalID       Integer32,
        ptDSCServerPoolAVPAlias         DisplayString,
        ptDSCServerPoolDSCIndex         Integer32,
        ptDSCServerPoolDSCNodesIndex    Integer32,
        ptDSCServerPoolDSCNodeIndex     Integer32,
        ptDSCServerPoolServerPoolsIndex Integer32,
        ptDSCServerPoolActions          INTEGER,
        ptDSCServerPoolParentOID        OBJECT IDENTIFIER,
        ptDSCServerPoolRowStatus        RowStatus,
        ptDSCServerPoolIndex            Integer32
    }

ptDSCServerPoolName OBJECT-TYPE
    SYNTAX          DisplayString (SIZE(0..255))
    MAX-ACCESS      read-only
    STATUS          current
    DESCRIPTION     
            "Name to uniquely identify the Server Pool. \nThe name must be unique within the DSC Node. \nIt is recommended that the name be set to a short and unique value to facilitate logs and alarms correlation. \nValid values: alphanumeric characters, dashes, and underscores (maximum size of 32)."
    ::= { ptDSCServerPoolEntry 1 }

ptDSCServerPoolSessionBinding OBJECT-TYPE
    SYNTAX          INTEGER { disabled(0), session(1), pcrf(2) }
    MAX-ACCESS      read-create
    STATUS          current
    DESCRIPTION     
            "Session Binding (DISABLED/SESSION/PCRF). \nIf set to DISABLED, load balancing the chosen load balancing algorithm is applied. \nIf set to SESSION, bind is performed to the Diameter Session-Id AVP. \nIf set to PCRF, bind is performed to the EPC IP-CAN session. \nDefault value: DISABLED."
    ::= { ptDSCServerPoolEntry 2 }

ptDSCServerPoolRoutingTableName OBJECT-TYPE
    SYNTAX          DisplayString (SIZE(0..255))
    MAX-ACCESS      read-create
    STATUS          current
    DESCRIPTION     
            "Routing Table Name for post-lookup entry point. \nValid values: dsc_default or an existing Routing Table Name. \nDefault value: dsc_default."
    ::= { ptDSCServerPoolEntry 3 }

ptDSCServerPoolStatus OBJECT-TYPE
    SYNTAX          INTEGER { active(0), inactive(1) }
    MAX-ACCESS      read-only
    STATUS          current
    DESCRIPTION     
            "Server Pool State (INACTIVE/ACTIVE). \nActivate the Server Pool to enable this feature."
    ::= { ptDSCServerPoolEntry 4 }

ptDSCServerPoolLoadBalancing OBJECT-TYPE
    SYNTAX          INTEGER { roundRobinWeight(0), leastLoaded(1), 
                        roundRobinCost(2), hash(3) }
    MAX-ACCESS      read-create
    STATUS          current
    DESCRIPTION     
            "Load Balancing \nWhen Round Robin Cost is selected then the lowest cost record is chosen as the routing destination. \nIf more than one record has the same cost then messages are \nload shared in a round robin manner across the available destinations. \n Valid costs are values 1 to 99. \nWhen Round Robin Weight is selected, the weights represent the ratio of messages delivered to each destination. \nFor example: Candidate A has weight = 10, B = 20 and C = 5. \nIn a group of messages, the first 10 messages are sent to A, then the next 20 to B and the next 5 to C. The process is then restarted at A for the next messages. \n With Hash based the routing candidate is selected by hashing a defined AVP value in the message. \nWhen Least Loaded is selected, the weights indicate the relative message capacity of each server (in messages per second). \nDefault Value: ROUND ROBIN WEIGHT."
    ::= { ptDSCServerPoolEntry 5 }

ptDSCServerPoolInternalID OBJECT-TYPE
    SYNTAX          Integer32 (-2147483648..2147483647)
    MAX-ACCESS      read-only
    STATUS          current
    DESCRIPTION     
            "Server Pool internal ID. \nReserved for internal use."
    ::= { ptDSCServerPoolEntry 6 }

ptDSCServerPoolAVPAlias OBJECT-TYPE
    SYNTAX          DisplayString (SIZE(0..255))
    MAX-ACCESS      read-create
    STATUS          current
    DESCRIPTION     
            "The name of an AVP Alias. This AVP is used by the hashing algorithm to perform traffic load balancing. \nValid values: An AVP Alias which has been created in the DSC AVP Alias Definitions tables. If the AVP is not present in the message, then the hop-by-hop header value is used. \nDefault value: session-id AVP."
    ::= { ptDSCServerPoolEntry 7 }

ptDSCServerPoolDSCIndex OBJECT-TYPE
    SYNTAX          Integer32 (-2147483648..2147483647)
    MAX-ACCESS      not-accessible
    STATUS          current
    DESCRIPTION     
            "This is the index of the parent type for this object.
             This parent type is DSC."
    ::= { ptDSCServerPoolEntry 242 }

ptDSCServerPoolDSCNodesIndex OBJECT-TYPE
    SYNTAX          Integer32 (-2147483648..2147483647)
    MAX-ACCESS      not-accessible
    STATUS          current
    DESCRIPTION     
            "This is the index of the parent type for this object.
             This parent type is DSCNodes."
    ::= { ptDSCServerPoolEntry 243 }

ptDSCServerPoolDSCNodeIndex OBJECT-TYPE
    SYNTAX          Integer32 (-2147483648..2147483647)
    MAX-ACCESS      not-accessible
    STATUS          current
    DESCRIPTION     
            "This is the index of the parent type for this object.
             This parent type is DSCNode."
    ::= { ptDSCServerPoolEntry 244 }

ptDSCServerPoolServerPoolsIndex OBJECT-TYPE
    SYNTAX          Integer32 (-2147483648..2147483647)
    MAX-ACCESS      not-accessible
    STATUS          current
    DESCRIPTION     
            "This is the index of the parent type for this object.
             This parent type is ServerPools."
    ::= { ptDSCServerPoolEntry 245 }

ptDSCServerPoolActions OBJECT-TYPE
    SYNTAX          INTEGER { activate(1), deactivate(2) }
    MAX-ACCESS      read-create
    STATUS          current
    DESCRIPTION     
            "The OID of all possible actions for this instance"
    ::= { ptDSCServerPoolEntry 252 }

ptDSCServerPoolParentOID OBJECT-TYPE
    SYNTAX          OBJECT IDENTIFIER
    MAX-ACCESS      read-create
    STATUS          current
    DESCRIPTION     
            "The OID of the parent object for this instance"
    ::= { ptDSCServerPoolEntry 253 }

ptDSCServerPoolRowStatus OBJECT-TYPE
    SYNTAX          RowStatus
    MAX-ACCESS      read-create
    STATUS          current
    DESCRIPTION     
            "The row status for the DSCServerPool table"
    ::= { ptDSCServerPoolEntry 254 }

ptDSCServerPoolIndex OBJECT-TYPE
    SYNTAX          Integer32 (-2147483648..2147483647)
    MAX-ACCESS      not-accessible
    STATUS          current
    DESCRIPTION     
            "The row number for the DSCServerPool table"
    ::= { ptDSCServerPoolEntry 255 }

ptDSCMemberDiameterID OBJECT IDENTIFIER
    ::= { ptDSCServerPool 1843 }

ptDSCMemberDiameterIDTable OBJECT-TYPE
    SYNTAX          SEQUENCE OF PtDSCMemberDiameterIDEntry
    MAX-ACCESS      not-accessible
    STATUS          current
    DESCRIPTION     
            "No description supplied in the proxy config file."
    ::= { ptDSCMemberDiameterID 1 }

ptDSCMemberDiameterIDEntry OBJECT-TYPE
    SYNTAX          PtDSCMemberDiameterIDEntry
    MAX-ACCESS      not-accessible
    STATUS          current
    DESCRIPTION     
            "A sequence of DSCMemberDiameterID attributes."
    INDEX           { ptConnGroupIndex, ptDSCMemberDiameterIDDSCIndex, 
                      ptDSCMemberDiameterIDDSCNodesIndex, 
                      ptDSCMemberDiameterIDDSCNodeIndex, 
                      ptDSCMemberDiameterIDServerPoolsIndex, 
                      ptDSCMemberDiameterIDServerPoolIndex, 
                      ptDSCMemberDiameterIDIndex }
    ::= { ptDSCMemberDiameterIDTable 1 }

PtDSCMemberDiameterIDEntry ::=
    SEQUENCE {
        ptDSCMemberDiameterIDDiameterID DisplayString,
        ptDSCMemberDiameterIDWeight     Integer32,
        ptDSCMemberDiameterIDInternalID Integer32,
        ptDSCMemberDiameterIDCost       Integer32,
        ptDSCMemberDiameterIDDSCIndex   Integer32,
        ptDSCMemberDiameterIDDSCNodesIndex  Integer32,
        ptDSCMemberDiameterIDDSCNodeIndex Integer32,
        ptDSCMemberDiameterIDServerPoolsIndex     Integer32,
        ptDSCMemberDiameterIDServerPoolIndex    Integer32,
        ptDSCMemberDiameterIDParentOID  OBJECT IDENTIFIER,
        ptDSCMemberDiameterIDRowStatus  RowStatus,
        ptDSCMemberDiameterIDIndex      Integer32
    }

ptDSCMemberDiameterIDDiameterID OBJECT-TYPE
    SYNTAX          DisplayString (SIZE(0..255))
    MAX-ACCESS      read-only
    STATUS          current
    DESCRIPTION     
            "Diameter ID associated to the Server Pool. \nValid values: FQDN format."
    ::= { ptDSCMemberDiameterIDEntry 1 }

ptDSCMemberDiameterIDWeight OBJECT-TYPE
    SYNTAX          Integer32
    MAX-ACCESS      read-create
    STATUS          current
    DESCRIPTION     
            "Weight of the Diameter ID (0 to 400000). \nThe Diameter ID Weight is used to indicate the relative message capacity of this Diameter ID when load sharing on the server pool. \nValid values: 0 to 100 (ROUND ROBIN) \n 0 to 4000000 (LEAST LOADED). \nDefault value: 10 (ADN) and 0 (non-ADN) (ROUND ROBIN) \n 2000 (ADN) and 0 (non-ADN) (LEAST LOADED)"
    ::= { ptDSCMemberDiameterIDEntry 2 }

ptDSCMemberDiameterIDInternalID OBJECT-TYPE
    SYNTAX          Integer32 (-2147483648..2147483647)
    MAX-ACCESS      read-only
    STATUS          current
    DESCRIPTION     
            "Member Diameter ID internal ID. \nReserved for internal use."
    ::= { ptDSCMemberDiameterIDEntry 3 }

ptDSCMemberDiameterIDCost OBJECT-TYPE
    SYNTAX          Integer32 (1..99)
    MAX-ACCESS      read-create
    STATUS          current
    DESCRIPTION     
            "Cost of the result record (1 to 99). \nLowest available record is used for routing. \nIf more than one record have the lowest available cost, loadsharing is performed."
    ::= { ptDSCMemberDiameterIDEntry 4 }

ptDSCMemberDiameterIDDSCIndex OBJECT-TYPE
    SYNTAX          Integer32 (-2147483648..2147483647)
    MAX-ACCESS      not-accessible
    STATUS          current
    DESCRIPTION     
            "This is the index of the parent type for this object.
             This parent type is DSC."
    ::= { ptDSCMemberDiameterIDEntry 242 }

ptDSCMemberDiameterIDDSCNodesIndex OBJECT-TYPE
    SYNTAX          Integer32 (-2147483648..2147483647)
    MAX-ACCESS      not-accessible
    STATUS          current
    DESCRIPTION     
            "This is the index of the parent type for this object.
             This parent type is DSCNodes."
    ::= { ptDSCMemberDiameterIDEntry 243 }

ptDSCMemberDiameterIDDSCNodeIndex OBJECT-TYPE
    SYNTAX          Integer32 (-2147483648..2147483647)
    MAX-ACCESS      not-accessible
    STATUS          current
    DESCRIPTION     
            "This is the index of the parent type for this object.
             This parent type is DSCNode."
    ::= { ptDSCMemberDiameterIDEntry 244 }

ptDSCMemberDiameterIDServerPoolsIndex OBJECT-TYPE
    SYNTAX          Integer32 (-2147483648..2147483647)
    MAX-ACCESS      not-accessible
    STATUS          current
    DESCRIPTION     
            "This is the index of the parent type for this object.
             This parent type is ServerPools."
    ::= { ptDSCMemberDiameterIDEntry 245 }

ptDSCMemberDiameterIDServerPoolIndex OBJECT-TYPE
    SYNTAX          Integer32 (-2147483648..2147483647)
    MAX-ACCESS      not-accessible
    STATUS          current
    DESCRIPTION     
            "This is the index of the parent type for this object.
             This parent type is ServerPool."
    ::= { ptDSCMemberDiameterIDEntry 246 }

ptDSCMemberDiameterIDParentOID OBJECT-TYPE
    SYNTAX          OBJECT IDENTIFIER
    MAX-ACCESS      read-create
    STATUS          current
    DESCRIPTION     
            "The OID of the parent object for this instance"
    ::= { ptDSCMemberDiameterIDEntry 253 }

ptDSCMemberDiameterIDRowStatus OBJECT-TYPE
    SYNTAX          RowStatus
    MAX-ACCESS      read-create
    STATUS          current
    DESCRIPTION     
            "The row status for the DSCMemberDiameterID table"
    ::= { ptDSCMemberDiameterIDEntry 254 }

ptDSCMemberDiameterIDIndex OBJECT-TYPE
    SYNTAX          Integer32 (-2147483648..2147483647)
    MAX-ACCESS      not-accessible
    STATUS          current
    DESCRIPTION     
            "The row number for the DSCMemberDiameterID table"
    ::= { ptDSCMemberDiameterIDEntry 255 }

ptDSCPoolApplicationID OBJECT IDENTIFIER
    ::= { ptDSCServerPool 1844 }

ptDSCPoolApplicationIDTable OBJECT-TYPE
    SYNTAX          SEQUENCE OF PtDSCPoolApplicationIDEntry
    MAX-ACCESS      not-accessible
    STATUS          current
    DESCRIPTION     
            "No description supplied in the proxy config file."
    ::= { ptDSCPoolApplicationID 1 }

ptDSCPoolApplicationIDEntry OBJECT-TYPE
    SYNTAX          PtDSCPoolApplicationIDEntry
    MAX-ACCESS      not-accessible
    STATUS          current
    DESCRIPTION     
            "A sequence of DSCPoolApplicationID attributes."
    INDEX           { ptConnGroupIndex, ptDSCPoolApplicationIDDSCIndex, 
                      ptDSCPoolApplicationIDDSCNodesIndex, 
                      ptDSCPoolApplicationIDDSCNodeIndex, 
                      ptDSCPoolApplicationIDServerPoolsIndex, 
                      ptDSCPoolApplicationIDServerPoolIndex, 
                      ptDSCPoolApplicationIDIndex }
    ::= { ptDSCPoolApplicationIDTable 1 }

PtDSCPoolApplicationIDEntry ::=
    SEQUENCE {
        ptDSCPoolApplicationIDApplicationID   DisplayString,
        ptDSCPoolApplicationIDInternalID Integer32,
        ptDSCPoolApplicationIDDSCIndex  Integer32,
        ptDSCPoolApplicationIDDSCNodesIndex   Integer32,
        ptDSCPoolApplicationIDDSCNodeIndex  Integer32,
        ptDSCPoolApplicationIDServerPoolsIndex      Integer32,
        ptDSCPoolApplicationIDServerPoolIndex     Integer32,
        ptDSCPoolApplicationIDParentOID OBJECT IDENTIFIER,
        ptDSCPoolApplicationIDRowStatus RowStatus,
        ptDSCPoolApplicationIDIndex     Integer32
    }

ptDSCPoolApplicationIDApplicationID OBJECT-TYPE
    SYNTAX          DisplayString (SIZE(0..255))
    MAX-ACCESS      read-only
    STATUS          current
    DESCRIPTION     
            "Application ID associated to the Server Pool. \nValid values: Existing Application ID Definition."
    ::= { ptDSCPoolApplicationIDEntry 1 }

ptDSCPoolApplicationIDInternalID OBJECT-TYPE
    SYNTAX          Integer32 (-2147483648..2147483647)
    MAX-ACCESS      read-only
    STATUS          current
    DESCRIPTION     
            "Pool Application internal ID. \nReserved for internal use."
    ::= { ptDSCPoolApplicationIDEntry 2 }

ptDSCPoolApplicationIDDSCIndex OBJECT-TYPE
    SYNTAX          Integer32 (-2147483648..2147483647)
    MAX-ACCESS      not-accessible
    STATUS          current
    DESCRIPTION     
            "This is the index of the parent type for this object.
             This parent type is DSC."
    ::= { ptDSCPoolApplicationIDEntry 242 }

ptDSCPoolApplicationIDDSCNodesIndex OBJECT-TYPE
    SYNTAX          Integer32 (-2147483648..2147483647)
    MAX-ACCESS      not-accessible
    STATUS          current
    DESCRIPTION     
            "This is the index of the parent type for this object.
             This parent type is DSCNodes."
    ::= { ptDSCPoolApplicationIDEntry 243 }

ptDSCPoolApplicationIDDSCNodeIndex OBJECT-TYPE
    SYNTAX          Integer32 (-2147483648..2147483647)
    MAX-ACCESS      not-accessible
    STATUS          current
    DESCRIPTION     
            "This is the index of the parent type for this object.
             This parent type is DSCNode."
    ::= { ptDSCPoolApplicationIDEntry 244 }

ptDSCPoolApplicationIDServerPoolsIndex OBJECT-TYPE
    SYNTAX          Integer32 (-2147483648..2147483647)
    MAX-ACCESS      not-accessible
    STATUS          current
    DESCRIPTION     
            "This is the index of the parent type for this object.
             This parent type is ServerPools."
    ::= { ptDSCPoolApplicationIDEntry 245 }

ptDSCPoolApplicationIDServerPoolIndex OBJECT-TYPE
    SYNTAX          Integer32 (-2147483648..2147483647)
    MAX-ACCESS      not-accessible
    STATUS          current
    DESCRIPTION     
            "This is the index of the parent type for this object.
             This parent type is ServerPool."
    ::= { ptDSCPoolApplicationIDEntry 246 }

ptDSCPoolApplicationIDParentOID OBJECT-TYPE
    SYNTAX          OBJECT IDENTIFIER
    MAX-ACCESS      read-create
    STATUS          current
    DESCRIPTION     
            "The OID of the parent object for this instance"
    ::= { ptDSCPoolApplicationIDEntry 253 }

ptDSCPoolApplicationIDRowStatus OBJECT-TYPE
    SYNTAX          RowStatus
    MAX-ACCESS      read-create
    STATUS          current
    DESCRIPTION     
            "The row status for the DSCPoolApplicationID table"
    ::= { ptDSCPoolApplicationIDEntry 254 }

ptDSCPoolApplicationIDIndex OBJECT-TYPE
    SYNTAX          Integer32 (-2147483648..2147483647)
    MAX-ACCESS      not-accessible
    STATUS          current
    DESCRIPTION     
            "The row number for the DSCPoolApplicationID table"
    ::= { ptDSCPoolApplicationIDEntry 255 }

ptDSCDSCRoutingTables OBJECT IDENTIFIER
    ::= { ptDSCDSC 1803 }

ptDSCDSCRoutingTablesTable OBJECT-TYPE
    SYNTAX          SEQUENCE OF PtDSCDSCRoutingTablesEntry
    MAX-ACCESS      not-accessible
    STATUS          current
    DESCRIPTION     
            "No description supplied in the proxy config file."
    ::= { ptDSCDSCRoutingTables 1 }

ptDSCDSCRoutingTablesEntry OBJECT-TYPE
    SYNTAX          PtDSCDSCRoutingTablesEntry
    MAX-ACCESS      not-accessible
    STATUS          current
    DESCRIPTION     
            "A sequence of DSCDSCRoutingTables attributes."
    INDEX           { ptConnGroupIndex, ptDSCDSCRoutingTablesDSCIndex, 
                      ptDSCDSCRoutingTablesIndex }
    ::= { ptDSCDSCRoutingTablesTable 1 }

PtDSCDSCRoutingTablesEntry ::=
    SEQUENCE {
        ptDSCDSCRoutingTablesDSCIndex   Integer32,
        ptDSCDSCRoutingTablesParentOID  OBJECT IDENTIFIER,
        ptDSCDSCRoutingTablesRowStatus  RowStatus,
        ptDSCDSCRoutingTablesIndex      Integer32
    }

ptDSCDSCRoutingTablesDSCIndex OBJECT-TYPE
    SYNTAX          Integer32 (-2147483648..2147483647)
    MAX-ACCESS      not-accessible
    STATUS          current
    DESCRIPTION     
            "This is the index of the parent type for this object.
             This parent type is DSC."
    ::= { ptDSCDSCRoutingTablesEntry 242 }

ptDSCDSCRoutingTablesParentOID OBJECT-TYPE
    SYNTAX          OBJECT IDENTIFIER
    MAX-ACCESS      read-create
    STATUS          current
    DESCRIPTION     
            "The OID of the parent object for this instance"
    ::= { ptDSCDSCRoutingTablesEntry 253 }

ptDSCDSCRoutingTablesRowStatus OBJECT-TYPE
    SYNTAX          RowStatus
    MAX-ACCESS      read-create
    STATUS          current
    DESCRIPTION     
            "The row status for the DSCDSCRoutingTables table"
    ::= { ptDSCDSCRoutingTablesEntry 254 }

ptDSCDSCRoutingTablesIndex OBJECT-TYPE
    SYNTAX          Integer32 (-2147483648..2147483647)
    MAX-ACCESS      not-accessible
    STATUS          current
    DESCRIPTION     
            "The row number for the DSCDSCRoutingTables table"
    ::= { ptDSCDSCRoutingTablesEntry 255 }

ptDSCIncomingADNRoutingTable OBJECT IDENTIFIER
    ::= { ptDSCDSCRoutingTables 1810 }

ptDSCIncomingADNRoutingTableTable OBJECT-TYPE
    SYNTAX          SEQUENCE OF PtDSCIncomingADNRoutingTableEntry
    MAX-ACCESS      not-accessible
    STATUS          current
    DESCRIPTION     
            "No description supplied in the proxy config file."
    ::= { ptDSCIncomingADNRoutingTable 1 }

ptDSCIncomingADNRoutingTableEntry OBJECT-TYPE
    SYNTAX          PtDSCIncomingADNRoutingTableEntry
    MAX-ACCESS      not-accessible
    STATUS          current
    DESCRIPTION     
            "A sequence of DSCIncomingADNRoutingTable attributes."
    INDEX           { ptConnGroupIndex, 
                      ptDSCIncomingADNRoutingTableDSCIndex, 
                      ptDSCIncomingADNRoutingTableDSCRoutingTablesIndex, 
                      ptDSCIncomingADNRoutingTableIndex }
    ::= { ptDSCIncomingADNRoutingTableTable 1 }

PtDSCIncomingADNRoutingTableEntry ::=
    SEQUENCE {
        ptDSCIncomingADNRoutingTableTableName     DisplayString,
        ptDSCIncomingADNRoutingTableADNSearchType         INTEGER,
        ptDSCIncomingADNRoutingTableDSCIndex    Integer32,
        ptDSCIncomingADNRoutingTableDSCRoutingTablesIndex                 Integer32,
        ptDSCIncomingADNRoutingTableParentOID     OBJECT IDENTIFIER,
        ptDSCIncomingADNRoutingTableRowStatus     RowStatus,
        ptDSCIncomingADNRoutingTableIndex Integer32
    }

ptDSCIncomingADNRoutingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCIncomingADNRoutingTableEntry 1 }

ptDSCIncomingADNRoutingTableADNSearchType OBJECT-TYPE
    SYNTAX          INTEGER { exactMatch(1), longestFromRight(2) }
    MAX-ACCESS      read-only
    STATUS          current
    DESCRIPTION     
            "Incoming ADN Search Type (EXACT MATCH/LONGEST FROM RIGHT) \nExact match must result in existing ADNs in the Incoming ADN records. \nDefault value: EXACT MATCH (reference only)."
    ::= { ptDSCIncomingADNRoutingTableEntry 2 }

ptDSCIncomingADNRoutingTableDSCIndex OBJECT-TYPE
    SYNTAX          Integer32 (-2147483648..2147483647)
    MAX-ACCESS      not-accessible
    STATUS          current
    DESCRIPTION     
            "This is the index of the parent type for this object.
             This parent type is DSC."
    ::= { ptDSCIncomingADNRoutingTableEntry 242 }

ptDSCIncomingADNRoutingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCIncomingADNRoutingTableEntry 243 }

ptDSCIncomingADNRoutingTableParentOID OBJECT-TYPE
    SYNTAX          OBJECT IDENTIFIER
    MAX-ACCESS      read-create
    STATUS          current
    DESCRIPTION     
            "The OID of the parent object for this instance"
    ::= { ptDSCIncomingADNRoutingTableEntry 253 }

ptDSCIncomingADNRoutingTableRowStatus OBJECT-TYPE
    SYNTAX          RowStatus
    MAX-ACCESS      read-create
    STATUS          current
    DESCRIPTION     
            "The row status for the DSCIncomingADNRoutingTable table"
    ::= { ptDSCIncomingADNRoutingTableEntry 254 }

ptDSCIncomingADNRoutingTableIndex OBJECT-TYPE
    SYNTAX          Integer32 (-2147483648..2147483647)
    MAX-ACCESS      not-accessible
    STATUS          current
    DESCRIPTION     
            "The row number for the DSCIncomingADNRoutingTable table"
    ::= { ptDSCIncomingADNRoutingTableEntry 255 }

ptDSCIncomingADNRoutingRecord OBJECT IDENTIFIER
    ::= { ptDSCIncomingADNRoutingTable 1811 }

ptDSCIncomingADNRoutingRecordTable OBJECT-TYPE
    SYNTAX          SEQUENCE OF PtDSCIncomingADNRoutingRecordEntry
    MAX-ACCESS      not-accessible
    STATUS          current
    DESCRIPTION     
            "No description supplied in the proxy config file."
    ::= { ptDSCIncomingADNRoutingRecord 1 }

ptDSCIncomingADNRoutingRecordEntry OBJECT-TYPE
    SYNTAX          PtDSCIncomingADNRoutingRecordEntry
    MAX-ACCESS      not-accessible
    STATUS          current
    DESCRIPTION     
            "A sequence of DSCIncomingADNRoutingRecord attributes."
    INDEX           { ptConnGroupIndex, 
                      ptDSCIncomingADNRoutingRecordDSCIndex, 
                      ptDSCIncomingADNRoutingRecordDSCRoutingTablesIndex, 
                      ptDSCIncomingADNRoutingRecordIncomingADNRoutingTableIndex, 
                      ptDSCIncomingADNRoutingRecordIndex }
    ::= { ptDSCIncomingADNRoutingRecordTable 1 }

PtDSCIncomingADNRoutingRecordEntry ::=
    SEQUENCE {
        ptDSCIncomingADNRoutingRecordRecordType       INTEGER,
        ptDSCIncomingADNRoutingRecordAdjacentDiameterNode                 DisplayString,
        ptDSCIncomingADNRoutingRecordNextTableName          DisplayString,
        ptDSCIncomingADNRoutingRecordModificationTableName                  DisplayString,
        ptDSCIncomingADNRoutingRecordDSCNodeID      INTEGER,
        ptDSCIncomingADNRoutingRecordDSCNodeName        DisplayString,
        ptDSCIncomingADNRoutingRecordDSCIndex     Integer32,
        ptDSCIncomingADNRoutingRecordDSCRoutingTablesIndex                  Integer32,
        ptDSCIncomingADNRoutingRecordIncomingADNRoutingTableIndex                         Integer32,
        ptDSCIncomingADNRoutingRecordParentOID      OBJECT IDENTIFIER,
        ptDSCIncomingADNRoutingRecordRowStatus      RowStatus,
        ptDSCIncomingADNRoutingRecordIndex  Integer32
    }

ptDSCIncomingADNRoutingRecordRecordType OBJECT-TYPE
    SYNTAX          INTEGER { default(1), value(1000) }
    MAX-ACCESS      read-only
    STATUS          current
    DESCRIPTION     
            "Record Type (DEFAULT/VALUE) \nA single non-deleteable DEFAULT record handles routing if no VALUE match is found. \nDefault value: VALUE."
    ::= { ptDSCIncomingADNRoutingRecordEntry 1 }

ptDSCIncomingADNRoutingRecordAdjacentDiameterNode OBJECT-TYPE
    SYNTAX          DisplayString (SIZE(0..255))
    MAX-ACCESS      read-only
    STATUS          current
    DESCRIPTION     
            "Associated Adjacent Diameter Node. \nValid values: empty string (DEFAULT record type) \n FQDN format and empty string (VALUE record type and LONGEST FROM RIGHT ADN search type) \n existing ADN name (VALUE record type and EXACT MATCH ADN search type)."
    ::= { ptDSCIncomingADNRoutingRecordEntry 2 }

ptDSCIncomingADNRoutingRecordNextTableName OBJECT-TYPE
    SYNTAX          DisplayString (SIZE(0..255))
    MAX-ACCESS      read-create
    STATUS          current
    DESCRIPTION     
            "Next routing table, result table, default routing, or error handling to route the message. \nDepending on the required routing decision, set to: \n1) The name of the next routing table to continue routing. \n2) The name of the result table to send the message. \n3) dsc_default to apply default routing. \n4) dsc_error to return Result-Code 3002, UNABLE_TO_DELIVER. \n5) dsc_error<error code> to return Result-Code of <error code>. \n6) dsc_error<vendor id>_<error code> to return Experimental-Result with Vendor-Id of <vendor id> and Experimental-Result-Code of <error code>. \n7) dsc_discard to drop the request. \n \nOptional text may be added after a variant of dsc_error, separated by a space, to indicated a desired Error-Message. \nThe next table cannot be a modification table."
    ::= { ptDSCIncomingADNRoutingRecordEntry 3 }

ptDSCIncomingADNRoutingRecordModificationTableName OBJECT-TYPE
    SYNTAX          DisplayString (SIZE(0..255))
    MAX-ACCESS      read-create
    STATUS          current
    DESCRIPTION     
            "Associated optional Modification Table to be applied to the message. \nValid values: empty string and existing Modification Table name. \nDefault value: empty string."
    ::= { ptDSCIncomingADNRoutingRecordEntry 4 }

ptDSCIncomingADNRoutingRecordDSCNodeID OBJECT-TYPE
    SYNTAX          INTEGER { any(0) }
    MAX-ACCESS      read-only
    STATUS          current
    DESCRIPTION     
            "Internal ID of the associated DSC Node that owns the ADN. \nObsolete as of release 14.3. \nValid values: ANY (DEFAULT record type) \n Existing DSC Node ID (VALUE record type)."
    ::= { ptDSCIncomingADNRoutingRecordEntry 5 }

ptDSCIncomingADNRoutingRecordDSCNodeName OBJECT-TYPE
    SYNTAX          DisplayString (SIZE(0..255))
    MAX-ACCESS      read-only
    STATUS          current
    DESCRIPTION     
            "DSC Node Name of the associated DSC Node which owns the ADN. \nValid values: ANY (DEFAULT record type) \n Existing DSC Node Name (VALUE record type)."
    ::= { ptDSCIncomingADNRoutingRecordEntry 6 }

ptDSCIncomingADNRoutingRecordDSCIndex OBJECT-TYPE
    SYNTAX          Integer32 (-2147483648..2147483647)
    MAX-ACCESS      not-accessible
    STATUS          current
    DESCRIPTION     
            "This is the index of the parent type for this object.
             This parent type is DSC."
    ::= { ptDSCIncomingADNRoutingRecordEntry 242 }

ptDSCIncomingADNRoutingRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCIncomingADNRoutingRecordEntry 243 }

ptDSCIncomingADNRoutingRecordIncomingADNRoutingTableIndex OBJECT-TYPE
    SYNTAX          Integer32 (-2147483648..2147483647)
    MAX-ACCESS      not-accessible
    STATUS          current
    DESCRIPTION     
            "This is the index of the parent type for this object.
             This parent type is IncomingADNRoutingTable."
    ::= { ptDSCIncomingADNRoutingRecordEntry 244 }

ptDSCIncomingADNRoutingRecordParentOID OBJECT-TYPE
    SYNTAX          OBJECT IDENTIFIER
    MAX-ACCESS      read-create
    STATUS          current
    DESCRIPTION     
            "The OID of the parent object for this instance"
    ::= { ptDSCIncomingADNRoutingRecordEntry 253 }

ptDSCIncomingADNRoutingRecordRowStatus OBJECT-TYPE
    SYNTAX          RowStatus
    MAX-ACCESS      read-create
    STATUS          current
    DESCRIPTION     
            "The row status for the DSCIncomingADNRoutingRecord table"
    ::= { ptDSCIncomingADNRoutingRecordEntry 254 }

ptDSCIncomingADNRoutingRecordIndex OBJECT-TYPE
    SYNTAX          Integer32 (-2147483648..2147483647)
    MAX-ACCESS      not-accessible
    STATUS          current
    DESCRIPTION     
            "The row number for the DSCIncomingADNRoutingRecord table"
    ::= { ptDSCIncomingADNRoutingRecordEntry 255 }

ptDSCApplicationIDRoutingTable OBJECT IDENTIFIER
    ::= { ptDSCDSCRoutingTables 1812 }

ptDSCApplicationIDRoutingTableTable OBJECT-TYPE
    SYNTAX          SEQUENCE OF PtDSCApplicationIDRoutingTableEntry
    MAX-ACCESS      not-accessible
    STATUS          current
    DESCRIPTION     
            "No description supplied in the proxy config file."
    ::= { ptDSCApplicationIDRoutingTable 1 }

ptDSCApplicationIDRoutingTableEntry OBJECT-TYPE
    SYNTAX          PtDSCApplicationIDRoutingTableEntry
    MAX-ACCESS      not-accessible
    STATUS          current
    DESCRIPTION     
            "A sequence of DSCApplicationIDRoutingTable attributes."
    INDEX           { ptConnGroupIndex, 
                      ptDSCApplicationIDRoutingTableDSCIndex, 
                      ptDSCApplicationIDRoutingTableDSCRoutingTablesIndex, 
                      ptDSCApplicationIDRoutingTableIndex }
    ::= { ptDSCApplicationIDRoutingTableTable 1 }

PtDSCApplicationIDRoutingTableEntry ::=
    SEQUENCE {
        ptDSCApplicationIDRoutingTableTableName       DisplayString,
        ptDSCApplicationIDRoutingTableDSCIndex      Integer32,
        ptDSCApplicationIDRoutingTableDSCRoutingTablesIndex                   Integer32,
        ptDSCApplicationIDRoutingTableParentOID       OBJECT IDENTIFIER,
        ptDSCApplicationIDRoutingTableRowStatus       RowStatus,
        ptDSCApplicationIDRoutingTableIndex   Integer32
    }

ptDSCApplicationIDRoutingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCApplicationIDRoutingTableEntry 1 }

ptDSCApplicationIDRoutingTableDSCIndex OBJECT-TYPE
    SYNTAX          Integer32 (-2147483648..2147483647)
    MAX-ACCESS      not-accessible
    STATUS          current
    DESCRIPTION     
            "This is the index of the parent type for this object.
             This parent type is DSC."
    ::= { ptDSCApplicationIDRoutingTableEntry 242 }

ptDSCApplicationIDRoutingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCApplicationIDRoutingTableEntry 243 }

ptDSCApplicationIDRoutingTableParentOID OBJECT-TYPE
    SYNTAX          OBJECT IDENTIFIER
    MAX-ACCESS      read-create
    STATUS          current
    DESCRIPTION     
            "The OID of the parent object for this instance"
    ::= { ptDSCApplicationIDRoutingTableEntry 253 }

ptDSCApplicationIDRoutingTableRowStatus OBJECT-TYPE
    SYNTAX          RowStatus
    MAX-ACCESS      read-create
    STATUS          current
    DESCRIPTION     
            "The row status for the DSCApplicationIDRoutingTable table"
    ::= { ptDSCApplicationIDRoutingTableEntry 254 }

ptDSCApplicationIDRoutingTableIndex OBJECT-TYPE
    SYNTAX          Integer32 (-2147483648..2147483647)
    MAX-ACCESS      not-accessible
    STATUS          current
    DESCRIPTION     
            "The row number for the DSCApplicationIDRoutingTable table"
    ::= { ptDSCApplicationIDRoutingTableEntry 255 }

ptDSCApplicationIDRoutingRecord OBJECT IDENTIFIER
    ::= { ptDSCApplicationIDRoutingTable 1813 }

ptDSCApplicationIDRoutingRecordTable OBJECT-TYPE
    SYNTAX          SEQUENCE OF PtDSCApplicationIDRoutingRecordEntry
    MAX-ACCESS      not-accessible
    STATUS          current
    DESCRIPTION     
            "No description supplied in the proxy config file."
    ::= { ptDSCApplicationIDRoutingRecord 1 }

ptDSCApplicationIDRoutingRecordEntry OBJECT-TYPE
    SYNTAX          PtDSCApplicationIDRoutingRecordEntry
    MAX-ACCESS      not-accessible
    STATUS          current
    DESCRIPTION     
            "A sequence of DSCApplicationIDRoutingRecord attributes."
    INDEX           { ptConnGroupIndex, 
                      ptDSCApplicationIDRoutingRecordDSCIndex, 
                      ptDSCApplicationIDRoutingRecordDSCRoutingTablesIndex, 
                      ptDSCApplicationIDRoutingRecordApplicationIDRoutingTableIndex, 
                      ptDSCApplicationIDRoutingRecordIndex }
    ::= { ptDSCApplicationIDRoutingRecordTable 1 }

PtDSCApplicationIDRoutingRecordEntry ::=
    SEQUENCE {
        ptDSCApplicationIDRoutingRecordRecordType         INTEGER,
        ptDSCApplicationIDRoutingRecordApplicationID            DisplayString,
        ptDSCApplicationIDRoutingRecordNextTableName            DisplayString,
        ptDSCApplicationIDRoutingRecordModificationTableName                    DisplayString,
        ptDSCApplicationIDRoutingRecordDSCIndex       Integer32,
        ptDSCApplicationIDRoutingRecordDSCRoutingTablesIndex                    Integer32,
        ptDSCApplicationIDRoutingRecordApplicationIDRoutingTableIndex                             Integer32,
        ptDSCApplicationIDRoutingRecordParentOID        OBJECT IDENTIFIER,
        ptDSCApplicationIDRoutingRecordRowStatus        RowStatus,
        ptDSCApplicationIDRoutingRecordIndex    Integer32
    }

ptDSCApplicationIDRoutingRecordRecordType OBJECT-TYPE
    SYNTAX          INTEGER { default(1), value(1000) }
    MAX-ACCESS      read-only
    STATUS          current
    DESCRIPTION     
            "Record Type (DEFAULT/VALUE) \nA single non-deleteable DEFAULT record handles routing if no VALUE match is found. \nDefault value: VALUE."
    ::= { ptDSCApplicationIDRoutingRecordEntry 1 }

ptDSCApplicationIDRoutingRecordApplicationID OBJECT-TYPE
    SYNTAX          DisplayString (SIZE(0..255))
    MAX-ACCESS      read-only
    STATUS          current
    DESCRIPTION     
            "Associated Application ID Definition name. \nValid values: existing Application ID definition name."
    ::= { ptDSCApplicationIDRoutingRecordEntry 2 }

ptDSCApplicationIDRoutingRecordNextTableName OBJECT-TYPE
    SYNTAX          DisplayString (SIZE(0..255))
    MAX-ACCESS      read-create
    STATUS          current
    DESCRIPTION     
            "Next routing table, result table, default routing, or error handling to route the message. \nDepending on the required routing decision, set to: \n1) The name of the next routing table to continue routing. \n2) The name of the result table to send the message. \n3) dsc_default to apply default routing. \n4) dsc_error to return Result-Code 3002, UNABLE_TO_DELIVER. \n5) dsc_error<error code> to return Result-Code of <error code>. \n6) dsc_error<vendor id>_<error code> to return Experimental-Result with Vendor-Id of <vendor id> and Experimental-Result-Code of <error code>. \n7) dsc_discard to drop the request. \n \nOptional text may be added after a variant of dsc_error, separated by a space, to indicated a desired Error-Message. \nThe next table cannot be a modification table."
    ::= { ptDSCApplicationIDRoutingRecordEntry 3 }

ptDSCApplicationIDRoutingRecordModificationTableName OBJECT-TYPE
    SYNTAX          DisplayString (SIZE(0..255))
    MAX-ACCESS      read-create
    STATUS          current
    DESCRIPTION     
            "Associated optional Modification Table to be applied to the message. \nValid values: empty string and existing Modification Table name. \nDefault value: empty string."
    ::= { ptDSCApplicationIDRoutingRecordEntry 4 }

ptDSCApplicationIDRoutingRecordDSCIndex OBJECT-TYPE
    SYNTAX          Integer32 (-2147483648..2147483647)
    MAX-ACCESS      not-accessible
    STATUS          current
    DESCRIPTION     
            "This is the index of the parent type for this object.
             This parent type is DSC."
    ::= { ptDSCApplicationIDRoutingRecordEntry 242 }

ptDSCApplicationIDRoutingRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCApplicationIDRoutingRecordEntry 243 }

ptDSCApplicationIDRoutingRecordApplicationIDRoutingTableIndex OBJECT-TYPE
    SYNTAX          Integer32 (-2147483648..2147483647)
    MAX-ACCESS      not-accessible
    STATUS          current
    DESCRIPTION     
            "This is the index of the parent type for this object.
             This parent type is ApplicationIDRoutingTable."
    ::= { ptDSCApplicationIDRoutingRecordEntry 244 }

ptDSCApplicationIDRoutingRecordParentOID OBJECT-TYPE
    SYNTAX          OBJECT IDENTIFIER
    MAX-ACCESS      read-create
    STATUS          current
    DESCRIPTION     
            "The OID of the parent object for this instance"
    ::= { ptDSCApplicationIDRoutingRecordEntry 253 }

ptDSCApplicationIDRoutingRecordRowStatus OBJECT-TYPE
    SYNTAX          RowStatus
    MAX-ACCESS      read-create
    STATUS          current
    DESCRIPTION     
            "The row status for the DSCApplicationIDRoutingRecord table"
    ::= { ptDSCApplicationIDRoutingRecordEntry 254 }

ptDSCApplicationIDRoutingRecordIndex OBJECT-TYPE
    SYNTAX          Integer32 (-2147483648..2147483647)
    MAX-ACCESS      not-accessible
    STATUS          current
    DESCRIPTION     
            "The row number for the DSCApplicationIDRoutingRecord table"
    ::= { ptDSCApplicationIDRoutingRecordEntry 255 }

ptDSCAVPRoutingTable OBJECT IDENTIFIER
    ::= { ptDSCDSCRoutingTables 1814 }

ptDSCAVPRoutingTableTable OBJECT-TYPE
    SYNTAX          SEQUENCE OF PtDSCAVPRoutingTableEntry
    MAX-ACCESS      not-accessible
    STATUS          current
    DESCRIPTION     
            "No description supplied in the proxy config file."
    ::= { ptDSCAVPRoutingTable 1 }

ptDSCAVPRoutingTableEntry OBJECT-TYPE
    SYNTAX          PtDSCAVPRoutingTableEntry
    MAX-ACCESS      not-accessible
    STATUS          current
    DESCRIPTION     
            "A sequence of DSCAVPRoutingTable attributes."
    INDEX           { ptConnGroupIndex, ptDSCAVPRoutingTableDSCIndex, 
                      ptDSCAVPRoutingTableDSCRoutingTablesIndex, 
                      ptDSCAVPRoutingTableIndex }
    ::= { ptDSCAVPRoutingTableTable 1 }

PtDSCAVPRoutingTableEntry ::=
    SEQUENCE {
        ptDSCAVPRoutingTableTableName   DisplayString,
        ptDSCAVPRoutingTableAVPAlias    DisplayString,
        ptDSCAVPRoutingTableSearchType  INTEGER,
        ptDSCAVPRoutingTablePreProcessing DisplayString,
        ptDSCAVPRoutingTableDSCIndex    Integer32,
        ptDSCAVPRoutingTableDSCRoutingTablesIndex         Integer32,
        ptDSCAVPRoutingTableParentOID   OBJECT IDENTIFIER,
        ptDSCAVPRoutingTableRowStatus   RowStatus,
        ptDSCAVPRoutingTableIndex       Integer32
    }

ptDSCAVPRoutingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCAVPRoutingTableEntry 1 }

ptDSCAVPRoutingTableAVPAlias OBJECT-TYPE
    SYNTAX          DisplayString (SIZE(0..255))
    MAX-ACCESS      read-only
    STATUS          current
    DESCRIPTION     
            "Associated AVP Alias Definition name. \nValid values: existing AVP Alias Definition name."
    ::= { ptDSCAVPRoutingTableEntry 2 }

ptDSCAVPRoutingTableSearchType OBJECT-TYPE
    SYNTAX          INTEGER { exactMatch(1), longestFromRight(2), 
                        longestFromLeft(3) }
    MAX-ACCESS      read-only
    STATUS          current
    DESCRIPTION     
            "Search Type (EXACT MATCH/LONGEST FROM LEFT/LONGEST FROM RIGHT) \nLongest search types are only applicable on string based AVP types. Thus AVP types such as Unsigned32, Enumerated, Integer32, and Unsigned64 are restricted to EXACT MATCH searches. \Default value: EXACT MATCH (reference only)."
    ::= { ptDSCAVPRoutingTableEntry 3 }

ptDSCAVPRoutingTablePreProcessing OBJECT-TYPE
    SYNTAX          DisplayString (SIZE(0..255))
    MAX-ACCESS      read-create
    STATUS          current
    DESCRIPTION     
            "Pre-Processing - Currently not supported."
    ::= { ptDSCAVPRoutingTableEntry 4 }

ptDSCAVPRoutingTableDSCIndex OBJECT-TYPE
    SYNTAX          Integer32 (-2147483648..2147483647)
    MAX-ACCESS      not-accessible
    STATUS          current
    DESCRIPTION     
            "This is the index of the parent type for this object.
             This parent type is DSC."
    ::= { ptDSCAVPRoutingTableEntry 242 }

ptDSCAVPRoutingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCAVPRoutingTableEntry 243 }

ptDSCAVPRoutingTableParentOID OBJECT-TYPE
    SYNTAX          OBJECT IDENTIFIER
    MAX-ACCESS      read-create
    STATUS          current
    DESCRIPTION     
            "The OID of the parent object for this instance"
    ::= { ptDSCAVPRoutingTableEntry 253 }

ptDSCAVPRoutingTableRowStatus OBJECT-TYPE
    SYNTAX          RowStatus
    MAX-ACCESS      read-create
    STATUS          current
    DESCRIPTION     
            "The row status for the DSCAVPRoutingTable table"
    ::= { ptDSCAVPRoutingTableEntry 254 }

ptDSCAVPRoutingTableIndex OBJECT-TYPE
    SYNTAX          Integer32 (-2147483648..2147483647)
    MAX-ACCESS      not-accessible
    STATUS          current
    DESCRIPTION     
            "The row number for the DSCAVPRoutingTable table"
    ::= { ptDSCAVPRoutingTableEntry 255 }

ptDSCAVPRoutingRecord OBJECT IDENTIFIER
    ::= { ptDSCAVPRoutingTable 1815 }

ptDSCAVPRoutingRecordTable OBJECT-TYPE
    SYNTAX          SEQUENCE OF PtDSCAVPRoutingRecordEntry
    MAX-ACCESS      not-accessible
    STATUS          current
    DESCRIPTION     
            "No description supplied in the proxy config file."
    ::= { ptDSCAVPRoutingRecord 1 }

ptDSCAVPRoutingRecordEntry OBJECT-TYPE
    SYNTAX          PtDSCAVPRoutingRecordEntry
    MAX-ACCESS      not-accessible
    STATUS          current
    DESCRIPTION     
            "A sequence of DSCAVPRoutingRecord attributes."
    INDEX           { ptConnGroupIndex, ptDSCAVPRoutingRecordDSCIndex, 
                      ptDSCAVPRoutingRecordDSCRoutingTablesIndex, 
                      ptDSCAVPRoutingRecordAVPRoutingTableIndex, 
                      ptDSCAVPRoutingRecordIndex }
    ::= { ptDSCAVPRoutingRecordTable 1 }

PtDSCAVPRoutingRecordEntry ::=
    SEQUENCE {
        ptDSCAVPRoutingRecordRecordType INTEGER,
        ptDSCAVPRoutingRecordAVPValue   DisplayString,
        ptDSCAVPRoutingRecordNextTableName  DisplayString,
        ptDSCAVPRoutingRecordModificationTableName          DisplayString,
        ptDSCAVPRoutingRecordDSCIndex   Integer32,
        ptDSCAVPRoutingRecordDSCRoutingTablesIndex          Integer32,
        ptDSCAVPRoutingRecordAVPRoutingTableIndex         Integer32,
        ptDSCAVPRoutingRecordParentOID  OBJECT IDENTIFIER,
        ptDSCAVPRoutingRecordRowStatus  RowStatus,
        ptDSCAVPRoutingRecordIndex      Integer32
    }

ptDSCAVPRoutingRecordRecordType OBJECT-TYPE
    SYNTAX          INTEGER { default(1), noAvp(2), valueString(1000), 
                        valueInt(2000), valueHexString(3000), 
                        valueAdn(4000), valueRealm(5000) }
    MAX-ACCESS      read-only
    STATUS          current
    DESCRIPTION     
            "Record Type (DEFAULT/NO AVP/VALUE) \nA single non-deleteable NO AVP record handles routing if the AVP is not found in the message. \nA single non-deleteable DEFAULT record handles routing if the AVP is found in the message but no VALUE match is found. \nA VALUE record handles routing if the AVP Value attribute matches the corresponding AVP from the message based on the appropriate format (STRING, HEX STRING, INT, ADN, REALM). \nA VALUE STRING record must have an AVP Value in the form of a printable ASCII string. \nA VALUE HEX STRING record must have an AVP Value in the form of space separated hexadecimal pairs. \nA VALUE INT record must have an AVP Value that represents a decimal encoded integer. \nA VALUE ADN record must have an AVP Value that represents an existing ADN Name that is different from the default name (AVP Node Diameter ID attribute). \nA VALUE REALM record must have an AVP Value that represents an existing Realm Alias. \nDefault value: VALUE."
    ::= { ptDSCAVPRoutingRecordEntry 1 }

ptDSCAVPRoutingRecordAVPValue OBJECT-TYPE
    SYNTAX          DisplayString (SIZE(0..255))
    MAX-ACCESS      read-only
    STATUS          current
    DESCRIPTION     
            "Associated AVP value for the table associated AVP Alias. \nValid values: based on the associated AVP Alias AVP Definition AVP Type attribute."
    ::= { ptDSCAVPRoutingRecordEntry 2 }

ptDSCAVPRoutingRecordNextTableName OBJECT-TYPE
    SYNTAX          DisplayString (SIZE(0..255))
    MAX-ACCESS      read-create
    STATUS          current
    DESCRIPTION     
            "Next routing table, result table, default routing, or error handling to route the message. \nDepending on the required routing decision, set to: \n1) The name of the next routing table to continue routing. \n2) The name of the result table to send the message. \n3) dsc_default to apply default routing. \n4) dsc_error to return Result-Code 3002, UNABLE_TO_DELIVER. \n5) dsc_error<error code> to return Result-Code of <error code>. \n6) dsc_error<vendor id>_<error code> to return Experimental-Result with Vendor-Id of <vendor id> and Experimental-Result-Code of <error code>. \n7) dsc_discard to drop the request. \n \nOptional text may be added after a variant of dsc_error, separated by a space, to indicated a desired Error-Message. \nThe next table cannot be a modification table."
    ::= { ptDSCAVPRoutingRecordEntry 3 }

ptDSCAVPRoutingRecordModificationTableName OBJECT-TYPE
    SYNTAX          DisplayString (SIZE(0..255))
    MAX-ACCESS      read-create
    STATUS          current
    DESCRIPTION     
            "Associated optional Modification Table to be applied to the message. \nValid values: empty string and existing Modification Table name. \nDefault value: empty string."
    ::= { ptDSCAVPRoutingRecordEntry 4 }

ptDSCAVPRoutingRecordDSCIndex OBJECT-TYPE
    SYNTAX          Integer32 (-2147483648..2147483647)
    MAX-ACCESS      not-accessible
    STATUS          current
    DESCRIPTION     
            "This is the index of the parent type for this object.
             This parent type is DSC."
    ::= { ptDSCAVPRoutingRecordEntry 242 }

ptDSCAVPRoutingRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCAVPRoutingRecordEntry 243 }

ptDSCAVPRoutingRecordAVPRoutingTableIndex OBJECT-TYPE
    SYNTAX          Integer32 (-2147483648..2147483647)
    MAX-ACCESS      not-accessible
    STATUS          current
    DESCRIPTION     
            "This is the index of the parent type for this object.
             This parent type is AVPRoutingTable."
    ::= { ptDSCAVPRoutingRecordEntry 244 }

ptDSCAVPRoutingRecordParentOID OBJECT-TYPE
    SYNTAX          OBJECT IDENTIFIER
    MAX-ACCESS      read-create
    STATUS          current
    DESCRIPTION     
            "The OID of the parent object for this instance"
    ::= { ptDSCAVPRoutingRecordEntry 253 }

ptDSCAVPRoutingRecordRowStatus OBJECT-TYPE
    SYNTAX          RowStatus
    MAX-ACCESS      read-create
    STATUS          current
    DESCRIPTION     
            "The row status for the DSCAVPRoutingRecord table"
    ::= { ptDSCAVPRoutingRecordEntry 254 }

ptDSCAVPRoutingRecordIndex OBJECT-TYPE
    SYNTAX          Integer32 (-2147483648..2147483647)
    MAX-ACCESS      not-accessible
    STATUS          current
    DESCRIPTION     
            "The row number for the DSCAVPRoutingRecord table"
    ::= { ptDSCAVPRoutingRecordEntry 255 }

ptDSCResultTable OBJECT IDENTIFIER
    ::= { ptDSCDSCRoutingTables 1816 }

ptDSCResultTableTable OBJECT-TYPE
    SYNTAX          SEQUENCE OF PtDSCResultTableEntry
    MAX-ACCESS      not-accessible
    STATUS          current
    DESCRIPTION     
            "No description supplied in the proxy config file."
    ::= { ptDSCResultTable 1 }

ptDSCResultTableEntry OBJECT-TYPE
    SYNTAX          PtDSCResultTableEntry
    MAX-ACCESS      not-accessible
    STATUS          current
    DESCRIPTION     
            "A sequence of DSCResultTable attributes."
    INDEX           { ptConnGroupIndex, ptDSCResultTableDSCIndex, 
                      ptDSCResultTableDSCRoutingTablesIndex, 
                      ptDSCResultTableIndex }
    ::= { ptDSCResultTableTable 1 }

PtDSCResultTableEntry ::=
    SEQUENCE {
        ptDSCResultTableTableName       DisplayString,
        ptDSCResultTableDSCNodeID       INTEGER,
        ptDSCResultTableDSCNodeName     DisplayString,
        ptDSCResultTableLoadBalancing   INTEGER,
        ptDSCResultTableAVPAlias        DisplayString,
        ptDSCResultTableDSCIndex        Integer32,
        ptDSCResultTableDSCRoutingTablesIndex     Integer32,
        ptDSCResultTableParentOID       OBJECT IDENTIFIER,
        ptDSCResultTableRowStatus       RowStatus,
        ptDSCResultTableIndex           Integer32
    }

ptDSCResultTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCResultTableEntry 1 }

ptDSCResultTableDSCNodeID OBJECT-TYPE
    SYNTAX          INTEGER { any(0) }
    MAX-ACCESS      read-only
    STATUS          current
    DESCRIPTION     
            "Associated DSC Node Internal ID. \nObsolete as of release 14.3. \nValid values: existing DSC Node Internal ID."
    ::= { ptDSCResultTableEntry 2 }

ptDSCResultTableDSCNodeName OBJECT-TYPE
    SYNTAX          DisplayString (SIZE(0..255))
    MAX-ACCESS      read-only
    STATUS          current
    DESCRIPTION     
            "Associated DSC Node name. \nValid values: existing DSC Node name."
    ::= { ptDSCResultTableEntry 3 }

ptDSCResultTableLoadBalancing OBJECT-TYPE
    SYNTAX          INTEGER { roundRobinWeight(0), leastLoaded(1), 
                        roundRobinCost(2), hash(3) }
    MAX-ACCESS      read-create
    STATUS          current
    DESCRIPTION     
            "Load Balancing \nWhen Round Robin Cost is selected then the lowest cost record is chosen as the routing destination. \nIf more than one record has the same cost then messages are \nload shared in a round robin manner across the available destinations. \n Valid costs are values 1 to 99. \nWhen Round Robin Weight is selected, the weights represent the ratio of messages delivered to each destination. \nFor example: Candidate A has weight = 10, B = 20 and C = 5. \nIn a group of messages, the first 10 messages are sent to A, then the next 20 to B and the next 5 to C. The process is then restarted at A for the next messages. \n With Hash based the routing candidate is selected by hashing a defined AVP value in the message. \nWhen Least Loaded is selected, the weights indicate the relative message capacity of each server (in messages per second). \nDefault Value: ROUND ROBIN WEIGHT."
    ::= { ptDSCResultTableEntry 4 }

ptDSCResultTableAVPAlias OBJECT-TYPE
    SYNTAX          DisplayString (SIZE(0..255))
    MAX-ACCESS      read-create
    STATUS          current
    DESCRIPTION     
            "The name of an AVP Alias. This AVP is used by the hashing algorithm to perform traffic load balancing. \nValid values: Must be an AVP Alias which has been created in the DSC AVP Alias Definitions tables. If the AVP is not present in the message, then the hop-by-hop header value is used."
    ::= { ptDSCResultTableEntry 5 }

ptDSCResultTableDSCIndex OBJECT-TYPE
    SYNTAX          Integer32 (-2147483648..2147483647)
    MAX-ACCESS      not-accessible
    STATUS          current
    DESCRIPTION     
            "This is the index of the parent type for this object.
             This parent type is DSC."
    ::= { ptDSCResultTableEntry 242 }

ptDSCResultTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCResultTableEntry 243 }

ptDSCResultTableParentOID OBJECT-TYPE
    SYNTAX          OBJECT IDENTIFIER
    MAX-ACCESS      read-create
    STATUS          current
    DESCRIPTION     
            "The OID of the parent object for this instance"
    ::= { ptDSCResultTableEntry 253 }

ptDSCResultTableRowStatus OBJECT-TYPE
    SYNTAX          RowStatus
    MAX-ACCESS      read-create
    STATUS          current
    DESCRIPTION     
            "The row status for the DSCResultTable table"
    ::= { ptDSCResultTableEntry 254 }

ptDSCResultTableIndex OBJECT-TYPE
    SYNTAX          Integer32 (-2147483648..2147483647)
    MAX-ACCESS      not-accessible
    STATUS          current
    DESCRIPTION     
            "The row number for the DSCResultTable table"
    ::= { ptDSCResultTableEntry 255 }

ptDSCResultRecord OBJECT IDENTIFIER
    ::= { ptDSCResultTable 1817 }

ptDSCResultRecordTable OBJECT-TYPE
    SYNTAX          SEQUENCE OF PtDSCResultRecordEntry
    MAX-ACCESS      not-accessible
    STATUS          current
    DESCRIPTION     
            "No description supplied in the proxy config file."
    ::= { ptDSCResultRecord 1 }

ptDSCResultRecordEntry OBJECT-TYPE
    SYNTAX          PtDSCResultRecordEntry
    MAX-ACCESS      not-accessible
    STATUS          current
    DESCRIPTION     
            "A sequence of DSCResultRecord attributes."
    INDEX           { ptConnGroupIndex, ptDSCResultRecordDSCIndex, 
                      ptDSCResultRecordDSCRoutingTablesIndex, 
                      ptDSCResultRecordResultTableIndex, 
                      ptDSCResultRecordIndex }
    ::= { ptDSCResultRecordTable 1 }

PtDSCResultRecordEntry ::=
    SEQUENCE {
        ptDSCResultRecordRecordType     INTEGER,
        ptDSCResultRecordCost           Integer32,
        ptDSCResultRecordRecordValue    DisplayString,
        ptDSCResultRecordWeight         Integer32,
        ptDSCResultRecordDSCIndex       Integer32,
        ptDSCResultRecordDSCRoutingTablesIndex      Integer32,
        ptDSCResultRecordResultTableIndex Integer32,
        ptDSCResultRecordParentOID      OBJECT IDENTIFIER,
        ptDSCResultRecordRowStatus      RowStatus,
        ptDSCResultRecordIndex          Integer32
    }

ptDSCResultRecordRecordType OBJECT-TYPE
    SYNTAX          INTEGER { relay(0), redirect(1), realmRedirect(2) }
    MAX-ACCESS      read-only
    STATUS          current
    DESCRIPTION     
            "Record Type (RELAY/REDIRECT/REALM_REDIRECT). \nRELAY: The message is forwarded (relayed) to the ADN represented by Record Value. \nREDIRECT: An answer message is returned to the originator instructing it to try the peer given in Record Value. \nREALM_REDIRECT: An answer message is returned to the originator instructing it to try the realm given in Record Value. \nDefault value: RELAY (reference only)."
    ::= { ptDSCResultRecordEntry 1 }

ptDSCResultRecordCost OBJECT-TYPE
    SYNTAX          Integer32 (1..99)
    MAX-ACCESS      read-create
    STATUS          current
    DESCRIPTION     
            "Cost of the result record (1 to 99). \nLowest available record is used for routing. \nIf more than one record have the lowest available cost, loadsharing is performed."
    ::= { ptDSCResultRecordEntry 2 }

ptDSCResultRecordRecordValue OBJECT-TYPE
    SYNTAX          DisplayString (SIZE(0..255))
    MAX-ACCESS      read-create
    STATUS          current
    DESCRIPTION     
            "Record Value representing an ADN for RELAY, URI for REDIRECT and Realm Definition for REALM_REDIRECT type. \n \nFor RELAY records, if a FQDN Diameter ID is specified, the value will be replaced by the associated ADN name. \nValid values: existing ADN Diameter ID (FQDN format) or ADN name (RELAY). \n \n URI format (REDIRECT). \nExamples: URI format \n NO Transport security URI format - \n aaa://FQDN [port] [transport] [protocol] \n aaa://host.example.com:1813;transport=tcp;protocol=diameter \n Transport security URI format - \n aaas://FQDN [port] [transport] [protocol] \n aaas://host.example.com:1813;transport=tcp;protocol=diameter \n \nFor REALM_REDIRECT records, the realm record value must be the Alias of an existing Realm Definition. "
    ::= { ptDSCResultRecordEntry 3 }

ptDSCResultRecordWeight OBJECT-TYPE
    SYNTAX          Integer32
    MAX-ACCESS      read-create
    STATUS          current
    DESCRIPTION     
            "Weight of the Diameter ID (0 to 400000). \nThe Diameter ID Weight is used to indicate the relative message capacity of this Diameter ID when load sharing on the server pool. \nValid values: 0 to 100 (ROUND ROBIN) \n 0 to 4000000 (LEAST LOADED). \nDefault value: 10 (ADN) and 0 (non-ADN) (ROUND ROBIN) \n 2000 (ADN) and 0 (non-ADN) (LEAST LOADED)"
    ::= { ptDSCResultRecordEntry 4 }

ptDSCResultRecordDSCIndex OBJECT-TYPE
    SYNTAX          Integer32 (-2147483648..2147483647)
    MAX-ACCESS      not-accessible
    STATUS          current
    DESCRIPTION     
            "This is the index of the parent type for this object.
             This parent type is DSC."
    ::= { ptDSCResultRecordEntry 242 }

ptDSCResultRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCResultRecordEntry 243 }

ptDSCResultRecordResultTableIndex OBJECT-TYPE
    SYNTAX          Integer32 (-2147483648..2147483647)
    MAX-ACCESS      not-accessible
    STATUS          current
    DESCRIPTION     
            "This is the index of the parent type for this object.
             This parent type is ResultTable."
    ::= { ptDSCResultRecordEntry 244 }

ptDSCResultRecordParentOID OBJECT-TYPE
    SYNTAX          OBJECT IDENTIFIER
    MAX-ACCESS      read-create
    STATUS          current
    DESCRIPTION     
            "The OID of the parent object for this instance"
    ::= { ptDSCResultRecordEntry 253 }

ptDSCResultRecordRowStatus OBJECT-TYPE
    SYNTAX          RowStatus
    MAX-ACCESS      read-create
    STATUS          current
    DESCRIPTION     
            "The row status for the DSCResultRecord table"
    ::= { ptDSCResultRecordEntry 254 }

ptDSCResultRecordIndex OBJECT-TYPE
    SYNTAX          Integer32 (-2147483648..2147483647)
    MAX-ACCESS      not-accessible
    STATUS          current
    DESCRIPTION     
            "The row number for the DSCResultRecord table"
    ::= { ptDSCResultRecordEntry 255 }

ptDSCModificationTable OBJECT IDENTIFIER
    ::= { ptDSCDSCRoutingTables 1830 }

ptDSCModificationTableTable OBJECT-TYPE
    SYNTAX          SEQUENCE OF PtDSCModificationTableEntry
    MAX-ACCESS      not-accessible
    STATUS          current
    DESCRIPTION     
            "No description supplied in the proxy config file."
    ::= { ptDSCModificationTable 1 }

ptDSCModificationTableEntry OBJECT-TYPE
    SYNTAX          PtDSCModificationTableEntry
    MAX-ACCESS      not-accessible
    STATUS          current
    DESCRIPTION     
            "A sequence of DSCModificationTable attributes."
    INDEX           { ptConnGroupIndex, ptDSCModificationTableDSCIndex, 
                      ptDSCModificationTableDSCRoutingTablesIndex, 
                      ptDSCModificationTableIndex }
    ::= { ptDSCModificationTableTable 1 }

PtDSCModificationTableEntry ::=
    SEQUENCE {
        ptDSCModificationTableTableName DisplayString,
        ptDSCModificationTableDSCIndex  Integer32,
        ptDSCModificationTableDSCRoutingTablesIndex           Integer32,
        ptDSCModificationTableParentOID OBJECT IDENTIFIER,
        ptDSCModificationTableRowStatus RowStatus,
        ptDSCModificationTableIndex     Integer32
    }

ptDSCModificationTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCModificationTableEntry 1 }

ptDSCModificationTableDSCIndex OBJECT-TYPE
    SYNTAX          Integer32 (-2147483648..2147483647)
    MAX-ACCESS      not-accessible
    STATUS          current
    DESCRIPTION     
            "This is the index of the parent type for this object.
             This parent type is DSC."
    ::= { ptDSCModificationTableEntry 242 }

ptDSCModificationTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCModificationTableEntry 243 }

ptDSCModificationTableParentOID OBJECT-TYPE
    SYNTAX          OBJECT IDENTIFIER
    MAX-ACCESS      read-create
    STATUS          current
    DESCRIPTION     
            "The OID of the parent object for this instance"
    ::= { ptDSCModificationTableEntry 253 }

ptDSCModificationTableRowStatus OBJECT-TYPE
    SYNTAX          RowStatus
    MAX-ACCESS      read-create
    STATUS          current
    DESCRIPTION     
            "The row status for the DSCModificationTable table"
    ::= { ptDSCModificationTableEntry 254 }

ptDSCModificationTableIndex OBJECT-TYPE
    SYNTAX          Integer32 (-2147483648..2147483647)
    MAX-ACCESS      not-accessible
    STATUS          current
    DESCRIPTION     
            "The row number for the DSCModificationTable table"
    ::= { ptDSCModificationTableEntry 255 }

ptDSCModificationRecord OBJECT IDENTIFIER
    ::= { ptDSCModificationTable 1831 }

ptDSCModificationRecordTable OBJECT-TYPE
    SYNTAX          SEQUENCE OF PtDSCModificationRecordEntry
    MAX-ACCESS      not-accessible
    STATUS          current
    DESCRIPTION     
            "No description supplied in the proxy config file."
    ::= { ptDSCModificationRecord 1 }

ptDSCModificationRecordEntry OBJECT-TYPE
    SYNTAX          PtDSCModificationRecordEntry
    MAX-ACCESS      not-accessible
    STATUS          current
    DESCRIPTION     
            "A sequence of DSCModificationRecord attributes."
    INDEX           { ptConnGroupIndex, ptDSCModificationRecordDSCIndex, 
                      ptDSCModificationRecordDSCRoutingTablesIndex, 
                      ptDSCModificationRecordModificationTableIndex, 
                      ptDSCModificationRecordIndex }
    ::= { ptDSCModificationRecordTable 1 }

PtDSCModificationRecordEntry ::=
    SEQUENCE {
        ptDSCModificationRecordOrder    Integer32,
        ptDSCModificationRecordCommand  DisplayString,
        ptDSCModificationRecordDSCIndex Integer32,
        ptDSCModificationRecordDSCRoutingTablesIndex            Integer32,
        ptDSCModificationRecordModificationTableIndex             Integer32,
        ptDSCModificationRecordParentOID OBJECT IDENTIFIER,
        ptDSCModificationRecordRowStatus RowStatus,
        ptDSCModificationRecordIndex    Integer32
    }

ptDSCModificationRecordOrder OBJECT-TYPE
    SYNTAX          Integer32
    MAX-ACCESS      read-create
    STATUS          current
    DESCRIPTION     
            "Modification order for the message (1 to 100). \nRules with lower order are applied first. \nOrder must be unique on a per table basis."
    ::= { ptDSCModificationRecordEntry 1 }

ptDSCModificationRecordCommand OBJECT-TYPE
    SYNTAX          DisplayString (SIZE(0..255))
    MAX-ACCESS      read-create
    STATUS          current
    DESCRIPTION     
            "Modification command for the message applied in order. \nSyntax for the command is defined in the DSC provisioning guide. \nSupported commands include: \n append-avp <avpXML> \n count <statsName> <columnNumber> \n ingress-filtering \n mod-avp-value bitwise and <avpAlias> <0x mask> [offset] \n mod-avp-value bitwise or <avpAlias> <0x mask> [offset] \n mod-avp-value byte-replace <avpAlias> <0x value> [offset] \n mod-avp-value replace <avpAlias> <string> \n mod-avp-value delete left <avpAlias> <octetCount> \n mod-avp-value delete right <avpAlias> <octetCount> \n mod-avp-value insert left <avpAlias> <string> \n mod-avp-value insert right <avpAlias> <string> \n mod-avp-flag <avpAlias> assign M|P|<0x bits> \n mod-avp-flag <avpAlias> clear M|P|<0x bits> \n mod-avp-flag <avpAlias> set M|P|<0x bits> \n mod-message-flag assign P|E|T|<0x bits> \n mod-message-flag clear P|E|T|<0x bits> \n mod-message-flag set P|E|T|<0x bits> \n realm-accounting \n receive-realm-redirect-indications DISABLED \n receive-realm-redirect-indications PASSTHROUGH \n receive-realm-redirect-indications RFC7075 \n remove-avp <avpAlias> \n replace-avp <avpAlias> <avpXML> \n set-answer-rt <routingTableName> \n set-importance <importance> \n use-rate-limiter <rateLimiter> \n trace \n rta on|off \n replace-dest-realm-from-imsi <AVPAlias> [prefix=epc] [suffix=3gppnetwork.org] \n replace-dest-realm-from-imsi <AVPAlias> <empty> [suffix=3gppnetwork.org] \n replace-dest-realm-from-imsi-if <AVPAlias> <Destination-Realm> [prefix=epc] [suffix=3gppnetwork.org] \n replace-dest-realm-from-imsi-if <AVPAlias> <Destination-Realm> <empty> [suffix=3gppnetwork.org] \n \nExamples: \n ingress-filtering \n mod-message-flag set P \n append-avp <avp avp-name='Origin-Host' value='sonus.net'/> \n trace"
    ::= { ptDSCModificationRecordEntry 2 }

ptDSCModificationRecordDSCIndex OBJECT-TYPE
    SYNTAX          Integer32 (-2147483648..2147483647)
    MAX-ACCESS      not-accessible
    STATUS          current
    DESCRIPTION     
            "This is the index of the parent type for this object.
             This parent type is DSC."
    ::= { ptDSCModificationRecordEntry 242 }

ptDSCModificationRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCModificationRecordEntry 243 }

ptDSCModificationRecordModificationTableIndex OBJECT-TYPE
    SYNTAX          Integer32 (-2147483648..2147483647)
    MAX-ACCESS      not-accessible
    STATUS          current
    DESCRIPTION     
            "This is the index of the parent type for this object.
             This parent type is ModificationTable."
    ::= { ptDSCModificationRecordEntry 244 }

ptDSCModificationRecordParentOID OBJECT-TYPE
    SYNTAX          OBJECT IDENTIFIER
    MAX-ACCESS      read-create
    STATUS          current
    DESCRIPTION     
            "The OID of the parent object for this instance"
    ::= { ptDSCModificationRecordEntry 253 }

ptDSCModificationRecordRowStatus OBJECT-TYPE
    SYNTAX          RowStatus
    MAX-ACCESS      read-create
    STATUS          current
    DESCRIPTION     
            "The row status for the DSCModificationRecord table"
    ::= { ptDSCModificationRecordEntry 254 }

ptDSCModificationRecordIndex OBJECT-TYPE
    SYNTAX          Integer32 (-2147483648..2147483647)
    MAX-ACCESS      not-accessible
    STATUS          current
    DESCRIPTION     
            "The row number for the DSCModificationRecord table"
    ::= { ptDSCModificationRecordEntry 255 }

ptDSCCommandCodeRoutingTable OBJECT IDENTIFIER
    ::= { ptDSCDSCRoutingTables 1836 }

ptDSCCommandCodeRoutingTableTable OBJECT-TYPE
    SYNTAX          SEQUENCE OF PtDSCCommandCodeRoutingTableEntry
    MAX-ACCESS      not-accessible
    STATUS          current
    DESCRIPTION     
            "No description supplied in the proxy config file."
    ::= { ptDSCCommandCodeRoutingTable 1 }

ptDSCCommandCodeRoutingTableEntry OBJECT-TYPE
    SYNTAX          PtDSCCommandCodeRoutingTableEntry
    MAX-ACCESS      not-accessible
    STATUS          current
    DESCRIPTION     
            "A sequence of DSCCommandCodeRoutingTable attributes."
    INDEX           { ptConnGroupIndex, 
                      ptDSCCommandCodeRoutingTableDSCIndex, 
                      ptDSCCommandCodeRoutingTableDSCRoutingTablesIndex, 
                      ptDSCCommandCodeRoutingTableIndex }
    ::= { ptDSCCommandCodeRoutingTableTable 1 }

PtDSCCommandCodeRoutingTableEntry ::=
    SEQUENCE {
        ptDSCCommandCodeRoutingTableTableName     DisplayString,
        ptDSCCommandCodeRoutingTableDSCIndex    Integer32,
        ptDSCCommandCodeRoutingTableDSCRoutingTablesIndex                 Integer32,
        ptDSCCommandCodeRoutingTableParentOID     OBJECT IDENTIFIER,
        ptDSCCommandCodeRoutingTableRowStatus     RowStatus,
        ptDSCCommandCodeRoutingTableIndex Integer32
    }

ptDSCCommandCodeRoutingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCCommandCodeRoutingTableEntry 1 }

ptDSCCommandCodeRoutingTableDSCIndex OBJECT-TYPE
    SYNTAX          Integer32 (-2147483648..2147483647)
    MAX-ACCESS      not-accessible
    STATUS          current
    DESCRIPTION     
            "This is the index of the parent type for this object.
             This parent type is DSC."
    ::= { ptDSCCommandCodeRoutingTableEntry 242 }

ptDSCCommandCodeRoutingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCCommandCodeRoutingTableEntry 243 }

ptDSCCommandCodeRoutingTableParentOID OBJECT-TYPE
    SYNTAX          OBJECT IDENTIFIER
    MAX-ACCESS      read-create
    STATUS          current
    DESCRIPTION     
            "The OID of the parent object for this instance"
    ::= { ptDSCCommandCodeRoutingTableEntry 253 }

ptDSCCommandCodeRoutingTableRowStatus OBJECT-TYPE
    SYNTAX          RowStatus
    MAX-ACCESS      read-create
    STATUS          current
    DESCRIPTION     
            "The row status for the DSCCommandCodeRoutingTable table"
    ::= { ptDSCCommandCodeRoutingTableEntry 254 }

ptDSCCommandCodeRoutingTableIndex OBJECT-TYPE
    SYNTAX          Integer32 (-2147483648..2147483647)
    MAX-ACCESS      not-accessible
    STATUS          current
    DESCRIPTION     
            "The row number for the DSCCommandCodeRoutingTable table"
    ::= { ptDSCCommandCodeRoutingTableEntry 255 }

ptDSCCommandCodeRoutingRecord OBJECT IDENTIFIER
    ::= { ptDSCCommandCodeRoutingTable 1837 }

ptDSCCommandCodeRoutingRecordTable OBJECT-TYPE
    SYNTAX          SEQUENCE OF PtDSCCommandCodeRoutingRecordEntry
    MAX-ACCESS      not-accessible
    STATUS          current
    DESCRIPTION     
            "No description supplied in the proxy config file."
    ::= { ptDSCCommandCodeRoutingRecord 1 }

ptDSCCommandCodeRoutingRecordEntry OBJECT-TYPE
    SYNTAX          PtDSCCommandCodeRoutingRecordEntry
    MAX-ACCESS      not-accessible
    STATUS          current
    DESCRIPTION     
            "A sequence of DSCCommandCodeRoutingRecord attributes."
    INDEX           { ptConnGroupIndex, 
                      ptDSCCommandCodeRoutingRecordDSCIndex, 
                      ptDSCCommandCodeRoutingRecordDSCRoutingTablesIndex, 
                      ptDSCCommandCodeRoutingRecordCommandCodeRoutingTableIndex, 
                      ptDSCCommandCodeRoutingRecordIndex }
    ::= { ptDSCCommandCodeRoutingRecordTable 1 }

PtDSCCommandCodeRoutingRecordEntry ::=
    SEQUENCE {
        ptDSCCommandCodeRoutingRecordRecordType       INTEGER,
        ptDSCCommandCodeRoutingRecordCommandCodeName            DisplayString,
        ptDSCCommandCodeRoutingRecordNextTableName          DisplayString,
        ptDSCCommandCodeRoutingRecordModificationTableName                  DisplayString,
        ptDSCCommandCodeRoutingRecordDSCIndex     Integer32,
        ptDSCCommandCodeRoutingRecordDSCRoutingTablesIndex                  Integer32,
        ptDSCCommandCodeRoutingRecordCommandCodeRoutingTableIndex                         Integer32,
        ptDSCCommandCodeRoutingRecordParentOID      OBJECT IDENTIFIER,
        ptDSCCommandCodeRoutingRecordRowStatus      RowStatus,
        ptDSCCommandCodeRoutingRecordIndex  Integer32
    }

ptDSCCommandCodeRoutingRecordRecordType OBJECT-TYPE
    SYNTAX          INTEGER { default(1), value(1000) }
    MAX-ACCESS      read-only
    STATUS          current
    DESCRIPTION     
            "Record Type (DEFAULT/VALUE) \nA single non-deleteable DEFAULT record handles routing if no VALUE match is found. \nDefault value: VALUE."
    ::= { ptDSCCommandCodeRoutingRecordEntry 1 }

ptDSCCommandCodeRoutingRecordCommandCodeName OBJECT-TYPE
    SYNTAX          DisplayString (SIZE(0..255))
    MAX-ACCESS      read-only
    STATUS          current
    DESCRIPTION     
            "Associated Command Code Definition name. \nValid values: existing Command Code definition name."
    ::= { ptDSCCommandCodeRoutingRecordEntry 2 }

ptDSCCommandCodeRoutingRecordNextTableName OBJECT-TYPE
    SYNTAX          DisplayString (SIZE(0..255))
    MAX-ACCESS      read-create
    STATUS          current
    DESCRIPTION     
            "Next routing table, result table, default routing, or error handling to route the message. \nDepending on the required routing decision, set to: \n1) The name of the next routing table to continue routing. \n2) The name of the result table to send the message. \n3) dsc_default to apply default routing. \n4) dsc_error to return Result-Code 3002, UNABLE_TO_DELIVER. \n5) dsc_error<error code> to return Result-Code of <error code>. \n6) dsc_error<vendor id>_<error code> to return Experimental-Result with Vendor-Id of <vendor id> and Experimental-Result-Code of <error code>. \n7) dsc_discard to drop the request. \n \nOptional text may be added after a variant of dsc_error, separated by a space, to indicated a desired Error-Message. \nThe next table cannot be a modification table."
    ::= { ptDSCCommandCodeRoutingRecordEntry 3 }

ptDSCCommandCodeRoutingRecordModificationTableName OBJECT-TYPE
    SYNTAX          DisplayString (SIZE(0..255))
    MAX-ACCESS      read-create
    STATUS          current
    DESCRIPTION     
            "Associated optional Modification Table to be applied to the message. \nValid values: empty string and existing Modification Table name. \nDefault value: empty string."
    ::= { ptDSCCommandCodeRoutingRecordEntry 4 }

ptDSCCommandCodeRoutingRecordDSCIndex OBJECT-TYPE
    SYNTAX          Integer32 (-2147483648..2147483647)
    MAX-ACCESS      not-accessible
    STATUS          current
    DESCRIPTION     
            "This is the index of the parent type for this object.
             This parent type is DSC."
    ::= { ptDSCCommandCodeRoutingRecordEntry 242 }

ptDSCCommandCodeRoutingRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCCommandCodeRoutingRecordEntry 243 }

ptDSCCommandCodeRoutingRecordCommandCodeRoutingTableIndex OBJECT-TYPE
    SYNTAX          Integer32 (-2147483648..2147483647)
    MAX-ACCESS      not-accessible
    STATUS          current
    DESCRIPTION     
            "This is the index of the parent type for this object.
             This parent type is CommandCodeRoutingTable."
    ::= { ptDSCCommandCodeRoutingRecordEntry 244 }

ptDSCCommandCodeRoutingRecordParentOID OBJECT-TYPE
    SYNTAX          OBJECT IDENTIFIER
    MAX-ACCESS      read-create
    STATUS          current
    DESCRIPTION     
            "The OID of the parent object for this instance"
    ::= { ptDSCCommandCodeRoutingRecordEntry 253 }

ptDSCCommandCodeRoutingRecordRowStatus OBJECT-TYPE
    SYNTAX          RowStatus
    MAX-ACCESS      read-create
    STATUS          current
    DESCRIPTION     
            "The row status for the DSCCommandCodeRoutingRecord table"
    ::= { ptDSCCommandCodeRoutingRecordEntry 254 }

ptDSCCommandCodeRoutingRecordIndex OBJECT-TYPE
    SYNTAX          Integer32 (-2147483648..2147483647)
    MAX-ACCESS      not-accessible
    STATUS          current
    DESCRIPTION     
            "The row number for the DSCCommandCodeRoutingRecord table"
    ::= { ptDSCCommandCodeRoutingRecordEntry 255 }

ptDSCRealmRoutingTable OBJECT IDENTIFIER
    ::= { ptDSCDSCRoutingTables 1845 }

ptDSCRealmRoutingTableTable OBJECT-TYPE
    SYNTAX          SEQUENCE OF PtDSCRealmRoutingTableEntry
    MAX-ACCESS      not-accessible
    STATUS          current
    DESCRIPTION     
            "No description supplied in the proxy config file."
    ::= { ptDSCRealmRoutingTable 1 }

ptDSCRealmRoutingTableEntry OBJECT-TYPE
    SYNTAX          PtDSCRealmRoutingTableEntry
    MAX-ACCESS      not-accessible
    STATUS          current
    DESCRIPTION     
            "A sequence of DSCRealmRoutingTable attributes."
    INDEX           { ptConnGroupIndex, ptDSCRealmRoutingTableDSCIndex, 
                      ptDSCRealmRoutingTableDSCRoutingTablesIndex, 
                      ptDSCRealmRoutingTableIndex }
    ::= { ptDSCRealmRoutingTableTable 1 }

PtDSCRealmRoutingTableEntry ::=
    SEQUENCE {
        ptDSCRealmRoutingTableTableName DisplayString,
        ptDSCRealmRoutingTableDSCIndex  Integer32,
        ptDSCRealmRoutingTableDSCRoutingTablesIndex           Integer32,
        ptDSCRealmRoutingTableParentOID OBJECT IDENTIFIER,
        ptDSCRealmRoutingTableRowStatus RowStatus,
        ptDSCRealmRoutingTableIndex     Integer32
    }

ptDSCRealmRoutingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCRealmRoutingTableEntry 1 }

ptDSCRealmRoutingTableDSCIndex OBJECT-TYPE
    SYNTAX          Integer32 (-2147483648..2147483647)
    MAX-ACCESS      not-accessible
    STATUS          current
    DESCRIPTION     
            "This is the index of the parent type for this object.
             This parent type is DSC."
    ::= { ptDSCRealmRoutingTableEntry 242 }

ptDSCRealmRoutingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCRealmRoutingTableEntry 243 }

ptDSCRealmRoutingTableParentOID OBJECT-TYPE
    SYNTAX          OBJECT IDENTIFIER
    MAX-ACCESS      read-create
    STATUS          current
    DESCRIPTION     
            "The OID of the parent object for this instance"
    ::= { ptDSCRealmRoutingTableEntry 253 }

ptDSCRealmRoutingTableRowStatus OBJECT-TYPE
    SYNTAX          RowStatus
    MAX-ACCESS      read-create
    STATUS          current
    DESCRIPTION     
            "The row status for the DSCRealmRoutingTable table"
    ::= { ptDSCRealmRoutingTableEntry 254 }

ptDSCRealmRoutingTableIndex OBJECT-TYPE
    SYNTAX          Integer32 (-2147483648..2147483647)
    MAX-ACCESS      not-accessible
    STATUS          current
    DESCRIPTION     
            "The row number for the DSCRealmRoutingTable table"
    ::= { ptDSCRealmRoutingTableEntry 255 }

ptDSCRealmRoutingRecord OBJECT IDENTIFIER
    ::= { ptDSCRealmRoutingTable 1846 }

ptDSCRealmRoutingRecordTable OBJECT-TYPE
    SYNTAX          SEQUENCE OF PtDSCRealmRoutingRecordEntry
    MAX-ACCESS      not-accessible
    STATUS          current
    DESCRIPTION     
            "No description supplied in the proxy config file."
    ::= { ptDSCRealmRoutingRecord 1 }

ptDSCRealmRoutingRecordEntry OBJECT-TYPE
    SYNTAX          PtDSCRealmRoutingRecordEntry
    MAX-ACCESS      not-accessible
    STATUS          current
    DESCRIPTION     
            "A sequence of DSCRealmRoutingRecord attributes."
    INDEX           { ptConnGroupIndex, ptDSCRealmRoutingRecordDSCIndex, 
                      ptDSCRealmRoutingRecordDSCRoutingTablesIndex, 
                      ptDSCRealmRoutingRecordRealmRoutingTableIndex, 
                      ptDSCRealmRoutingRecordIndex }
    ::= { ptDSCRealmRoutingRecordTable 1 }

PtDSCRealmRoutingRecordEntry ::=
    SEQUENCE {
        ptDSCRealmRoutingRecordRecordType INTEGER,
        ptDSCRealmRoutingRecordRemoteRealm  DisplayString,
        ptDSCRealmRoutingRecordCost     INTEGER,
        ptDSCRealmRoutingRecordAdjacentRealm    DisplayString,
        ptDSCRealmRoutingRecordDSCIndex Integer32,
        ptDSCRealmRoutingRecordDSCRoutingTablesIndex            Integer32,
        ptDSCRealmRoutingRecordRealmRoutingTableIndex             Integer32,
        ptDSCRealmRoutingRecordParentOID OBJECT IDENTIFIER,
        ptDSCRealmRoutingRecordRowStatus RowStatus,
        ptDSCRealmRoutingRecordIndex    Integer32
    }

ptDSCRealmRoutingRecordRecordType OBJECT-TYPE
    SYNTAX          INTEGER { default(1), value(1000) }
    MAX-ACCESS      read-only
    STATUS          current
    DESCRIPTION     
            "Record Type (DEFAULT/VALUE). \nThere may be only one record of type DEFAULT in each Realm Routing table. Records of type DEFAULT are not allowed to specify a Remote Realm and should therefore be left unspecified upon creation. Records of type VALUE must specify both a Remote Realm and an Adjacent Realm. Default value: VALUE."
    ::= { ptDSCRealmRoutingRecordEntry 1 }

ptDSCRealmRoutingRecordRemoteRealm OBJECT-TYPE
    SYNTAX          DisplayString (SIZE(0..255))
    MAX-ACCESS      read-create
    STATUS          current
    DESCRIPTION     
            "Remote Realm that a message is to be routed. \nIf a FQDN is specified, a Realm Definition will be automatically created if none exists. If a Realm Definition is already defined, the FQDN value will be replaced by the associated alias. \nValid values: empty string (DEFAULT) \n FQDN format or existing Realm Definition alias (VALUE)."
    ::= { ptDSCRealmRoutingRecordEntry 2 }

ptDSCRealmRoutingRecordCost OBJECT-TYPE
    SYNTAX          INTEGER { incomingOnly(-1) }
    MAX-ACCESS      read-create
    STATUS          current
    DESCRIPTION     
            "Cost of routing a message to Adjacent Realm from Remote Realm (INCOMING ONLY (-1), 1 to 100). \nA value of INCOMING ONLY (-1) will prevent requests from being sent by the Adjacent Realm. \nDefault value: 10 (reference only)."
    ::= { ptDSCRealmRoutingRecordEntry 3 }

ptDSCRealmRoutingRecordAdjacentRealm OBJECT-TYPE
    SYNTAX          DisplayString (SIZE(0..255))
    MAX-ACCESS      read-create
    STATUS          current
    DESCRIPTION     
            "Adjacent Realm that a message from Remote Realm is to be routed to. \nIf a FQDN is specified, a Realm Definition will be automatically created if none exists. If a Realm Definition is already defined, the FQDN value will be replaced by the associated alias. \nValid values: FQDN format or existing Realm Definition alias."
    ::= { ptDSCRealmRoutingRecordEntry 4 }

ptDSCRealmRoutingRecordDSCIndex OBJECT-TYPE
    SYNTAX          Integer32 (-2147483648..2147483647)
    MAX-ACCESS      not-accessible
    STATUS          current
    DESCRIPTION     
            "This is the index of the parent type for this object.
             This parent type is DSC."
    ::= { ptDSCRealmRoutingRecordEntry 242 }

ptDSCRealmRoutingRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCRealmRoutingRecordEntry 243 }

ptDSCRealmRoutingRecordRealmRoutingTableIndex OBJECT-TYPE
    SYNTAX          Integer32 (-2147483648..2147483647)
    MAX-ACCESS      not-accessible
    STATUS          current
    DESCRIPTION     
            "This is the index of the parent type for this object.
             This parent type is RealmRoutingTable."
    ::= { ptDSCRealmRoutingRecordEntry 244 }

ptDSCRealmRoutingRecordParentOID OBJECT-TYPE
    SYNTAX          OBJECT IDENTIFIER
    MAX-ACCESS      read-create
    STATUS          current
    DESCRIPTION     
            "The OID of the parent object for this instance"
    ::= { ptDSCRealmRoutingRecordEntry 253 }

ptDSCRealmRoutingRecordRowStatus OBJECT-TYPE
    SYNTAX          RowStatus
    MAX-ACCESS      read-create
    STATUS          current
    DESCRIPTION     
            "The row status for the DSCRealmRoutingRecord table"
    ::= { ptDSCRealmRoutingRecordEntry 254 }

ptDSCRealmRoutingRecordIndex OBJECT-TYPE
    SYNTAX          Integer32 (-2147483648..2147483647)
    MAX-ACCESS      not-accessible
    STATUS          current
    DESCRIPTION     
            "The row number for the DSCRealmRoutingRecord table"
    ::= { ptDSCRealmRoutingRecordEntry 255 }

ptDSCTopologyMappingTable OBJECT IDENTIFIER
    ::= { ptDSCDSCRoutingTables 1850 }

ptDSCTopologyMappingTableTable OBJECT-TYPE
    SYNTAX          SEQUENCE OF PtDSCTopologyMappingTableEntry
    MAX-ACCESS      not-accessible
    STATUS          current
    DESCRIPTION     
            "No description supplied in the proxy config file."
    ::= { ptDSCTopologyMappingTable 1 }

ptDSCTopologyMappingTableEntry OBJECT-TYPE
    SYNTAX          PtDSCTopologyMappingTableEntry
    MAX-ACCESS      not-accessible
    STATUS          current
    DESCRIPTION     
            "A sequence of DSCTopologyMappingTable attributes."
    INDEX           { ptConnGroupIndex, 
                      ptDSCTopologyMappingTableDSCIndex, 
                      ptDSCTopologyMappingTableDSCRoutingTablesIndex, 
                      ptDSCTopologyMappingTableIndex }
    ::= { ptDSCTopologyMappingTableTable 1 }

PtDSCTopologyMappingTableEntry ::=
    SEQUENCE {
        ptDSCTopologyMappingTableTableName  DisplayString,
        ptDSCTopologyMappingTableDSCIndex Integer32,
        ptDSCTopologyMappingTableDSCRoutingTablesIndex              Integer32,
        ptDSCTopologyMappingTableParentOID  OBJECT IDENTIFIER,
        ptDSCTopologyMappingTableRowStatus  RowStatus,
        ptDSCTopologyMappingTableIndex  Integer32
    }

ptDSCTopologyMappingTableTableName OBJECT-TYPE
    SYNTAX          DisplayString (SIZE(0..255))
    MAX-ACCESS      read-only
    STATUS          current
    DESCRIPTION     
            "Table Name to uniquely identify the table. \nThe Table Name must be unique across all table types. \nLeading and trailing whitespaces are trimmed. \nValid values: alphanumeric characters, dashes, underscores, spaces, and dots (maximum size of 64). Cannot start the name with reserved dsc_ or pt_ (case insensitive)."
    ::= { ptDSCTopologyMappingTableEntry 1 }

ptDSCTopologyMappingTableDSCIndex OBJECT-TYPE
    SYNTAX          Integer32 (-2147483648..2147483647)
    MAX-ACCESS      not-accessible
    STATUS          current
    DESCRIPTION     
            "This is the index of the parent type for this object.
             This parent type is DSC."
    ::= { ptDSCTopologyMappingTableEntry 242 }

ptDSCTopologyMappingTableDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCTopologyMappingTableEntry 243 }

ptDSCTopologyMappingTableParentOID OBJECT-TYPE
    SYNTAX          OBJECT IDENTIFIER
    MAX-ACCESS      read-create
    STATUS          current
    DESCRIPTION     
            "The OID of the parent object for this instance"
    ::= { ptDSCTopologyMappingTableEntry 253 }

ptDSCTopologyMappingTableRowStatus OBJECT-TYPE
    SYNTAX          RowStatus
    MAX-ACCESS      read-create
    STATUS          current
    DESCRIPTION     
            "The row status for the DSCTopologyMappingTable table"
    ::= { ptDSCTopologyMappingTableEntry 254 }

ptDSCTopologyMappingTableIndex OBJECT-TYPE
    SYNTAX          Integer32 (-2147483648..2147483647)
    MAX-ACCESS      not-accessible
    STATUS          current
    DESCRIPTION     
            "The row number for the DSCTopologyMappingTable table"
    ::= { ptDSCTopologyMappingTableEntry 255 }

ptDSCTopologyOneToOnePublicMapping OBJECT IDENTIFIER
    ::= { ptDSCTopologyMappingTable 1851 }

ptDSCTopologyOneToOnePublicMappingTable OBJECT-TYPE
    SYNTAX          SEQUENCE OF PtDSCTopologyOneToOnePublicMappingEntry
    MAX-ACCESS      not-accessible
    STATUS          current
    DESCRIPTION     
            "No description supplied in the proxy config file."
    ::= { ptDSCTopologyOneToOnePublicMapping 1 }

ptDSCTopologyOneToOnePublicMappingEntry OBJECT-TYPE
    SYNTAX          PtDSCTopologyOneToOnePublicMappingEntry
    MAX-ACCESS      not-accessible
    STATUS          current
    DESCRIPTION     
            "A sequence of DSCTopologyOneToOnePublicMapping attributes."
    INDEX           { ptConnGroupIndex, 
                      ptDSCTopologyOneToOnePublicMappingDSCIndex, 
                      ptDSCTopologyOneToOnePublicMappingDSCRoutingTablesIndex, 
                      ptDSCTopologyOneToOnePublicMappingTopologyMappingTableIndex, 
                      ptDSCTopologyOneToOnePublicMappingIndex }
    ::= { ptDSCTopologyOneToOnePublicMappingTable 1 }

PtDSCTopologyOneToOnePublicMappingEntry ::=
    SEQUENCE {
        ptDSCTopologyOneToOnePublicMappingRealm       DisplayString,
        ptDSCTopologyOneToOnePublicMappingPrivateDIDHost                DisplayString,
        ptDSCTopologyOneToOnePublicMappingPublicDIDHost               DisplayString,
        ptDSCTopologyOneToOnePublicMappingDSCIndex          Integer32,
        ptDSCTopologyOneToOnePublicMappingDSCRoutingTablesIndex                       Integer32,
        ptDSCTopologyOneToOnePublicMappingTopologyMappingTableIndex                           Integer32,
        ptDSCTopologyOneToOnePublicMappingParentOID           OBJECT IDENTIFIER,
        ptDSCTopologyOneToOnePublicMappingRowStatus           RowStatus,
        ptDSCTopologyOneToOnePublicMappingIndex       Integer32
    }

ptDSCTopologyOneToOnePublicMappingRealm OBJECT-TYPE
    SYNTAX          DisplayString (SIZE(0..255))
    MAX-ACCESS      read-create
    STATUS          current
    DESCRIPTION     
            "Topology Mapping Realm to protect. \nAdd this value to the Private DID Host attribute for the internal protected Diameter ID. \nAdd this value to the Public DID Host attribute for the external Diameter ID. \nIf a FQDN is specified, a Realm Definition will be automatically created if none exists. If a Realm Definition is already defined, the FQDN value will be replaced by the associated alias. \nValid values: FQDN format or existing Realm Definition alias."
    ::= { ptDSCTopologyOneToOnePublicMappingEntry 1 }

ptDSCTopologyOneToOnePublicMappingPrivateDIDHost OBJECT-TYPE
    SYNTAX          DisplayString (SIZE(0..255))
    MAX-ACCESS      read-create
    STATUS          current
    DESCRIPTION     
            "Host of the Diameter Node inside the protected realm. \nValid values: FQDN format."
    ::= { ptDSCTopologyOneToOnePublicMappingEntry 2 }

ptDSCTopologyOneToOnePublicMappingPublicDIDHost OBJECT-TYPE
    SYNTAX          DisplayString (SIZE(0..255))
    MAX-ACCESS      read-create
    STATUS          current
    DESCRIPTION     
            "Host of the Diameter Node to present to the outside realms. \nValid values: FQDN format."
    ::= { ptDSCTopologyOneToOnePublicMappingEntry 3 }

ptDSCTopologyOneToOnePublicMappingDSCIndex OBJECT-TYPE
    SYNTAX          Integer32 (-2147483648..2147483647)
    MAX-ACCESS      not-accessible
    STATUS          current
    DESCRIPTION     
            "This is the index of the parent type for this object.
             This parent type is DSC."
    ::= { ptDSCTopologyOneToOnePublicMappingEntry 242 }

ptDSCTopologyOneToOnePublicMappingDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCTopologyOneToOnePublicMappingEntry 243 }

ptDSCTopologyOneToOnePublicMappingTopologyMappingTableIndex OBJECT-TYPE
    SYNTAX          Integer32 (-2147483648..2147483647)
    MAX-ACCESS      not-accessible
    STATUS          current
    DESCRIPTION     
            "This is the index of the parent type for this object.
             This parent type is TopologyMappingTable."
    ::= { ptDSCTopologyOneToOnePublicMappingEntry 244 }

ptDSCTopologyOneToOnePublicMappingParentOID OBJECT-TYPE
    SYNTAX          OBJECT IDENTIFIER
    MAX-ACCESS      read-create
    STATUS          current
    DESCRIPTION     
            "The OID of the parent object for this instance"
    ::= { ptDSCTopologyOneToOnePublicMappingEntry 253 }

ptDSCTopologyOneToOnePublicMappingRowStatus OBJECT-TYPE
    SYNTAX          RowStatus
    MAX-ACCESS      read-create
    STATUS          current
    DESCRIPTION     
            "The row status for the DSCTopologyOneToOnePublicMapping table"
    ::= { ptDSCTopologyOneToOnePublicMappingEntry 254 }

ptDSCTopologyOneToOnePublicMappingIndex OBJECT-TYPE
    SYNTAX          Integer32 (-2147483648..2147483647)
    MAX-ACCESS      not-accessible
    STATUS          current
    DESCRIPTION     
            "The row number for the DSCTopologyOneToOnePublicMapping table"
    ::= { ptDSCTopologyOneToOnePublicMappingEntry 255 }

ptDSCTopologyOneToNPublicMapping OBJECT IDENTIFIER
    ::= { ptDSCTopologyMappingTable 1852 }

ptDSCTopologyOneToNPublicMappingTable OBJECT-TYPE
    SYNTAX          SEQUENCE OF PtDSCTopologyOneToNPublicMappingEntry
    MAX-ACCESS      not-accessible
    STATUS          current
    DESCRIPTION     
            "No description supplied in the proxy config file."
    ::= { ptDSCTopologyOneToNPublicMapping 1 }

ptDSCTopologyOneToNPublicMappingEntry OBJECT-TYPE
    SYNTAX          PtDSCTopologyOneToNPublicMappingEntry
    MAX-ACCESS      not-accessible
    STATUS          current
    DESCRIPTION     
            "A sequence of DSCTopologyOneToNPublicMapping attributes."
    INDEX           { ptConnGroupIndex, 
                      ptDSCTopologyOneToNPublicMappingDSCIndex, 
                      ptDSCTopologyOneToNPublicMappingDSCRoutingTablesIndex, 
                      ptDSCTopologyOneToNPublicMappingTopologyMappingTableIndex, 
                      ptDSCTopologyOneToNPublicMappingIndex }
    ::= { ptDSCTopologyOneToNPublicMappingTable 1 }

PtDSCTopologyOneToNPublicMappingEntry ::=
    SEQUENCE {
        ptDSCTopologyOneToNPublicMappingRealm     DisplayString,
        ptDSCTopologyOneToNPublicMappingPrivateDIDHost              DisplayString,
        ptDSCTopologyOneToNPublicMappingPublicDIDHostPrefix                   DisplayString,
        ptDSCTopologyOneToNPublicMappingPublicDIDHostSuffix                   DisplayString,
        ptDSCTopologyOneToNPublicMappingDSCIndex        Integer32,
        ptDSCTopologyOneToNPublicMappingDSCRoutingTablesIndex                     Integer32,
        ptDSCTopologyOneToNPublicMappingTopologyMappingTableIndex                         Integer32,
        ptDSCTopologyOneToNPublicMappingParentOID         OBJECT IDENTIFIER,
        ptDSCTopologyOneToNPublicMappingRowStatus         RowStatus,
        ptDSCTopologyOneToNPublicMappingIndex     Integer32
    }

ptDSCTopologyOneToNPublicMappingRealm OBJECT-TYPE
    SYNTAX          DisplayString (SIZE(0..255))
    MAX-ACCESS      read-create
    STATUS          current
    DESCRIPTION     
            "Topology Mapping Realm to protect. \nAdd this value to the Private DID Host attribute for the internal protected Diameter ID. \nAdd this value to the Public DID Host attribute for the external Diameter ID. \nIf a FQDN is specified, a Realm Definition will be automatically created if none exists. If a Realm Definition is already defined, the FQDN value will be replaced by the associated alias. \nValid values: FQDN format or existing Realm Definition alias."
    ::= { ptDSCTopologyOneToNPublicMappingEntry 1 }

ptDSCTopologyOneToNPublicMappingPrivateDIDHost OBJECT-TYPE
    SYNTAX          DisplayString (SIZE(0..255))
    MAX-ACCESS      read-create
    STATUS          current
    DESCRIPTION     
            "Host of the Diameter Node inside the protected realm. \nValid values: FQDN format."
    ::= { ptDSCTopologyOneToNPublicMappingEntry 2 }

ptDSCTopologyOneToNPublicMappingPublicDIDHostPrefix OBJECT-TYPE
    SYNTAX          DisplayString (SIZE(0..255))
    MAX-ACCESS      read-create
    STATUS          current
    DESCRIPTION     
            "Host of the Diameter Node to present to the outside realms. \nValid values: FQDN format."
    ::= { ptDSCTopologyOneToNPublicMappingEntry 3 }

ptDSCTopologyOneToNPublicMappingPublicDIDHostSuffix OBJECT-TYPE
    SYNTAX          DisplayString (SIZE(0..255))
    MAX-ACCESS      read-create
    STATUS          current
    DESCRIPTION     
            "Input format is: <begin> - <end>, where <begin> and <end> are \nnumbers between 1-10000. There can be a difference up to \n32 between end and begin. This is the range of suffix \nvalues to add to the Public DID for this mapping."
    ::= { ptDSCTopologyOneToNPublicMappingEntry 4 }

ptDSCTopologyOneToNPublicMappingDSCIndex OBJECT-TYPE
    SYNTAX          Integer32 (-2147483648..2147483647)
    MAX-ACCESS      not-accessible
    STATUS          current
    DESCRIPTION     
            "This is the index of the parent type for this object.
             This parent type is DSC."
    ::= { ptDSCTopologyOneToNPublicMappingEntry 242 }

ptDSCTopologyOneToNPublicMappingDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCTopologyOneToNPublicMappingEntry 243 }

ptDSCTopologyOneToNPublicMappingTopologyMappingTableIndex OBJECT-TYPE
    SYNTAX          Integer32 (-2147483648..2147483647)
    MAX-ACCESS      not-accessible
    STATUS          current
    DESCRIPTION     
            "This is the index of the parent type for this object.
             This parent type is TopologyMappingTable."
    ::= { ptDSCTopologyOneToNPublicMappingEntry 244 }

ptDSCTopologyOneToNPublicMappingParentOID OBJECT-TYPE
    SYNTAX          OBJECT IDENTIFIER
    MAX-ACCESS      read-create
    STATUS          current
    DESCRIPTION     
            "The OID of the parent object for this instance"
    ::= { ptDSCTopologyOneToNPublicMappingEntry 253 }

ptDSCTopologyOneToNPublicMappingRowStatus OBJECT-TYPE
    SYNTAX          RowStatus
    MAX-ACCESS      read-create
    STATUS          current
    DESCRIPTION     
            "The row status for the DSCTopologyOneToNPublicMapping table"
    ::= { ptDSCTopologyOneToNPublicMappingEntry 254 }

ptDSCTopologyOneToNPublicMappingIndex OBJECT-TYPE
    SYNTAX          Integer32 (-2147483648..2147483647)
    MAX-ACCESS      not-accessible
    STATUS          current
    DESCRIPTION     
            "The row number for the DSCTopologyOneToNPublicMapping table"
    ::= { ptDSCTopologyOneToNPublicMappingEntry 255 }

ptDSCDSCRoutingSearchUtility OBJECT IDENTIFIER
    ::= { ptDSCDSCRoutingTables 1857 }

ptDSCDSCRoutingSearchUtilityTable OBJECT-TYPE
    SYNTAX          SEQUENCE OF PtDSCDSCRoutingSearchUtilityEntry
    MAX-ACCESS      not-accessible
    STATUS          current
    DESCRIPTION     
            "No description supplied in the proxy config file."
    ::= { ptDSCDSCRoutingSearchUtility 1 }

ptDSCDSCRoutingSearchUtilityEntry OBJECT-TYPE
    SYNTAX          PtDSCDSCRoutingSearchUtilityEntry
    MAX-ACCESS      not-accessible
    STATUS          current
    DESCRIPTION     
            "A sequence of DSCDSCRoutingSearchUtility attributes."
    INDEX           { ptConnGroupIndex, 
                      ptDSCDSCRoutingSearchUtilityDSCIndex, 
                      ptDSCDSCRoutingSearchUtilityDSCRoutingTablesIndex, 
                      ptDSCDSCRoutingSearchUtilityIndex }
    ::= { ptDSCDSCRoutingSearchUtilityTable 1 }

PtDSCDSCRoutingSearchUtilityEntry ::=
    SEQUENCE {
        ptDSCDSCRoutingSearchUtilityDSCNodeName       DisplayString,
        ptDSCDSCRoutingSearchUtilityRequestIncomingADNName                  DisplayString,
        ptDSCDSCRoutingSearchUtilityAnswerIncomingADNName                 DisplayString,
        ptDSCDSCRoutingSearchUtilityInitialRoutingTableName                   DisplayString,
        ptDSCDSCRoutingSearchUtilityResult  DisplayString,
        ptDSCDSCRoutingSearchUtilityDiagnosticMessage             DisplayString,
        ptDSCDSCRoutingSearchUtilityDSCIndex    Integer32,
        ptDSCDSCRoutingSearchUtilityDSCRoutingTablesIndex                 Integer32,
        ptDSCDSCRoutingSearchUtilityActions   INTEGER,
        ptDSCDSCRoutingSearchUtilityParentOID     OBJECT IDENTIFIER,
        ptDSCDSCRoutingSearchUtilityRowStatus     RowStatus,
        ptDSCDSCRoutingSearchUtilityIndex Integer32
    }

ptDSCDSCRoutingSearchUtilityDSCNodeName OBJECT-TYPE
    SYNTAX          DisplayString (SIZE(0..255))
    MAX-ACCESS      read-create
    STATUS          current
    DESCRIPTION     
            "Name used to logically identify the DSC Node. \nThe attribute is mandatory and is used to identify the DSC Node where the routing search is performed. \nThe Node Name value must be defined on the DSC instance of the Search Utility."
    ::= { ptDSCDSCRoutingSearchUtilityEntry 1 }

ptDSCDSCRoutingSearchUtilityRequestIncomingADNName OBJECT-TYPE
    SYNTAX          DisplayString (SIZE(0..255))
    MAX-ACCESS      read-create
    STATUS          current
    DESCRIPTION     
            "Incoming Adjacent Diameter Node Name for Request Message. \nThe attribute is mandatory and is used to identify the Request Message DSC Incoming ADN where the TEST message is received. \nFor Answer Test Message, this represents the incoming ADN of the original Request Message. \nThe ADN DID value must be defined on the input DSC Node and must have at least one connection."
    ::= { ptDSCDSCRoutingSearchUtilityEntry 2 }

ptDSCDSCRoutingSearchUtilityAnswerIncomingADNName OBJECT-TYPE
    SYNTAX          DisplayString (SIZE(0..255))
    MAX-ACCESS      read-create
    STATUS          current
    DESCRIPTION     
            "Incoming Adjacent Diameter Node Name for Answer Message. \nThe attribute is mandatory for Answer Message but is not required for REQUEST Message. It is used to identify the Answer Message Incoming ADN where the TEST message is received. \nThe ADN DID value must be defined on the input DSC Node diameter ID and must have at least one connection."
    ::= { ptDSCDSCRoutingSearchUtilityEntry 3 }

ptDSCDSCRoutingSearchUtilityInitialRoutingTableName OBJECT-TYPE
    SYNTAX          DisplayString (SIZE(0..255))
    MAX-ACCESS      read-create
    STATUS          current
    DESCRIPTION     
            "Initial Routing Table Name to Test. \nThe Test Message will be routed starting from this routing table. The Initial Routing Table Name must be defined on the search interface instance routing table. \nIf not supplied, it will use the Initial Routing Table Name of the input node for Request message. For Answer message, this will return INVALID INPUT result"
    ::= { ptDSCDSCRoutingSearchUtilityEntry 4 }

ptDSCDSCRoutingSearchUtilityResult OBJECT-TYPE
    SYNTAX          DisplayString (SIZE(0..255))
    MAX-ACCESS      read-only
    STATUS          current
    DESCRIPTION     
            "Routing Test Result of the message (MESSAGE TESTED SUCCESSFULLY, RETURN ERROR, DISCARD MESSAGE, INVALID INPUT, MESSAGE TESTED NOT COMPLETED)."
    ::= { ptDSCDSCRoutingSearchUtilityEntry 20 }

ptDSCDSCRoutingSearchUtilityDiagnosticMessage OBJECT-TYPE
    SYNTAX          DisplayString (SIZE(0..255))
    MAX-ACCESS      read-only
    STATUS          current
    DESCRIPTION     
            "The Diagnostic Message will display the header of the test message for user to confirm the test message content. It will also capture the message path of the test message. \nif an error is detected in the search criteria, this will alert the user on what is specifically wrong with the data."
    ::= { ptDSCDSCRoutingSearchUtilityEntry 21 }

ptDSCDSCRoutingSearchUtilityDSCIndex OBJECT-TYPE
    SYNTAX          Integer32 (-2147483648..2147483647)
    MAX-ACCESS      not-accessible
    STATUS          current
    DESCRIPTION     
            "This is the index of the parent type for this object.
             This parent type is DSC."
    ::= { ptDSCDSCRoutingSearchUtilityEntry 242 }

ptDSCDSCRoutingSearchUtilityDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCDSCRoutingSearchUtilityEntry 243 }

ptDSCDSCRoutingSearchUtilityActions OBJECT-TYPE
    SYNTAX          INTEGER { clearSearchCriteria(1), performSearch(2) }
    MAX-ACCESS      read-create
    STATUS          current
    DESCRIPTION     
            "The OID of all possible actions for this instance"
    ::= { ptDSCDSCRoutingSearchUtilityEntry 252 }

ptDSCDSCRoutingSearchUtilityParentOID OBJECT-TYPE
    SYNTAX          OBJECT IDENTIFIER
    MAX-ACCESS      read-create
    STATUS          current
    DESCRIPTION     
            "The OID of the parent object for this instance"
    ::= { ptDSCDSCRoutingSearchUtilityEntry 253 }

ptDSCDSCRoutingSearchUtilityRowStatus OBJECT-TYPE
    SYNTAX          RowStatus
    MAX-ACCESS      read-create
    STATUS          current
    DESCRIPTION     
            "The row status for the DSCDSCRoutingSearchUtility table"
    ::= { ptDSCDSCRoutingSearchUtilityEntry 254 }

ptDSCDSCRoutingSearchUtilityIndex OBJECT-TYPE
    SYNTAX          Integer32 (-2147483648..2147483647)
    MAX-ACCESS      not-accessible
    STATUS          current
    DESCRIPTION     
            "The row number for the DSCDSCRoutingSearchUtility table"
    ::= { ptDSCDSCRoutingSearchUtilityEntry 255 }

ptDSCDSCTableRecord OBJECT IDENTIFIER
    ::= { ptDSCDSCRoutingSearchUtility 1859 }

ptDSCDSCTableRecordTable OBJECT-TYPE
    SYNTAX          SEQUENCE OF PtDSCDSCTableRecordEntry
    MAX-ACCESS      not-accessible
    STATUS          current
    DESCRIPTION     
            "No description supplied in the proxy config file."
    ::= { ptDSCDSCTableRecord 1 }

ptDSCDSCTableRecordEntry OBJECT-TYPE
    SYNTAX          PtDSCDSCTableRecordEntry
    MAX-ACCESS      not-accessible
    STATUS          current
    DESCRIPTION     
            "A sequence of DSCDSCTableRecord attributes."
    INDEX           { ptConnGroupIndex, ptDSCDSCTableRecordDSCIndex, 
                      ptDSCDSCTableRecordDSCRoutingTablesIndex, 
                      ptDSCDSCTableRecordDSCRoutingSearchUtilityIndex, 
                      ptDSCDSCTableRecordIndex }
    ::= { ptDSCDSCTableRecordTable 1 }

PtDSCDSCTableRecordEntry ::=
    SEQUENCE {
        ptDSCDSCTableRecordSequenceNumber Integer32,
        ptDSCDSCTableRecordMatchingTableType    DisplayString,
        ptDSCDSCTableRecordMatchingTableName    DisplayString,
        ptDSCDSCTableRecordTableRecord  DisplayString,
        ptDSCDSCTableRecordNextTable    DisplayString,
        ptDSCDSCTableRecordModificationTable    DisplayString,
        ptDSCDSCTableRecordDSCIndex     Integer32,
        ptDSCDSCTableRecordDSCRoutingTablesIndex        Integer32,
        ptDSCDSCTableRecordDSCRoutingSearchUtilityIndex               Integer32,
        ptDSCDSCTableRecordParentOID    OBJECT IDENTIFIER,
        ptDSCDSCTableRecordRowStatus    RowStatus,
        ptDSCDSCTableRecordIndex        Integer32
    }

ptDSCDSCTableRecordSequenceNumber OBJECT-TYPE
    SYNTAX          Integer32 (-2147483648..2147483647)
    MAX-ACCESS      read-only
    STATUS          current
    DESCRIPTION     
            "Routing Search Result Sequence Number to indicate the sequence of the matching table record. The smaller the number, the early the test message passes through the matching table record."
    ::= { ptDSCDSCTableRecordEntry 1 }

ptDSCDSCTableRecordMatchingTableType OBJECT-TYPE
    SYNTAX          DisplayString (SIZE(0..255))
    MAX-ACCESS      read-only
    STATUS          current
    DESCRIPTION     
            "DSC Search Result Matching Table Type"
    ::= { ptDSCDSCTableRecordEntry 2 }

ptDSCDSCTableRecordMatchingTableName OBJECT-TYPE
    SYNTAX          DisplayString (SIZE(0..255))
    MAX-ACCESS      read-only
    STATUS          current
    DESCRIPTION     
            "DSC Search Result Matching Table Name"
    ::= { ptDSCDSCTableRecordEntry 3 }

ptDSCDSCTableRecordTableRecord OBJECT-TYPE
    SYNTAX          DisplayString (SIZE(0..255))
    MAX-ACCESS      read-only
    STATUS          current
    DESCRIPTION     
            "DSC Matching Table Record to store the key and content of the matching record"
    ::= { ptDSCDSCTableRecordEntry 4 }

ptDSCDSCTableRecordNextTable OBJECT-TYPE
    SYNTAX          DisplayString (SIZE(0..255))
    MAX-ACCESS      read-only
    STATUS          current
    DESCRIPTION     
            "Next routing table, result table, default routing, or error handling to route the message. \nThe next table cannot be a modification table."
    ::= { ptDSCDSCTableRecordEntry 5 }

ptDSCDSCTableRecordModificationTable OBJECT-TYPE
    SYNTAX          DisplayString (SIZE(0..255))
    MAX-ACCESS      read-only
    STATUS          current
    DESCRIPTION     
            "Associated optional Modification Table to be applied to the message. \nValid values: empty string and existing Modification Table name."
    ::= { ptDSCDSCTableRecordEntry 6 }

ptDSCDSCTableRecordDSCIndex OBJECT-TYPE
    SYNTAX          Integer32 (-2147483648..2147483647)
    MAX-ACCESS      not-accessible
    STATUS          current
    DESCRIPTION     
            "This is the index of the parent type for this object.
             This parent type is DSC."
    ::= { ptDSCDSCTableRecordEntry 242 }

ptDSCDSCTableRecordDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCDSCTableRecordEntry 243 }

ptDSCDSCTableRecordDSCRoutingSearchUtilityIndex OBJECT-TYPE
    SYNTAX          Integer32 (-2147483648..2147483647)
    MAX-ACCESS      not-accessible
    STATUS          current
    DESCRIPTION     
            "This is the index of the parent type for this object.
             This parent type is DSCRoutingSearchUtility."
    ::= { ptDSCDSCTableRecordEntry 244 }

ptDSCDSCTableRecordParentOID OBJECT-TYPE
    SYNTAX          OBJECT IDENTIFIER
    MAX-ACCESS      read-create
    STATUS          current
    DESCRIPTION     
            "The OID of the parent object for this instance"
    ::= { ptDSCDSCTableRecordEntry 253 }

ptDSCDSCTableRecordRowStatus OBJECT-TYPE
    SYNTAX          RowStatus
    MAX-ACCESS      read-create
    STATUS          current
    DESCRIPTION     
            "The row status for the DSCDSCTableRecord table"
    ::= { ptDSCDSCTableRecordEntry 254 }

ptDSCDSCTableRecordIndex OBJECT-TYPE
    SYNTAX          Integer32 (-2147483648..2147483647)
    MAX-ACCESS      not-accessible
    STATUS          current
    DESCRIPTION     
            "The row number for the DSCDSCTableRecord table"
    ::= { ptDSCDSCTableRecordEntry 255 }

ptDSCDSCCandidateOutgoingADN OBJECT IDENTIFIER
    ::= { ptDSCDSCRoutingSearchUtility 1860 }

ptDSCDSCCandidateOutgoingADNTable OBJECT-TYPE
    SYNTAX          SEQUENCE OF PtDSCDSCCandidateOutgoingADNEntry
    MAX-ACCESS      not-accessible
    STATUS          current
    DESCRIPTION     
            "No description supplied in the proxy config file."
    ::= { ptDSCDSCCandidateOutgoingADN 1 }

ptDSCDSCCandidateOutgoingADNEntry OBJECT-TYPE
    SYNTAX          PtDSCDSCCandidateOutgoingADNEntry
    MAX-ACCESS      not-accessible
    STATUS          current
    DESCRIPTION     
            "A sequence of DSCDSCCandidateOutgoingADN attributes."
    INDEX           { ptConnGroupIndex, 
                      ptDSCDSCCandidateOutgoingADNDSCIndex, 
                      ptDSCDSCCandidateOutgoingADNDSCRoutingTablesIndex, 
                      ptDSCDSCCandidateOutgoingADNDSCRoutingSearchUtilityIndex, 
                      ptDSCDSCCandidateOutgoingADNIndex }
    ::= { ptDSCDSCCandidateOutgoingADNTable 1 }

PtDSCDSCCandidateOutgoingADNEntry ::=
    SEQUENCE {
        ptDSCDSCCandidateOutgoingADNOrder Integer32,
        ptDSCDSCCandidateOutgoingADNCandidateADNName            DisplayString,
        ptDSCDSCCandidateOutgoingADNCandidateStatus           INTEGER,
        ptDSCDSCCandidateOutgoingADNDSCIndex    Integer32,
        ptDSCDSCCandidateOutgoingADNDSCRoutingTablesIndex                 Integer32,
        ptDSCDSCCandidateOutgoingADNDSCRoutingSearchUtilityIndex                        Integer32,
        ptDSCDSCCandidateOutgoingADNParentOID     OBJECT IDENTIFIER,
        ptDSCDSCCandidateOutgoingADNRowStatus     RowStatus,
        ptDSCDSCCandidateOutgoingADNIndex Integer32
    }

ptDSCDSCCandidateOutgoingADNOrder OBJECT-TYPE
    SYNTAX          Integer32 (-2147483648..2147483647)
    MAX-ACCESS      read-only
    STATUS          current
    DESCRIPTION     
            "the candidate ADN order where the DSC will try to send out the message. The smaller the order number, the early the DSC will try to send the message on that ADN."
    ::= { ptDSCDSCCandidateOutgoingADNEntry 1 }

ptDSCDSCCandidateOutgoingADNCandidateADNName OBJECT-TYPE
    SYNTAX          DisplayString (SIZE(0..255))
    MAX-ACCESS      read-only
    STATUS          current
    DESCRIPTION     
            "the candidate outgoing ADN Name where the test message will be routed to."
    ::= { ptDSCDSCCandidateOutgoingADNEntry 2 }

ptDSCDSCCandidateOutgoingADNCandidateStatus OBJECT-TYPE
    SYNTAX          INTEGER { unavailable(0), previouslyUsed(1), 
                        noApplicationId(2), available(3) }
    MAX-ACCESS      read-only
    STATUS          current
    DESCRIPTION     
            "the candidate ADN Status (UNAVAILABLE, PREVIOUSLY USED, NO APPLICATION ID, AVAILABLE). The UNAVAILABLE status ADN will be displayed only if it is from a Result table record and will NOT be seen from other routing mechanisms."
    ::= { ptDSCDSCCandidateOutgoingADNEntry 3 }

ptDSCDSCCandidateOutgoingADNDSCIndex OBJECT-TYPE
    SYNTAX          Integer32 (-2147483648..2147483647)
    MAX-ACCESS      not-accessible
    STATUS          current
    DESCRIPTION     
            "This is the index of the parent type for this object.
             This parent type is DSC."
    ::= { ptDSCDSCCandidateOutgoingADNEntry 242 }

ptDSCDSCCandidateOutgoingADNDSCRoutingTablesIndex OBJECT-TYPE
    SYNTAX          Integer32 (-2147483648..2147483647)
    MAX-ACCESS      not-accessible
    STATUS          current
    DESCRIPTION     
            "This is the index of the parent type for this object.
             This parent type is DSCRoutingTables."
    ::= { ptDSCDSCCandidateOutgoingADNEntry 243 }

ptDSCDSCCandidateOutgoingADNDSCRoutingSearchUtilityIndex OBJECT-TYPE
    SYNTAX          Integer32 (-2147483648..2147483647)
    MAX-ACCESS      not-accessible
    STATUS          current
    DESCRIPTION     
            "This is the index of the parent type for this object.
             This parent type is DSCRoutingSearchUtility."
    ::= { ptDSCDSCCandidateOutgoingADNEntry 244 }

ptDSCDSCCandidateOutgoingADNParentOID OBJECT-TYPE
    SYNTAX          OBJECT IDENTIFIER
    MAX-ACCESS      read-create
    STATUS          current
    DESCRIPTION     
            "The OID of the parent object for this instance"
    ::= { ptDSCDSCCandidateOutgoingADNEntry 253 }

ptDSCDSCCandidateOutgoingADNRowStatus OBJECT-TYPE
    SYNTAX          RowStatus
    MAX-ACCESS      read-create
    STATUS          current
    DESCRIPTION     
            "The row status for the DSCDSCCandidateOutgoingADN table"
    ::= { ptDSCDSCCandidateOutgoingADNEntry 254 }

ptDSCDSCCandidateOutgoingADNIndex OBJECT-TYPE
    SYNTAX          Integer32 (-2147483648..2147483647)
    MAX-ACCESS      not-accessible
    STATUS          current
    DESCRIPTION     
            "The row number for the DSCDSCCandidateOutgoingADN table"
    ::= { ptDSCDSCCandidateOutgoingADNEntry 255 }

ptDSCDSCParameterSets OBJECT IDENTIFIER
    ::= { ptDSCDSC 1804 }

ptDSCDSCParameterSetsTable OBJECT-TYPE
    SYNTAX          SEQUENCE OF PtDSCDSCParameterSetsEntry
    MAX-ACCESS      not-accessible
    STATUS          current
    DESCRIPTION     
            "No description supplied in the proxy config file."
    ::= { ptDSCDSCParameterSets 1 }

ptDSCDSCParameterSetsEntry OBJECT-TYPE
    SYNTAX          PtDSCDSCParameterSetsEntry
    MAX-ACCESS      not-accessible
    STATUS          current
    DESCRIPTION     
            "A sequence of DSCDSCParameterSets attributes."
    INDEX           { ptConnGroupIndex, ptDSCDSCParameterSetsDSCIndex, 
                      ptDSCDSCParameterSetsIndex }
    ::= { ptDSCDSCParameterSetsTable 1 }

PtDSCDSCParameterSetsEntry ::=
    SEQUENCE {
        ptDSCDSCParameterSetsDSCIndex   Integer32,
        ptDSCDSCParameterSetsParentOID  OBJECT IDENTIFIER,
        ptDSCDSCParameterSetsRowStatus  RowStatus,
        ptDSCDSCParameterSetsIndex      Integer32
    }

ptDSCDSCParameterSetsDSCIndex OBJECT-TYPE
    SYNTAX          Integer32 (-2147483648..2147483647)
    MAX-ACCESS      not-accessible
    STATUS          current
    DESCRIPTION     
            "This is the index of the parent type for this object.
             This parent type is DSC."
    ::= { ptDSCDSCParameterSetsEntry 242 }

ptDSCDSCParameterSetsParentOID OBJECT-TYPE
    SYNTAX          OBJECT IDENTIFIER
    MAX-ACCESS      read-create
    STATUS          current
    DESCRIPTION     
            "The OID of the parent object for this instance"
    ::= { ptDSCDSCParameterSetsEntry 253 }

ptDSCDSCParameterSetsRowStatus OBJECT-TYPE
    SYNTAX          RowStatus
    MAX-ACCESS      read-create
    STATUS          current
    DESCRIPTION     
            "The row status for the DSCDSCParameterSets table"
    ::= { ptDSCDSCParameterSetsEntry 254 }

ptDSCDSCParameterSetsIndex OBJECT-TYPE
    SYNTAX          Integer32 (-2147483648..2147483647)
    MAX-ACCESS      not-accessible
    STATUS          current
    DESCRIPTION     
            "The row number for the DSCDSCParameterSets table"
    ::= { ptDSCDSCParameterSetsEntry 255 }

ptDSCSCTPParameterSet OBJECT IDENTIFIER
    ::= { ptDSCDSCParameterSets 1818 }

ptDSCSCTPParameterSetTable OBJECT-TYPE
    SYNTAX          SEQUENCE OF PtDSCSCTPParameterSetEntry
    MAX-ACCESS      not-accessible
    STATUS          current
    DESCRIPTION     
            "No description supplied in the proxy config file."
    ::= { ptDSCSCTPParameterSet 1 }

ptDSCSCTPParameterSetEntry OBJECT-TYPE
    SYNTAX          PtDSCSCTPParameterSetEntry
    MAX-ACCESS      not-accessible
    STATUS          current
    DESCRIPTION     
            "A sequence of DSCSCTPParameterSet attributes."
    INDEX           { ptConnGroupIndex, ptDSCSCTPParameterSetDSCIndex, 
                      ptDSCSCTPParameterSetDSCParameterSetsIndex, 
                      ptDSCSCTPParameterSetIndex }
    ::= { ptDSCSCTPParameterSetTable 1 }

PtDSCSCTPParameterSetEntry ::=
    SEQUENCE {
        ptDSCSCTPParameterSetName       DisplayString,
        ptDSCSCTPParameterSetRTOInitial Integer32,
        ptDSCSCTPParameterSetRTOMinimum Integer32,
        ptDSCSCTPParameterSetRTOMaximum Integer32,
        ptDSCSCTPParameterSetMaximumPathRetrans       Integer32,
        ptDSCSCTPParameterSetMaximumAssocRetrans        Integer32,
        ptDSCSCTPParameterSetHeartbeat  INTEGER,
        ptDSCSCTPParameterSetBundling   INTEGER,
        ptDSCSCTPParameterSetHeartbeatInterval      Integer32,
        ptDSCSCTPParameterSetDelayedACKTO INTEGER,
        ptDSCSCTPParameterSetDSCP       Integer32,
        ptDSCSCTPParameterSetInternalID Integer32,
        ptDSCSCTPParameterSetDSCIndex   Integer32,
        ptDSCSCTPParameterSetDSCParameterSetsIndex          Integer32,
        ptDSCSCTPParameterSetParentOID  OBJECT IDENTIFIER,
        ptDSCSCTPParameterSetRowStatus  RowStatus,
        ptDSCSCTPParameterSetIndex      Integer32
    }

ptDSCSCTPParameterSetName OBJECT-TYPE
    SYNTAX          DisplayString (SIZE(0..255))
    MAX-ACCESS      read-only
    STATUS          current
    DESCRIPTION     
            "Name to uniquely identify the Parameter Set. \nLeading and trailing whitespaces are trimmed. \nValid values: alphanumeric characters, dashes, underscores, spaces, and dots (maximum size of 64)."
    ::= { ptDSCSCTPParameterSetEntry 1 }

ptDSCSCTPParameterSetRTOInitial OBJECT-TYPE
    SYNTAX          Integer32 (0..2147483647)
    MAX-ACCESS      read-create
    STATUS          current
    DESCRIPTION     
            "Retransmission Timeout (RTO) Initial sets the initial expected time for packets to be sent and returned (0 to + ms). \nMust be greater than or equal to the RTO Minimum and less than or equal to the RTO Maximum. \nDefault value: 2000 ms."
    ::= { ptDSCSCTPParameterSetEntry 2 }

ptDSCSCTPParameterSetRTOMinimum OBJECT-TYPE
    SYNTAX          Integer32 (0..2147483647)
    MAX-ACCESS      read-create
    STATUS          current
    DESCRIPTION     
            "Retransmission Timeout (RTO) Minimum is the smallest expected time for packets to be sent and returned (0 to + ms). \nDefault value: 60 ms."
    ::= { ptDSCSCTPParameterSetEntry 3 }

ptDSCSCTPParameterSetRTOMaximum OBJECT-TYPE
    SYNTAX          Integer32 (0..2147483647)
    MAX-ACCESS      read-create
    STATUS          current
    DESCRIPTION     
            "Retransmission Timeout (RTO) Maximum is the largest expected time for packets to be sent and returned (0 to + ms). \nDefault value: 2000 ms."
    ::= { ptDSCSCTPParameterSetEntry 4 }

ptDSCSCTPParameterSetMaximumPathRetrans OBJECT-TYPE
    SYNTAX          Integer32 (0..2147483647)
    MAX-ACCESS      read-create
    STATUS          current
    DESCRIPTION     
            "Maximum Path Retransmissions sets the number of retransmissions that will be attempted over the current transmission path without success before the path is deemed unavailable and a new transmission path is sought. \nValid values: 0 to +. \nDefault value: 4 (tailored for a single-homed association)."
    ::= { ptDSCSCTPParameterSetEntry 5 }

ptDSCSCTPParameterSetMaximumAssocRetrans OBJECT-TYPE
    SYNTAX          Integer32 (0..2147483647)
    MAX-ACCESS      read-create
    STATUS          current
    DESCRIPTION     
            "Maximum Association Retransmissions sets the number of retransmissions to a remote device over all possible paths that will be attempted without success before deeming the end device as unavailable. \nValid values: 0 to +. \nDefault value: 4 (tailored for a single-homed association)."
    ::= { ptDSCSCTPParameterSetEntry 6 }

ptDSCSCTPParameterSetHeartbeat OBJECT-TYPE
    SYNTAX          INTEGER { disabled(0), enabled(1) }
    MAX-ACCESS      read-create
    STATUS          current
    DESCRIPTION     
            "Heartbeat feature (DISABLED/ENABLED). \nEnabling the Heartbeat feature triggers the sending of cyclical test messages on the connection to determine its availability on the network. \nDefault value: ENABLED."
    ::= { ptDSCSCTPParameterSetEntry 8 }

ptDSCSCTPParameterSetBundling OBJECT-TYPE
    SYNTAX          INTEGER { disabled(0), enabled(1) }
    MAX-ACCESS      read-create
    STATUS          current
    DESCRIPTION     
            "Bundling feature (DISABLED/ENABLED). \nEnabling Bundling allows the bundling of messages into larger packets for greater line efficiency. \nDefault value: ENABLED."
    ::= { ptDSCSCTPParameterSetEntry 9 }

ptDSCSCTPParameterSetHeartbeatInterval OBJECT-TYPE
    SYNTAX          Integer32 (0..65535)
    MAX-ACCESS      read-create
    STATUS          current
    DESCRIPTION     
            "Heartbeat Interval for the SCTP association (0 to 65535 ms). \nDefault value: 150 ms."
    ::= { ptDSCSCTPParameterSetEntry 10 }

ptDSCSCTPParameterSetDelayedACKTO OBJECT-TYPE
    SYNTAX          INTEGER { disabled(0) }
    MAX-ACCESS      read-create
    STATUS          current
    DESCRIPTION     
            "Delayed Acknowledgement Time Out (ACK TO) sets the time that the system waits after receiving a packet before sending an acknowledgement (10 to 500 ms). \nTo disable the Delayed ACK feature, set the value to 0. \nDefault value: 20 ms."
    ::= { ptDSCSCTPParameterSetEntry 11 }

ptDSCSCTPParameterSetDSCP OBJECT-TYPE
    SYNTAX          Integer32 (-2147483648..2147483647)
    MAX-ACCESS      read-create
    STATUS          current
    DESCRIPTION     
            "Differentiated Services Code Point is used to classify traffic within a network in order to determine the priority of the various classes of traffic (0 to 63). \nDefault value: 0."
    ::= { ptDSCSCTPParameterSetEntry 15 }

ptDSCSCTPParameterSetInternalID OBJECT-TYPE
    SYNTAX          Integer32 (-2147483648..2147483647)
    MAX-ACCESS      read-only
    STATUS          current
    DESCRIPTION     
            "Parameter set unique internal ID. \nReserved for internal use."
    ::= { ptDSCSCTPParameterSetEntry 99 }

ptDSCSCTPParameterSetDSCIndex OBJECT-TYPE
    SYNTAX          Integer32 (-2147483648..2147483647)
    MAX-ACCESS      not-accessible
    STATUS          current
    DESCRIPTION     
            "This is the index of the parent type for this object.
             This parent type is DSC."
    ::= { ptDSCSCTPParameterSetEntry 242 }

ptDSCSCTPParameterSetDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCSCTPParameterSetEntry 243 }

ptDSCSCTPParameterSetParentOID OBJECT-TYPE
    SYNTAX          OBJECT IDENTIFIER
    MAX-ACCESS      read-create
    STATUS          current
    DESCRIPTION     
            "The OID of the parent object for this instance"
    ::= { ptDSCSCTPParameterSetEntry 253 }

ptDSCSCTPParameterSetRowStatus OBJECT-TYPE
    SYNTAX          RowStatus
    MAX-ACCESS      read-create
    STATUS          current
    DESCRIPTION     
            "The row status for the DSCSCTPParameterSet table"
    ::= { ptDSCSCTPParameterSetEntry 254 }

ptDSCSCTPParameterSetIndex OBJECT-TYPE
    SYNTAX          Integer32 (-2147483648..2147483647)
    MAX-ACCESS      not-accessible
    STATUS          current
    DESCRIPTION     
            "The row number for the DSCSCTPParameterSet table"
    ::= { ptDSCSCTPParameterSetEntry 255 }

ptDSCCERParameterSet OBJECT IDENTIFIER
    ::= { ptDSCDSCParameterSets 1819 }

ptDSCCERParameterSetTable OBJECT-TYPE
    SYNTAX          SEQUENCE OF PtDSCCERParameterSetEntry
    MAX-ACCESS      not-accessible
    STATUS          current
    DESCRIPTION     
            "No description supplied in the proxy config file."
    ::= { ptDSCCERParameterSet 1 }

ptDSCCERParameterSetEntry OBJECT-TYPE
    SYNTAX          PtDSCCERParameterSetEntry
    MAX-ACCESS      not-accessible
    STATUS          current
    DESCRIPTION     
            "A sequence of DSCCERParameterSet attributes."
    INDEX           { ptConnGroupIndex, ptDSCCERParameterSetDSCIndex, 
                      ptDSCCERParameterSetDSCParameterSetsIndex, 
                      ptDSCCERParameterSetIndex }
    ::= { ptDSCCERParameterSetTable 1 }

PtDSCCERParameterSetEntry ::=
    SEQUENCE {
        ptDSCCERParameterSetName        DisplayString,
        ptDSCCERParameterSetLocalDiameterIDOverride           DisplayString,
        ptDSCCERParameterSetInternalID  Integer32,
        ptDSCCERParameterSetDSCIndex    Integer32,
        ptDSCCERParameterSetDSCParameterSetsIndex         Integer32,
        ptDSCCERParameterSetParentOID   OBJECT IDENTIFIER,
        ptDSCCERParameterSetRowStatus   RowStatus,
        ptDSCCERParameterSetIndex       Integer32
    }

ptDSCCERParameterSetName OBJECT-TYPE
    SYNTAX          DisplayString (SIZE(0..255))
    MAX-ACCESS      read-only
    STATUS          current
    DESCRIPTION     
            "Name to uniquely identify the Parameter Set. \nLeading and trailing whitespaces are trimmed. \nValid values: alphanumeric characters, dashes, underscores, spaces, and dots (maximum size of 64)."
    ::= { ptDSCCERParameterSetEntry 1 }

ptDSCCERParameterSetLocalDiameterIDOverride OBJECT-TYPE
    SYNTAX          DisplayString (SIZE(0..255))
    MAX-ACCESS      read-create
    STATUS          current
    DESCRIPTION     
            "Override the local Diameter ID of the DSC Node when sending CE[A/R] messages, resolving elections, etc. \nIf empty string, use the local Diameter ID of the DSC Node. \nValid values: FQDN format or empty string. \nDefault value: empty string."
    ::= { ptDSCCERParameterSetEntry 2 }

ptDSCCERParameterSetInternalID OBJECT-TYPE
    SYNTAX          Integer32 (-2147483648..2147483647)
    MAX-ACCESS      read-only
    STATUS          current
    DESCRIPTION     
            "Parameter set unique internal ID. \nReserved for internal use."
    ::= { ptDSCCERParameterSetEntry 99 }

ptDSCCERParameterSetDSCIndex OBJECT-TYPE
    SYNTAX          Integer32 (-2147483648..2147483647)
    MAX-ACCESS      not-accessible
    STATUS          current
    DESCRIPTION     
            "This is the index of the parent type for this object.
             This parent type is DSC."
    ::= { ptDSCCERParameterSetEntry 242 }

ptDSCCERParameterSetDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCCERParameterSetEntry 243 }

ptDSCCERParameterSetParentOID OBJECT-TYPE
    SYNTAX          OBJECT IDENTIFIER
    MAX-ACCESS      read-create
    STATUS          current
    DESCRIPTION     
            "The OID of the parent object for this instance"
    ::= { ptDSCCERParameterSetEntry 253 }

ptDSCCERParameterSetRowStatus OBJECT-TYPE
    SYNTAX          RowStatus
    MAX-ACCESS      read-create
    STATUS          current
    DESCRIPTION     
            "The row status for the DSCCERParameterSet table"
    ::= { ptDSCCERParameterSetEntry 254 }

ptDSCCERParameterSetIndex OBJECT-TYPE
    SYNTAX          Integer32 (-2147483648..2147483647)
    MAX-ACCESS      not-accessible
    STATUS          current
    DESCRIPTION     
            "The row number for the DSCCERParameterSet table"
    ::= { ptDSCCERParameterSetEntry 255 }

ptDSCCERApplicationID OBJECT IDENTIFIER
    ::= { ptDSCCERParameterSet 1821 }

ptDSCCERApplicationIDTable OBJECT-TYPE
    SYNTAX          SEQUENCE OF PtDSCCERApplicationIDEntry
    MAX-ACCESS      not-accessible
    STATUS          current
    DESCRIPTION     
            "No description supplied in the proxy config file."
    ::= { ptDSCCERApplicationID 1 }

ptDSCCERApplicationIDEntry OBJECT-TYPE
    SYNTAX          PtDSCCERApplicationIDEntry
    MAX-ACCESS      not-accessible
    STATUS          current
    DESCRIPTION     
            "A sequence of DSCCERApplicationID attributes."
    INDEX           { ptConnGroupIndex, ptDSCCERApplicationIDDSCIndex, 
                      ptDSCCERApplicationIDDSCParameterSetsIndex, 
                      ptDSCCERApplicationIDCERParameterSetIndex, 
                      ptDSCCERApplicationIDIndex }
    ::= { ptDSCCERApplicationIDTable 1 }

PtDSCCERApplicationIDEntry ::=
    SEQUENCE {
        ptDSCCERApplicationIDApplicationID  DisplayString,
        ptDSCCERApplicationIDVendorID   DisplayString,
        ptDSCCERApplicationIDInternalID Integer32,
        ptDSCCERApplicationIDDSCIndex   Integer32,
        ptDSCCERApplicationIDDSCParameterSetsIndex          Integer32,
        ptDSCCERApplicationIDCERParameterSetIndex         Integer32,
        ptDSCCERApplicationIDParentOID  OBJECT IDENTIFIER,
        ptDSCCERApplicationIDRowStatus  RowStatus,
        ptDSCCERApplicationIDIndex      Integer32
    }

ptDSCCERApplicationIDApplicationID OBJECT-TYPE
    SYNTAX          DisplayString (SIZE(0..255))
    MAX-ACCESS      read-only
    STATUS          current
    DESCRIPTION     
            "Application ID for transmit in CE messages. \nValid values: existing Application ID definition name."
    ::= { ptDSCCERApplicationIDEntry 1 }

ptDSCCERApplicationIDVendorID OBJECT-TYPE
    SYNTAX          DisplayString (SIZE(0..255))
    MAX-ACCESS      read-only
    STATUS          current
    DESCRIPTION     
            "Vendor ID - if not Diameter, Vendor-Specific-Application-Id AVP is added to CE. \nAn empty string is assumed to be Diameter which will include the non-vendor specific Auth-Application-Id AVP. \nValid values: existing Vendor ID definition name or empty string."
    ::= { ptDSCCERApplicationIDEntry 2 }

ptDSCCERApplicationIDInternalID OBJECT-TYPE
    SYNTAX          Integer32 (-2147483648..2147483647)
    MAX-ACCESS      read-only
    STATUS          current
    DESCRIPTION     
            "CER Application ID unique internal ID. \nReserved for internal use."
    ::= { ptDSCCERApplicationIDEntry 99 }

ptDSCCERApplicationIDDSCIndex OBJECT-TYPE
    SYNTAX          Integer32 (-2147483648..2147483647)
    MAX-ACCESS      not-accessible
    STATUS          current
    DESCRIPTION     
            "This is the index of the parent type for this object.
             This parent type is DSC."
    ::= { ptDSCCERApplicationIDEntry 242 }

ptDSCCERApplicationIDDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCCERApplicationIDEntry 243 }

ptDSCCERApplicationIDCERParameterSetIndex OBJECT-TYPE
    SYNTAX          Integer32 (-2147483648..2147483647)
    MAX-ACCESS      not-accessible
    STATUS          current
    DESCRIPTION     
            "This is the index of the parent type for this object.
             This parent type is CERParameterSet."
    ::= { ptDSCCERApplicationIDEntry 244 }

ptDSCCERApplicationIDParentOID OBJECT-TYPE
    SYNTAX          OBJECT IDENTIFIER
    MAX-ACCESS      read-create
    STATUS          current
    DESCRIPTION     
            "The OID of the parent object for this instance"
    ::= { ptDSCCERApplicationIDEntry 253 }

ptDSCCERApplicationIDRowStatus OBJECT-TYPE
    SYNTAX          RowStatus
    MAX-ACCESS      read-create
    STATUS          current
    DESCRIPTION     
            "The row status for the DSCCERApplicationID table"
    ::= { ptDSCCERApplicationIDEntry 254 }

ptDSCCERApplicationIDIndex OBJECT-TYPE
    SYNTAX          Integer32 (-2147483648..2147483647)
    MAX-ACCESS      not-accessible
    STATUS          current
    DESCRIPTION     
            "The row number for the DSCCERApplicationID table"
    ::= { ptDSCCERApplicationIDEntry 255 }

ptDSCCERSupportedVendorID OBJECT IDENTIFIER
    ::= { ptDSCCERParameterSet 1853 }

ptDSCCERSupportedVendorIDTable OBJECT-TYPE
    SYNTAX          SEQUENCE OF PtDSCCERSupportedVendorIDEntry
    MAX-ACCESS      not-accessible
    STATUS          current
    DESCRIPTION     
            "No description supplied in the proxy config file."
    ::= { ptDSCCERSupportedVendorID 1 }

ptDSCCERSupportedVendorIDEntry OBJECT-TYPE
    SYNTAX          PtDSCCERSupportedVendorIDEntry
    MAX-ACCESS      not-accessible
    STATUS          current
    DESCRIPTION     
            "A sequence of DSCCERSupportedVendorID attributes."
    INDEX           { ptConnGroupIndex, 
                      ptDSCCERSupportedVendorIDDSCIndex, 
                      ptDSCCERSupportedVendorIDDSCParameterSetsIndex, 
                      ptDSCCERSupportedVendorIDCERParameterSetIndex, 
                      ptDSCCERSupportedVendorIDIndex }
    ::= { ptDSCCERSupportedVendorIDTable 1 }

PtDSCCERSupportedVendorIDEntry ::=
    SEQUENCE {
        ptDSCCERSupportedVendorIDVendorID DisplayString,
        ptDSCCERSupportedVendorIDInternalID   Integer32,
        ptDSCCERSupportedVendorIDDSCIndex Integer32,
        ptDSCCERSupportedVendorIDDSCParameterSetsIndex              Integer32,
        ptDSCCERSupportedVendorIDCERParameterSetIndex             Integer32,
        ptDSCCERSupportedVendorIDParentOID  OBJECT IDENTIFIER,
        ptDSCCERSupportedVendorIDRowStatus  RowStatus,
        ptDSCCERSupportedVendorIDIndex  Integer32
    }

ptDSCCERSupportedVendorIDVendorID OBJECT-TYPE
    SYNTAX          DisplayString (SIZE(0..255))
    MAX-ACCESS      read-only
    STATUS          current
    DESCRIPTION     
            "Vendor ID - Supported-Vendor-Id AVP is added to CE. \nValid values: existing Vendor ID definition name."
    ::= { ptDSCCERSupportedVendorIDEntry 4 }

ptDSCCERSupportedVendorIDInternalID OBJECT-TYPE
    SYNTAX          Integer32 (-2147483648..2147483647)
    MAX-ACCESS      read-only
    STATUS          current
    DESCRIPTION     
            "CER Supported Vendor ID unique internal ID. \nReserved for internal use."
    ::= { ptDSCCERSupportedVendorIDEntry 99 }

ptDSCCERSupportedVendorIDDSCIndex OBJECT-TYPE
    SYNTAX          Integer32 (-2147483648..2147483647)
    MAX-ACCESS      not-accessible
    STATUS          current
    DESCRIPTION     
            "This is the index of the parent type for this object.
             This parent type is DSC."
    ::= { ptDSCCERSupportedVendorIDEntry 242 }

ptDSCCERSupportedVendorIDDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCCERSupportedVendorIDEntry 243 }

ptDSCCERSupportedVendorIDCERParameterSetIndex OBJECT-TYPE
    SYNTAX          Integer32 (-2147483648..2147483647)
    MAX-ACCESS      not-accessible
    STATUS          current
    DESCRIPTION     
            "This is the index of the parent type for this object.
             This parent type is CERParameterSet."
    ::= { ptDSCCERSupportedVendorIDEntry 244 }

ptDSCCERSupportedVendorIDParentOID OBJECT-TYPE
    SYNTAX          OBJECT IDENTIFIER
    MAX-ACCESS      read-create
    STATUS          current
    DESCRIPTION     
            "The OID of the parent object for this instance"
    ::= { ptDSCCERSupportedVendorIDEntry 253 }

ptDSCCERSupportedVendorIDRowStatus OBJECT-TYPE
    SYNTAX          RowStatus
    MAX-ACCESS      read-create
    STATUS          current
    DESCRIPTION     
            "The row status for the DSCCERSupportedVendorID table"
    ::= { ptDSCCERSupportedVendorIDEntry 254 }

ptDSCCERSupportedVendorIDIndex OBJECT-TYPE
    SYNTAX          Integer32 (-2147483648..2147483647)
    MAX-ACCESS      not-accessible
    STATUS          current
    DESCRIPTION     
            "The row number for the DSCCERSupportedVendorID table"
    ::= { ptDSCCERSupportedVendorIDEntry 255 }

ptDSCCapacityParameterSet OBJECT IDENTIFIER
    ::= { ptDSCDSCParameterSets 1822 }

ptDSCCapacityParameterSetTable OBJECT-TYPE
    SYNTAX          SEQUENCE OF PtDSCCapacityParameterSetEntry
    MAX-ACCESS      not-accessible
    STATUS          current
    DESCRIPTION     
            "No description supplied in the proxy config file."
    ::= { ptDSCCapacityParameterSet 1 }

ptDSCCapacityParameterSetEntry OBJECT-TYPE
    SYNTAX          PtDSCCapacityParameterSetEntry
    MAX-ACCESS      not-accessible
    STATUS          current
    DESCRIPTION     
            "A sequence of DSCCapacityParameterSet attributes."
    INDEX           { ptConnGroupIndex, 
                      ptDSCCapacityParameterSetDSCIndex, 
                      ptDSCCapacityParameterSetDSCParameterSetsIndex, 
                      ptDSCCapacityParameterSetIndex }
    ::= { ptDSCCapacityParameterSetTable 1 }

PtDSCCapacityParameterSetEntry ::=
    SEQUENCE {
        ptDSCCapacityParameterSetName   DisplayString,
        ptDSCCapacityParameterSetQueueSizeInSeconds           Integer32,
        ptDSCCapacityParameterSetMessagePerSecondCapacity                 INTEGER,
        ptDSCCapacityParameterSetUsageThreshold1        Integer32,
        ptDSCCapacityParameterSetUsageThreshold2        Integer32,
        ptDSCCapacityParameterSetUsageThreshold3        Integer32,
        ptDSCCapacityParameterSetQueueSizeInMessages            INTEGER,
        ptDSCCapacityParameterSetQueueSizeInKBytes          INTEGER,
        ptDSCCapacityParameterSetCongestionAlarm1         Integer32,
        ptDSCCapacityParameterSetCongestionAbatement1             Integer32,
        ptDSCCapacityParameterSetCongestionOnset1         Integer32,
        ptDSCCapacityParameterSetCongestionAlarm2         Integer32,
        ptDSCCapacityParameterSetCongestionAbatement2             Integer32,
        ptDSCCapacityParameterSetCongestionOnset2         Integer32,
        ptDSCCapacityParameterSetCongestionAlarm3         Integer32,
        ptDSCCapacityParameterSetCongestionAbatement3             Integer32,
        ptDSCCapacityParameterSetCongestionOnset3         Integer32,
        ptDSCCapacityParameterSetCongestionHandling1            DisplayString,
        ptDSCCapacityParameterSetCongestionHandling2            DisplayString,
        ptDSCCapacityParameterSetCongestionHandling3            DisplayString,
        ptDSCCapacityParameterSetOverloadHandling1          DisplayString,
        ptDSCCapacityParameterSetOverloadHandling2          DisplayString,
        ptDSCCapacityParameterSetOverloadHandling3          DisplayString,
        ptDSCCapacityParameterSetInternalID   Integer32,
        ptDSCCapacityParameterSetDSCIndex Integer32,
        ptDSCCapacityParameterSetDSCParameterSetsIndex              Integer32,
        ptDSCCapacityParameterSetParentOID  OBJECT IDENTIFIER,
        ptDSCCapacityParameterSetRowStatus  RowStatus,
        ptDSCCapacityParameterSetIndex  Integer32
    }

ptDSCCapacityParameterSetName OBJECT-TYPE
    SYNTAX          DisplayString (SIZE(0..255))
    MAX-ACCESS      read-only
    STATUS          current
    DESCRIPTION     
            "Name to uniquely identify the Parameter Set. \nLeading and trailing whitespaces are trimmed. \nValid values: alphanumeric characters, dashes, underscores, spaces, and dots (maximum size of 64)."
    ::= { ptDSCCapacityParameterSetEntry 1 }

ptDSCCapacityParameterSetQueueSizeInSeconds OBJECT-TYPE
    SYNTAX          Integer32 (5..60)
    MAX-ACCESS      read-create
    STATUS          current
    DESCRIPTION     
            "Queue Size in Seconds for oldest message in queue (5 to 60). \The queue is considered full when the oldest message in the queue is older than the queue size. Other congestion levels occur at fractions of this age. \nDefault value: 10."
    ::= { ptDSCCapacityParameterSetEntry 2 }

ptDSCCapacityParameterSetMessagePerSecondCapacity OBJECT-TYPE
    SYNTAX          INTEGER { unlimited(-1) }
    MAX-ACCESS      read-create
    STATUS          current
    DESCRIPTION     
            "Message per second capacity is the maximum processing rate for the associated Diameter node (100 to UNLIMITED). \nDefault value: UNLIMITED."
    ::= { ptDSCCapacityParameterSetEntry 3 }

ptDSCCapacityParameterSetUsageThreshold1 OBJECT-TYPE
    SYNTAX          Integer32
    MAX-ACCESS      read-create
    STATUS          current
    DESCRIPTION     
            "Percentage of Message Per Second Capacity used for usage alarms (0 to 100%). \nNote that thresholds cannot overlap. Threshold 1 must be less than threshold 2 and threshold 2 must be less than threshold 3. \nDefault value: 35% (if the mate fails, the node will be at 70% capacity)."
    ::= { ptDSCCapacityParameterSetEntry 4 }

ptDSCCapacityParameterSetUsageThreshold2 OBJECT-TYPE
    SYNTAX          Integer32
    MAX-ACCESS      read-create
    STATUS          current
    DESCRIPTION     
            "Percentage of Message Per Second Capacity used for usage alarms (0 to 100%). \nNote that thresholds cannot overlap. Threshold 1 must be less than threshold 2 and threshold 2 must be less than threshold 3. \nDefault value: 45% (if the mate fails, the node will be at 90% capacity)."
    ::= { ptDSCCapacityParameterSetEntry 5 }

ptDSCCapacityParameterSetUsageThreshold3 OBJECT-TYPE
    SYNTAX          Integer32
    MAX-ACCESS      read-create
    STATUS          current
    DESCRIPTION     
            "Percentage of Message Per Second Capacity used for usage alarms (0 to 100%). \nNote that thresholds cannot overlap. Threshold 1 must be less than threshold 2 and threshold 2 must be less than threshold 3. \nDefault value: 90% (the node is very close to capacity)."
    ::= { ptDSCCapacityParameterSetEntry 6 }

ptDSCCapacityParameterSetQueueSizeInMessages OBJECT-TYPE
    SYNTAX          INTEGER { unlimited(-1) }
    MAX-ACCESS      read-create
    STATUS          current
    DESCRIPTION     
            "Queue Size in Messages, set to UNLIMITED to disable (100 to UNLIMITED). \nNote that if flow control limits the number of messages per second, then messages may take [Message Queue Size divided by Message per Second] seconds to get through the queue. If the 'Queue Size in Seconds' attribute is lower than this computed value, then this attribute will be irrelevant. \nDefault value: UNLIMITED."
    ::= { ptDSCCapacityParameterSetEntry 7 }

ptDSCCapacityParameterSetQueueSizeInKBytes OBJECT-TYPE
    SYNTAX          INTEGER { unlimited(-1) }
    MAX-ACCESS      read-create
    STATUS          current
    DESCRIPTION     
            "Queue Size in KiloBytes (70 to UNLIMITED). \nSet to UNLIMITED to disable. \nDefault value: UNLIMITED."
    ::= { ptDSCCapacityParameterSetEntry 8 }

ptDSCCapacityParameterSetCongestionAlarm1 OBJECT-TYPE
    SYNTAX          Integer32
    MAX-ACCESS      read-create
    STATUS          current
    DESCRIPTION     
            "Percentage of the queue size to raise the congestion level 1 alarm (0 to 100%). \nMust be less than or equal to 'Congestion Abatement 1' and less than 'Congestion Alarm 2'. \nDefault value: 30%."
    ::= { ptDSCCapacityParameterSetEntry 9 }

ptDSCCapacityParameterSetCongestionAbatement1 OBJECT-TYPE
    SYNTAX          Integer32
    MAX-ACCESS      read-create
    STATUS          current
    DESCRIPTION     
            "Percentage of the queue size to leave congestion level 1 (0 to 100%). \nMust be less than 'Congestion Onset 1' and 'Congestion Abatement 2'. \nDefault value: 30%."
    ::= { ptDSCCapacityParameterSetEntry 10 }

ptDSCCapacityParameterSetCongestionOnset1 OBJECT-TYPE
    SYNTAX          Integer32
    MAX-ACCESS      read-create
    STATUS          current
    DESCRIPTION     
            "Percentage of the queue size to enter congestion level 1 (0 to 100%). \nMessages with importance 0 are discarded. \nMust be less than Congestion Abatement 2. \nDefault value: 40%."
    ::= { ptDSCCapacityParameterSetEntry 11 }

ptDSCCapacityParameterSetCongestionAlarm2 OBJECT-TYPE
    SYNTAX          Integer32
    MAX-ACCESS      read-create
    STATUS          current
    DESCRIPTION     
            "Percentage of the queue size to raise the congestion level 2 alarm (0 to 100%). \nMust be less than or equal to 'Congestion Abatement 2' and less than 'Congestion Alarm 3'. \nDefault value: 40%."
    ::= { ptDSCCapacityParameterSetEntry 12 }

ptDSCCapacityParameterSetCongestionAbatement2 OBJECT-TYPE
    SYNTAX          Integer32
    MAX-ACCESS      read-create
    STATUS          current
    DESCRIPTION     
            "Percentage of the queue size to leave congestion level 2 (0 to 100%). \nMust be less than 'Congestion Onset 2' and 'Congestion Abatement 3'. \nDefault value: 50%."
    ::= { ptDSCCapacityParameterSetEntry 13 }

ptDSCCapacityParameterSetCongestionOnset2 OBJECT-TYPE
    SYNTAX          Integer32
    MAX-ACCESS      read-create
    STATUS          current
    DESCRIPTION     
            "Percentage of the queue size to enter congestion level 2 (0 to 100%). \nMessages with an importance of 1 are discarded. \nMust be less than 'Congestion Abatement 3'. \nDefault value: 60%."
    ::= { ptDSCCapacityParameterSetEntry 14 }

ptDSCCapacityParameterSetCongestionAlarm3 OBJECT-TYPE
    SYNTAX          Integer32
    MAX-ACCESS      read-create
    STATUS          current
    DESCRIPTION     
            "Percentage of the queue size to raise the congestion level 3 alarm (0 to 100%). \nMust be less than or equal to 'Congestion Abatement 3'. \nDefault value: 60%."
    ::= { ptDSCCapacityParameterSetEntry 15 }

ptDSCCapacityParameterSetCongestionAbatement3 OBJECT-TYPE
    SYNTAX          Integer32
    MAX-ACCESS      read-create
    STATUS          current
    DESCRIPTION     
            "Percentage of the queue size to leave congestion level 3 (0 to 100%). \nMust be less than 'Congestion Onset 3'. \nDefault value: 70%."
    ::= { ptDSCCapacityParameterSetEntry 16 }

ptDSCCapacityParameterSetCongestionOnset3 OBJECT-TYPE
    SYNTAX          Integer32
    MAX-ACCESS      read-create
    STATUS          current
    DESCRIPTION     
            "Percentage of the queue size to enter congestion level 3 (0 to 100%). \nMessages with an importance of 2 or lower are discarded. \nDefault value: 80%."
    ::= { ptDSCCapacityParameterSetEntry 17 }

ptDSCCapacityParameterSetCongestionHandling1 OBJECT-TYPE
    SYNTAX          DisplayString (SIZE(0..255))
    MAX-ACCESS      read-create
    STATUS          current
    DESCRIPTION     
            "Handling performed on messages of lesser importance at congestion level 1. \nSupported options include: \n1. (empty string, default handling, same as dsc_error) \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the output rate to RATE) \nFor a Capacity Parameter Set associated with an ADN Connection, the handling action will be performed to the message if all paths are congested. The handling action configured for the last path is used."
    ::= { ptDSCCapacityParameterSetEntry 18 }

ptDSCCapacityParameterSetCongestionHandling2 OBJECT-TYPE
    SYNTAX          DisplayString (SIZE(0..255))
    MAX-ACCESS      read-create
    STATUS          current
    DESCRIPTION     
            "Handling performed on messages of lesser importance at congestion level 2. \nSupported options include: \n1. (empty string, default handling, same as dsc_error) \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the output rate to RATE) \nFor a Capacity Parameter Set associated with an ADN Connection, the handling action will be performed to the message if all paths are congested. The handling action configured for the last path is used."
    ::= { ptDSCCapacityParameterSetEntry 19 }

ptDSCCapacityParameterSetCongestionHandling3 OBJECT-TYPE
    SYNTAX          DisplayString (SIZE(0..255))
    MAX-ACCESS      read-create
    STATUS          current
    DESCRIPTION     
            "Handling performed on messages of lesser importance at congestion level 3. \nSupported options include: \n1. (empty string, default handling, same as dsc_error) \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the output rate to RATE) \nFor a Capacity Parameter Set associated with an ADN Connection, the handling action will be performed to the message if all paths are congested. The handling action configured for the last path is used."
    ::= { ptDSCCapacityParameterSetEntry 20 }

ptDSCCapacityParameterSetOverloadHandling1 OBJECT-TYPE
    SYNTAX          DisplayString (SIZE(0..255))
    MAX-ACCESS      read-create
    STATUS          current
    DESCRIPTION     
            "Handling performed on messages of lesser importance at local overload level 1. \nSupported options include: \n1. (empty string, default handling) \n * in the Local Overload Parameters, this is treated the same as dsc_error \n * in ADNConnection or Rate Limiter, the handling is deferred to the Local Overload Parameters \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the ADN input rate or Rate Limiter output rate to RATE) \nFor a Capacity Parameter Set associated with an ADN Connection, the handling action will be performed to the message if all paths are congested. The handling action configured for the last path is used."
    ::= { ptDSCCapacityParameterSetEntry 21 }

ptDSCCapacityParameterSetOverloadHandling2 OBJECT-TYPE
    SYNTAX          DisplayString (SIZE(0..255))
    MAX-ACCESS      read-create
    STATUS          current
    DESCRIPTION     
            "Handling performed on messages of lesser importance at local overload level 2. \nSupported options include: \n1. (empty string, default handling) \n * in the Local Overload Parameters, this is treated the same as dsc_error \n * in ADNConnection or Rate Limiter, the handling is deferred to the Local Overload Parameters \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the ADN input rate or Rate Limiter output rate to RATE) \nFor a Capacity Parameter Set associated with an ADN Connection, the handling action will be performed to the message if all paths are congested. The handling action configured for the last path is used."
    ::= { ptDSCCapacityParameterSetEntry 22 }

ptDSCCapacityParameterSetOverloadHandling3 OBJECT-TYPE
    SYNTAX          DisplayString (SIZE(0..255))
    MAX-ACCESS      read-create
    STATUS          current
    DESCRIPTION     
            "Handling performed on messages of lesser importance at local overload level 3. \nSupported options include: \n1. (empty string, default handling) \n * in the Local Overload Parameters, this is treated the same as dsc_error \n * in ADNConnection or Rate Limiter, the handling is deferred to the Local Overload Parameters \n2. dsc_error MESSAGE (return Result-Code 3002, UNABLE_TO_DELIVER, MESSAGE optional) \n3. dsc_error<error code> MESSAGE (return Result-Code of <error code>, MESSAGE optional) \n4. dsc_error<vendor id>_<error code> MESSAGE (return Experimental-Result with Vendor-Id of <vendor id> and Experimental-Result-Code of <error code>, MESSAGE optional) \n5. dsc_discard (discard requests) \n6. dsc_discard_all (discard requests and answers) \n7. dsc_table ROUTING_TABLE (use indicated routing table to customize an error answer) \n8. dsc_rate_limitRATE (Adjust the ADN input rate or Rate Limiter output rate to RATE) \nFor a Capacity Parameter Set associated with an ADN Connection, the handling action will be performed to the message if all paths are congested. The handling action configured for the last path is used. \nIf this field is a variant of dsc_error, the result code is used to reject messages if the ingress queue is full due to severe local overload."
    ::= { ptDSCCapacityParameterSetEntry 23 }

ptDSCCapacityParameterSetInternalID OBJECT-TYPE
    SYNTAX          Integer32 (-2147483648..2147483647)
    MAX-ACCESS      read-only
    STATUS          current
    DESCRIPTION     
            "Parameter set unique internal ID. \nReserved for internal use."
    ::= { ptDSCCapacityParameterSetEntry 99 }

ptDSCCapacityParameterSetDSCIndex OBJECT-TYPE
    SYNTAX          Integer32 (-2147483648..2147483647)
    MAX-ACCESS      not-accessible
    STATUS          current
    DESCRIPTION     
            "This is the index of the parent type for this object.
             This parent type is DSC."
    ::= { ptDSCCapacityParameterSetEntry 242 }

ptDSCCapacityParameterSetDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCCapacityParameterSetEntry 243 }

ptDSCCapacityParameterSetParentOID OBJECT-TYPE
    SYNTAX          OBJECT IDENTIFIER
    MAX-ACCESS      read-create
    STATUS          current
    DESCRIPTION     
            "The OID of the parent object for this instance"
    ::= { ptDSCCapacityParameterSetEntry 253 }

ptDSCCapacityParameterSetRowStatus OBJECT-TYPE
    SYNTAX          RowStatus
    MAX-ACCESS      read-create
    STATUS          current
    DESCRIPTION     
            "The row status for the DSCCapacityParameterSet table"
    ::= { ptDSCCapacityParameterSetEntry 254 }

ptDSCCapacityParameterSetIndex OBJECT-TYPE
    SYNTAX          Integer32 (-2147483648..2147483647)
    MAX-ACCESS      not-accessible
    STATUS          current
    DESCRIPTION     
            "The row number for the DSCCapacityParameterSet table"
    ::= { ptDSCCapacityParameterSetEntry 255 }

ptDSCSecurityParameterSet OBJECT IDENTIFIER
    ::= { ptDSCDSCParameterSets 1823 }

ptDSCSecurityParameterSetTable OBJECT-TYPE
    SYNTAX          SEQUENCE OF PtDSCSecurityParameterSetEntry
    MAX-ACCESS      not-accessible
    STATUS          current
    DESCRIPTION     
            "No description supplied in the proxy config file."
    ::= { ptDSCSecurityParameterSet 1 }

ptDSCSecurityParameterSetEntry OBJECT-TYPE
    SYNTAX          PtDSCSecurityParameterSetEntry
    MAX-ACCESS      not-accessible
    STATUS          current
    DESCRIPTION     
            "A sequence of DSCSecurityParameterSet attributes."
    INDEX           { ptConnGroupIndex, 
                      ptDSCSecurityParameterSetDSCIndex, 
                      ptDSCSecurityParameterSetDSCParameterSetsIndex, 
                      ptDSCSecurityParameterSetIndex }
    ::= { ptDSCSecurityParameterSetTable 1 }

PtDSCSecurityParameterSetEntry ::=
    SEQUENCE {
        ptDSCSecurityParameterSetName   DisplayString,
        ptDSCSecurityParameterSetSecurityType     INTEGER,
        ptDSCSecurityParameterSetFileSetName    DisplayString,
        ptDSCSecurityParameterSetPriorityString       DisplayString,
        ptDSCSecurityParameterSetInternalID   Integer32,
        ptDSCSecurityParameterSetDSCIndex Integer32,
        ptDSCSecurityParameterSetDSCParameterSetsIndex              Integer32,
        ptDSCSecurityParameterSetParentOID  OBJECT IDENTIFIER,
        ptDSCSecurityParameterSetRowStatus  RowStatus,
        ptDSCSecurityParameterSetIndex  Integer32
    }

ptDSCSecurityParameterSetName OBJECT-TYPE
    SYNTAX          DisplayString (SIZE(0..255))
    MAX-ACCESS      read-only
    STATUS          current
    DESCRIPTION     
            "Name to uniquely identify the Parameter Set. \nLeading and trailing whitespaces are trimmed. \nValid values: alphanumeric characters, dashes, underscores, spaces, and dots (maximum size of 64)."
    ::= { ptDSCSecurityParameterSetEntry 1 }

ptDSCSecurityParameterSetSecurityType OBJECT-TYPE
    SYNTAX          INTEGER { none(0), tls(1), fullTlsDtls(2) }
    MAX-ACCESS      read-create
    STATUS          current
    DESCRIPTION     
            "Security Type (NONE/TLS/FULL TLS DTLS). \nOnly default and plaintext security parameter sets can be set to NONE. \nDefault value: NONE (default and plaintext) \n TLS (else)."
    ::= { ptDSCSecurityParameterSetEntry 2 }

ptDSCSecurityParameterSetFileSetName OBJECT-TYPE
    SYNTAX          DisplayString (SIZE(0..255))
    MAX-ACCESS      read-create
    STATUS          current
    DESCRIPTION     
            "TLS Prefix file names \If the Security Type is NONE, set to empty string. \nUsed in certificate upload. \nValid value: empty string and file name string. \nDefault value: empty string (for default and plaintext Name) \n parameter set name (else)."
    ::= { ptDSCSecurityParameterSetEntry 3 }

ptDSCSecurityParameterSetPriorityString OBJECT-TYPE
    SYNTAX          DisplayString (SIZE(0..255))
    MAX-ACCESS      read-create
    STATUS          current
    DESCRIPTION     
            "TLS Priority String \nIf the Security type is NONE, set to empty string. \nLeave as 'NORMAL' unless there are errors. See documentation. \nValid values: empty string, NORMAL, valid OpenSSL cipher list (separated by :). \nDefault value: empty string (for default and plaintext Name) \n NORMAL (else). \nNote that to counter known security vulnerabilities, RC4 and MD5 algorithms have been disabled by default. \nFurthermore, TLS 1.0 and below have also been disabled by default. \nFor Diameter RFC compliance: \n Add RC4-SHA to enable TLS_RSA_WITH_RC4_128_SHA \n Add RC4-MD5 to enable TLS_RSA_WITH_RC4_128_MD5 \nFor compatibility (for example): \n Add !SHA384 to interwork with a remote peer that \n erroneously reports support for SHA384 ciphers \n Add &TLS10 to allow TLS 1.0"
    ::= { ptDSCSecurityParameterSetEntry 4 }

ptDSCSecurityParameterSetInternalID OBJECT-TYPE
    SYNTAX          Integer32 (-2147483648..2147483647)
    MAX-ACCESS      read-only
    STATUS          current
    DESCRIPTION     
            "Parameter set unique internal ID. \nReserved for internal use."
    ::= { ptDSCSecurityParameterSetEntry 99 }

ptDSCSecurityParameterSetDSCIndex OBJECT-TYPE
    SYNTAX          Integer32 (-2147483648..2147483647)
    MAX-ACCESS      not-accessible
    STATUS          current
    DESCRIPTION     
            "This is the index of the parent type for this object.
             This parent type is DSC."
    ::= { ptDSCSecurityParameterSetEntry 242 }

ptDSCSecurityParameterSetDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCSecurityParameterSetEntry 243 }

ptDSCSecurityParameterSetParentOID OBJECT-TYPE
    SYNTAX          OBJECT IDENTIFIER
    MAX-ACCESS      read-create
    STATUS          current
    DESCRIPTION     
            "The OID of the parent object for this instance"
    ::= { ptDSCSecurityParameterSetEntry 253 }

ptDSCSecurityParameterSetRowStatus OBJECT-TYPE
    SYNTAX          RowStatus
    MAX-ACCESS      read-create
    STATUS          current
    DESCRIPTION     
            "The row status for the DSCSecurityParameterSet table"
    ::= { ptDSCSecurityParameterSetEntry 254 }

ptDSCSecurityParameterSetIndex OBJECT-TYPE
    SYNTAX          Integer32 (-2147483648..2147483647)
    MAX-ACCESS      not-accessible
    STATUS          current
    DESCRIPTION     
            "The row number for the DSCSecurityParameterSet table"
    ::= { ptDSCSecurityParameterSetEntry 255 }

ptDSCDiameterProtocolParameterSet OBJECT IDENTIFIER
    ::= { ptDSCDSCParameterSets 1855 }

ptDSCDiameterProtocolParameterSetTable OBJECT-TYPE
    SYNTAX          SEQUENCE OF PtDSCDiameterProtocolParameterSetEntry
    MAX-ACCESS      not-accessible
    STATUS          current
    DESCRIPTION     
            "No description supplied in the proxy config file."
    ::= { ptDSCDiameterProtocolParameterSet 1 }

ptDSCDiameterProtocolParameterSetEntry OBJECT-TYPE
    SYNTAX          PtDSCDiameterProtocolParameterSetEntry
    MAX-ACCESS      not-accessible
    STATUS          current
    DESCRIPTION     
            "A sequence of DSCDiameterProtocolParameterSet attributes."
    INDEX           { ptConnGroupIndex, 
                      ptDSCDiameterProtocolParameterSetDSCIndex, 
                      ptDSCDiameterProtocolParameterSetDSCParameterSetsIndex, 
                      ptDSCDiameterProtocolParameterSetIndex }
    ::= { ptDSCDiameterProtocolParameterSetTable 1 }

PtDSCDiameterProtocolParameterSetEntry ::=
    SEQUENCE {
        ptDSCDiameterProtocolParameterSetName     DisplayString,
        ptDSCDiameterProtocolParameterSetP2PEndToEndIDValidation                        INTEGER,
        ptDSCDiameterProtocolParameterSetP2PHopByHopIDValidation                        INTEGER,
        ptDSCDiameterProtocolParameterSetP2PPBitValidation                  INTEGER,
        ptDSCDiameterProtocolParameterSetP2PUnexpectedCERValidation                           INTEGER,
        ptDSCDiameterProtocolParameterSetP2PUnexpectedCEAValidation                           INTEGER,
        ptDSCDiameterProtocolParameterSetInternalID           Integer32,
        ptDSCDiameterProtocolParameterSetDSCIndex         Integer32,
        ptDSCDiameterProtocolParameterSetDSCParameterSetsIndex                      Integer32,
        ptDSCDiameterProtocolParameterSetParentOID          OBJECT IDENTIFIER,
        ptDSCDiameterProtocolParameterSetRowStatus          RowStatus,
        ptDSCDiameterProtocolParameterSetIndex      Integer32
    }

ptDSCDiameterProtocolParameterSetName OBJECT-TYPE
    SYNTAX          DisplayString (SIZE(0..255))
    MAX-ACCESS      read-only
    STATUS          current
    DESCRIPTION     
            "Name to uniquely identify the Parameter Set. \nLeading and trailing whitespaces are trimmed. \nValid values: alphanumeric characters, dashes, underscores, spaces, and dots (maximum size of 64)."
    ::= { ptDSCDiameterProtocolParameterSetEntry 1 }

ptDSCDiameterProtocolParameterSetP2PEndToEndIDValidation OBJECT-TYPE
    SYNTAX          INTEGER { ignore(0), enforce(1) }
    MAX-ACCESS      read-create
    STATUS          current
    DESCRIPTION     
            "Point to Point End-to-End ID Validation for CE, and DW messages. RFC6733 states that 'The same End-to-End identifier in the request is used in the answer.'. Choose whether to ENFORCE or IGNORE this rule. \nValid values: IGNORE (0) or ENFORCE (1). \nDefault value: ENFORCE (1)."
    ::= { ptDSCDiameterProtocolParameterSetEntry 2 }

ptDSCDiameterProtocolParameterSetP2PHopByHopIDValidation OBJECT-TYPE
    SYNTAX          INTEGER { ignore(0), enforce(1) }
    MAX-ACCESS      read-create
    STATUS          current
    DESCRIPTION     
            "Point to Point Hop-by-Hop ID Validation for CE, and DW messages. RFC6733 states that 'The same Hop-by-Hop Identifier in the request is used in the answer.'. Choose whether to ENFORCE or IGNORE this rule. \nValid values: IGNORE (0) or ENFORCE (1). \nDefault value: ENFORCE (1)."
    ::= { ptDSCDiameterProtocolParameterSetEntry 3 }

ptDSCDiameterProtocolParameterSetP2PPBitValidation OBJECT-TYPE
    SYNTAX          INTEGER { ignore(0), enforce(1) }
    MAX-ACCESS      read-create
    STATUS          current
    DESCRIPTION     
            "Point to Point P-Bit Validation for CE, and DW messages. RFC6733 states that 'The 'P' bit is set to the same value as the one in the request.' and 'The CER and CEA messages MUST NOT be proxied, redirected, or relayed.'. Choose whether to ENFORCE or IGNORE this rule. \nValid values: IGNORE (0) or ENFORCE (1). \nDefault value: ENFORCE (1)."
    ::= { ptDSCDiameterProtocolParameterSetEntry 4 }

ptDSCDiameterProtocolParameterSetP2PUnexpectedCERValidation OBJECT-TYPE
    SYNTAX          INTEGER { ignore(0), enforce(1) }
    MAX-ACCESS      read-create
    STATUS          current
    DESCRIPTION     
            "Point to Point Unexpected CER Validation. When this rule is enforced, an error message is sent back when an unexpected CER is received. When ignored, the unexpected CER is not processed and a CEA is sent back. Choose whether to ENFORCE or IGNORE this rule. \nValid values: IGNORE (0) or ENFORCE (1). \nDefault value: ENFORCE (1)."
    ::= { ptDSCDiameterProtocolParameterSetEntry 5 }

ptDSCDiameterProtocolParameterSetP2PUnexpectedCEAValidation OBJECT-TYPE
    SYNTAX          INTEGER { ignore(0), enforce(1) }
    MAX-ACCESS      read-create
    STATUS          current
    DESCRIPTION     
            "Point to Point Unexpected CEA Validation. When this rule is enforced, the unexpected CEA is silently discarded. When ignored, the unexpected CEA is processed. Choose whether to ENFORCE or IGNORE this rule. \nValid values: IGNORE (0) or ENFORCE (1). \nDefault value: ENFORCE (1)."
    ::= { ptDSCDiameterProtocolParameterSetEntry 6 }

ptDSCDiameterProtocolParameterSetInternalID OBJECT-TYPE
    SYNTAX          Integer32 (-2147483648..2147483647)
    MAX-ACCESS      read-only
    STATUS          current
    DESCRIPTION     
            "Parameter set unique internal ID. \nReserved for internal use."
    ::= { ptDSCDiameterProtocolParameterSetEntry 99 }

ptDSCDiameterProtocolParameterSetDSCIndex OBJECT-TYPE
    SYNTAX          Integer32 (-2147483648..2147483647)
    MAX-ACCESS      not-accessible
    STATUS          current
    DESCRIPTION     
            "This is the index of the parent type for this object.
             This parent type is DSC."
    ::= { ptDSCDiameterProtocolParameterSetEntry 242 }

ptDSCDiameterProtocolParameterSetDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCDiameterProtocolParameterSetEntry 243 }

ptDSCDiameterProtocolParameterSetParentOID OBJECT-TYPE
    SYNTAX          OBJECT IDENTIFIER
    MAX-ACCESS      read-create
    STATUS          current
    DESCRIPTION     
            "The OID of the parent object for this instance"
    ::= { ptDSCDiameterProtocolParameterSetEntry 253 }

ptDSCDiameterProtocolParameterSetRowStatus OBJECT-TYPE
    SYNTAX          RowStatus
    MAX-ACCESS      read-create
    STATUS          current
    DESCRIPTION     
            "The row status for the DSCDiameterProtocolParameterSet table"
    ::= { ptDSCDiameterProtocolParameterSetEntry 254 }

ptDSCDiameterProtocolParameterSetIndex OBJECT-TYPE
    SYNTAX          Integer32 (-2147483648..2147483647)
    MAX-ACCESS      not-accessible
    STATUS          current
    DESCRIPTION     
            "The row number for the DSCDiameterProtocolParameterSet table"
    ::= { ptDSCDiameterProtocolParameterSetEntry 255 }

ptDSCRateLimiter OBJECT IDENTIFIER
    ::= { ptDSCDSCParameterSets 1856 }

ptDSCRateLimiterTable OBJECT-TYPE
    SYNTAX          SEQUENCE OF PtDSCRateLimiterEntry
    MAX-ACCESS      not-accessible
    STATUS          current
    DESCRIPTION     
            "No description supplied in the proxy config file."
    ::= { ptDSCRateLimiter 1 }

ptDSCRateLimiterEntry OBJECT-TYPE
    SYNTAX          PtDSCRateLimiterEntry
    MAX-ACCESS      not-accessible
    STATUS          current
    DESCRIPTION     
            "A sequence of DSCRateLimiter attributes."
    INDEX           { ptConnGroupIndex, ptDSCRateLimiterDSCIndex, 
                      ptDSCRateLimiterDSCParameterSetsIndex, 
                      ptDSCRateLimiterIndex }
    ::= { ptDSCRateLimiterTable 1 }

PtDSCRateLimiterEntry ::=
    SEQUENCE {
        ptDSCRateLimiterName            DisplayString,
        ptDSCRateLimiterCapacityParameterSet    DisplayString,
        ptDSCRateLimiterInternalID      Integer32,
        ptDSCRateLimiterDSCIndex        Integer32,
        ptDSCRateLimiterDSCParameterSetsIndex     Integer32,
        ptDSCRateLimiterParentOID       OBJECT IDENTIFIER,
        ptDSCRateLimiterRowStatus       RowStatus,
        ptDSCRateLimiterIndex           Integer32
    }

ptDSCRateLimiterName OBJECT-TYPE
    SYNTAX          DisplayString (SIZE(0..255))
    MAX-ACCESS      read-only
    STATUS          current
    DESCRIPTION     
            "Name to uniquely identify the Rate Limiter. \nLeading and trailing whitespaces are trimmed. \nValid values: alphanumeric characters, dashes, underscores, spaces, and dots (maximum size of 64). Cannot start the name with reserved dsc_ or pt_ (case insensitive)."
    ::= { ptDSCRateLimiterEntry 1 }

ptDSCRateLimiterCapacityParameterSet OBJECT-TYPE
    SYNTAX          DisplayString (SIZE(0..255))
    MAX-ACCESS      read-create
    STATUS          current
    DESCRIPTION     
            "Capacity Parameter Set associated with this Rate Limiter. \nValid values: Existing Capacity Parameter Set. \nDefault value: default."
    ::= { ptDSCRateLimiterEntry 2 }

ptDSCRateLimiterInternalID OBJECT-TYPE
    SYNTAX          Integer32 (-2147483648..2147483647)
    MAX-ACCESS      read-only
    STATUS          current
    DESCRIPTION     
            "Rate Limiter unique internal ID. \nReserved for internal use."
    ::= { ptDSCRateLimiterEntry 99 }

ptDSCRateLimiterDSCIndex OBJECT-TYPE
    SYNTAX          Integer32 (-2147483648..2147483647)
    MAX-ACCESS      not-accessible
    STATUS          current
    DESCRIPTION     
            "This is the index of the parent type for this object.
             This parent type is DSC."
    ::= { ptDSCRateLimiterEntry 242 }

ptDSCRateLimiterDSCParameterSetsIndex OBJECT-TYPE
    SYNTAX          Integer32 (-2147483648..2147483647)
    MAX-ACCESS      not-accessible
    STATUS          current
    DESCRIPTION     
            "This is the index of the parent type for this object.
             This parent type is DSCParameterSets."
    ::= { ptDSCRateLimiterEntry 243 }

ptDSCRateLimiterParentOID OBJECT-TYPE
    SYNTAX          OBJECT IDENTIFIER
    MAX-ACCESS      read-create
    STATUS          current
    DESCRIPTION     
            "The OID of the parent object for this instance"
    ::= { ptDSCRateLimiterEntry 253 }

ptDSCRateLimiterRowStatus OBJECT-TYPE
    SYNTAX          RowStatus
    MAX-ACCESS      read-create
    STATUS          current
    DESCRIPTION     
            "The row status for the DSCRateLimiter table"
    ::= { ptDSCRateLimiterEntry 254 }

ptDSCRateLimiterIndex OBJECT-TYPE
    SYNTAX          Integer32 (-2147483648..2147483647)
    MAX-ACCESS      not-accessible
    STATUS          current
    DESCRIPTION     
            "The row number for the DSCRateLimiter table"
    ::= { ptDSCRateLimiterEntry 255 }

ptDSCDSCDefinitions OBJECT IDENTIFIER
    ::= { ptDSCDSC 1820 }

ptDSCDSCDefinitionsTable OBJECT-TYPE
    SYNTAX          SEQUENCE OF PtDSCDSCDefinitionsEntry
    MAX-ACCESS      not-accessible
    STATUS          current
    DESCRIPTION     
            "No description supplied in the proxy config file."
    ::= { ptDSCDSCDefinitions 1 }

ptDSCDSCDefinitionsEntry OBJECT-TYPE
    SYNTAX          PtDSCDSCDefinitionsEntry
    MAX-ACCESS      not-accessible
    STATUS          current
    DESCRIPTION     
            "A sequence of DSCDSCDefinitions attributes."
    INDEX           { ptConnGroupIndex, ptDSCDSCDefinitionsDSCIndex, 
                      ptDSCDSCDefinitionsIndex }
    ::= { ptDSCDSCDefinitionsTable 1 }

PtDSCDSCDefinitionsEntry ::=
    SEQUENCE {
        ptDSCDSCDefinitionsDSCIndex     Integer32,
        ptDSCDSCDefinitionsParentOID    OBJECT IDENTIFIER,
        ptDSCDSCDefinitionsRowStatus    RowStatus,
        ptDSCDSCDefinitionsIndex        Integer32
    }

ptDSCDSCDefinitionsDSCIndex OBJECT-TYPE
    SYNTAX          Integer32 (-2147483648..2147483647)
    MAX-ACCESS      not-accessible
    STATUS          current
    DESCRIPTION     
            "This is the index of the parent type for this object.
             This parent type is DSC."
    ::= { ptDSCDSCDefinitionsEntry 242 }

ptDSCDSCDefinitionsParentOID OBJECT-TYPE
    SYNTAX          OBJECT IDENTIFIER
    MAX-ACCESS      read-create
    STATUS          current
    DESCRIPTION     
            "The OID of the parent object for this instance"
    ::= { ptDSCDSCDefinitionsEntry 253 }

ptDSCDSCDefinitionsRowStatus OBJECT-TYPE
    SYNTAX          RowStatus
    MAX-ACCESS      read-create
    STATUS          current
    DESCRIPTION     
            "The row status for the DSCDSCDefinitions table"
    ::= { ptDSCDSCDefinitionsEntry 254 }

ptDSCDSCDefinitionsIndex OBJECT-TYPE
    SYNTAX          Integer32 (-2147483648..2147483647)
    MAX-ACCESS      not-accessible
    STATUS          current
    DESCRIPTION     
            "The row number for the DSCDSCDefinitions table"
    ::= { ptDSCDSCDefinitionsEntry 255 }

ptDSCApplicationIDDefinitions OBJECT IDENTIFIER
    ::= { ptDSCDSCDefinitions 1824 }

ptDSCApplicationIDDefinitionsTable OBJECT-TYPE
    SYNTAX          SEQUENCE OF PtDSCApplicationIDDefinitionsEntry
    MAX-ACCESS      not-accessible
    STATUS          current
    DESCRIPTION     
            "No description supplied in the proxy config file."
    ::= { ptDSCApplicationIDDefinitions 1 }

ptDSCApplicationIDDefinitionsEntry OBJECT-TYPE
    SYNTAX          PtDSCApplicationIDDefinitionsEntry
    MAX-ACCESS      not-accessible
    STATUS          current
    DESCRIPTION     
            "A sequence of DSCApplicationIDDefinitions attributes."
    INDEX           { ptConnGroupIndex, 
                      ptDSCApplicationIDDefinitionsDSCIndex, 
                      ptDSCApplicationIDDefinitionsDSCDefinitionsIndex, 
                      ptDSCApplicationIDDefinitionsIndex }
    ::= { ptDSCApplicationIDDefinitionsTable 1 }

PtDSCApplicationIDDefinitionsEntry ::=
    SEQUENCE {
        ptDSCApplicationIDDefinitionsDSCIndex     Integer32,
        ptDSCApplicationIDDefinitionsDSCDefinitionsIndex                Integer32,
        ptDSCApplicationIDDefinitionsParentOID      OBJECT IDENTIFIER,
        ptDSCApplicationIDDefinitionsRowStatus      RowStatus,
        ptDSCApplicationIDDefinitionsIndex  Integer32
    }

ptDSCApplicationIDDefinitionsDSCIndex OBJECT-TYPE
    SYNTAX          Integer32 (-2147483648..2147483647)
    MAX-ACCESS      not-accessible
    STATUS          current
    DESCRIPTION     
            "This is the index of the parent type for this object.
             This parent type is DSC."
    ::= { ptDSCApplicationIDDefinitionsEntry 242 }

ptDSCApplicationIDDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCApplicationIDDefinitionsEntry 243 }

ptDSCApplicationIDDefinitionsParentOID OBJECT-TYPE
    SYNTAX          OBJECT IDENTIFIER
    MAX-ACCESS      read-create
    STATUS          current
    DESCRIPTION     
            "The OID of the parent object for this instance"
    ::= { ptDSCApplicationIDDefinitionsEntry 253 }

ptDSCApplicationIDDefinitionsRowStatus OBJECT-TYPE
    SYNTAX          RowStatus
    MAX-ACCESS      read-create
    STATUS          current
    DESCRIPTION     
            "The row status for the DSCApplicationIDDefinitions table"
    ::= { ptDSCApplicationIDDefinitionsEntry 254 }

ptDSCApplicationIDDefinitionsIndex OBJECT-TYPE
    SYNTAX          Integer32 (-2147483648..2147483647)
    MAX-ACCESS      not-accessible
    STATUS          current
    DESCRIPTION     
            "The row number for the DSCApplicationIDDefinitions table"
    ::= { ptDSCApplicationIDDefinitionsEntry 255 }

ptDSCApplicationIDDefinition OBJECT IDENTIFIER
    ::= { ptDSCApplicationIDDefinitions 1825 }

ptDSCApplicationIDDefinitionTable OBJECT-TYPE
    SYNTAX          SEQUENCE OF PtDSCApplicationIDDefinitionEntry
    MAX-ACCESS      not-accessible
    STATUS          current
    DESCRIPTION     
            "No description supplied in the proxy config file."
    ::= { ptDSCApplicationIDDefinition 1 }

ptDSCApplicationIDDefinitionEntry OBJECT-TYPE
    SYNTAX          PtDSCApplicationIDDefinitionEntry
    MAX-ACCESS      not-accessible
    STATUS          current
    DESCRIPTION     
            "A sequence of DSCApplicationIDDefinition attributes."
    INDEX           { ptConnGroupIndex, 
                      ptDSCApplicationIDDefinitionDSCIndex, 
                      ptDSCApplicationIDDefinitionDSCDefinitionsIndex, 
                      ptDSCApplicationIDDefinitionApplicationIDDefinitionsIndex, 
                      ptDSCApplicationIDDefinitionIndex }
    ::= { ptDSCApplicationIDDefinitionTable 1 }

PtDSCApplicationIDDefinitionEntry ::=
    SEQUENCE {
        ptDSCApplicationIDDefinitionName DisplayString,
        ptDSCApplicationIDDefinitionApplicationID         Integer32,
        ptDSCApplicationIDDefinitionDSCIndex    Integer32,
        ptDSCApplicationIDDefinitionDSCDefinitionsIndex               Integer32,
        ptDSCApplicationIDDefinitionApplicationIDDefinitionsIndex                         Integer32,
        ptDSCApplicationIDDefinitionParentOID     OBJECT IDENTIFIER,
        ptDSCApplicationIDDefinitionRowStatus     RowStatus,
        ptDSCApplicationIDDefinitionIndex Integer32
    }

ptDSCApplicationIDDefinitionName OBJECT-TYPE
    SYNTAX          DisplayString (SIZE(0..255))
    MAX-ACCESS      read-only
    STATUS          current
    DESCRIPTION     
            "String representation of the numeric Application ID. \nLeading and trailing whitespaces are trimmed. \nValid values: alphanumeric characters, dashes, underscores, spaces, and dots (maximum size of 64). Cannot start the name with reserved dsc_ or pt_ (case insensitive)."
    ::= { ptDSCApplicationIDDefinitionEntry 1 }

ptDSCApplicationIDDefinitionApplicationID OBJECT-TYPE
    SYNTAX          Integer32 (-2147483648..2147483647)
    MAX-ACCESS      read-only
    STATUS          current
    DESCRIPTION     
            "An Application ID is a Diameter concept, defined in RFC6733. \nApplication ID values are managed by IANA. See \n http://www.iana.org/assignments/aaa-parameters/aaa-parameters.txt \nfor more details on specific Application ID assignments. \nValid values: integers."
    ::= { ptDSCApplicationIDDefinitionEntry 2 }

ptDSCApplicationIDDefinitionDSCIndex OBJECT-TYPE
    SYNTAX          Integer32 (-2147483648..2147483647)
    MAX-ACCESS      not-accessible
    STATUS          current
    DESCRIPTION     
            "This is the index of the parent type for this object.
             This parent type is DSC."
    ::= { ptDSCApplicationIDDefinitionEntry 242 }

ptDSCApplicationIDDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCApplicationIDDefinitionEntry 243 }

ptDSCApplicationIDDefinitionApplicationIDDefinitionsIndex OBJECT-TYPE
    SYNTAX          Integer32 (-2147483648..2147483647)
    MAX-ACCESS      not-accessible
    STATUS          current
    DESCRIPTION     
            "This is the index of the parent type for this object.
             This parent type is ApplicationIDDefinitions."
    ::= { ptDSCApplicationIDDefinitionEntry 244 }

ptDSCApplicationIDDefinitionParentOID OBJECT-TYPE
    SYNTAX          OBJECT IDENTIFIER
    MAX-ACCESS      read-create
    STATUS          current
    DESCRIPTION     
            "The OID of the parent object for this instance"
    ::= { ptDSCApplicationIDDefinitionEntry 253 }

ptDSCApplicationIDDefinitionRowStatus OBJECT-TYPE
    SYNTAX          RowStatus
    MAX-ACCESS      read-create
    STATUS          current
    DESCRIPTION     
            "The row status for the DSCApplicationIDDefinition table"
    ::= { ptDSCApplicationIDDefinitionEntry 254 }

ptDSCApplicationIDDefinitionIndex OBJECT-TYPE
    SYNTAX          Integer32 (-2147483648..2147483647)
    MAX-ACCESS      not-accessible
    STATUS          current
    DESCRIPTION     
            "The row number for the DSCApplicationIDDefinition table"
    ::= { ptDSCApplicationIDDefinitionEntry 255 }

ptDSCVendorIDDefinitions OBJECT IDENTIFIER
    ::= { ptDSCDSCDefinitions 1826 }

ptDSCVendorIDDefinitionsTable OBJECT-TYPE
    SYNTAX          SEQUENCE OF PtDSCVendorIDDefinitionsEntry
    MAX-ACCESS      not-accessible
    STATUS          current
    DESCRIPTION     
            "No description supplied in the proxy config file."
    ::= { ptDSCVendorIDDefinitions 1 }

ptDSCVendorIDDefinitionsEntry OBJECT-TYPE
    SYNTAX          PtDSCVendorIDDefinitionsEntry
    MAX-ACCESS      not-accessible
    STATUS          current
    DESCRIPTION     
            "A sequence of DSCVendorIDDefinitions attributes."
    INDEX           { ptConnGroupIndex, ptDSCVendorIDDefinitionsDSCIndex, 
                      ptDSCVendorIDDefinitionsDSCDefinitionsIndex, 
                      ptDSCVendorIDDefinitionsIndex }
    ::= { ptDSCVendorIDDefinitionsTable 1 }

PtDSCVendorIDDefinitionsEntry ::=
    SEQUENCE {
        ptDSCVendorIDDefinitionsDSCIndex Integer32,
        ptDSCVendorIDDefinitionsDSCDefinitionsIndex           Integer32,
        ptDSCVendorIDDefinitionsParentOID OBJECT IDENTIFIER,
        ptDSCVendorIDDefinitionsRowStatus RowStatus,
        ptDSCVendorIDDefinitionsIndex   Integer32
    }

ptDSCVendorIDDefinitionsDSCIndex OBJECT-TYPE
    SYNTAX          Integer32 (-2147483648..2147483647)
    MAX-ACCESS      not-accessible
    STATUS          current
    DESCRIPTION     
            "This is the index of the parent type for this object.
             This parent type is DSC."
    ::= { ptDSCVendorIDDefinitionsEntry 242 }

ptDSCVendorIDDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCVendorIDDefinitionsEntry 243 }

ptDSCVendorIDDefinitionsParentOID OBJECT-TYPE
    SYNTAX          OBJECT IDENTIFIER
    MAX-ACCESS      read-create
    STATUS          current
    DESCRIPTION     
            "The OID of the parent object for this instance"
    ::= { ptDSCVendorIDDefinitionsEntry 253 }

ptDSCVendorIDDefinitionsRowStatus OBJECT-TYPE
    SYNTAX          RowStatus
    MAX-ACCESS      read-create
    STATUS          current
    DESCRIPTION     
            "The row status for the DSCVendorIDDefinitions table"
    ::= { ptDSCVendorIDDefinitionsEntry 254 }

ptDSCVendorIDDefinitionsIndex OBJECT-TYPE
    SYNTAX          Integer32 (-2147483648..2147483647)
    MAX-ACCESS      not-accessible
    STATUS          current
    DESCRIPTION     
            "The row number for the DSCVendorIDDefinitions table"
    ::= { ptDSCVendorIDDefinitionsEntry 255 }

ptDSCVendorIDDefinition OBJECT IDENTIFIER
    ::= { ptDSCVendorIDDefinitions 1827 }

ptDSCVendorIDDefinitionTable OBJECT-TYPE
    SYNTAX          SEQUENCE OF PtDSCVendorIDDefinitionEntry
    MAX-ACCESS      not-accessible
    STATUS          current
    DESCRIPTION     
            "No description supplied in the proxy config file."
    ::= { ptDSCVendorIDDefinition 1 }

ptDSCVendorIDDefinitionEntry OBJECT-TYPE
    SYNTAX          PtDSCVendorIDDefinitionEntry
    MAX-ACCESS      not-accessible
    STATUS          current
    DESCRIPTION     
            "A sequence of DSCVendorIDDefinition attributes."
    INDEX           { ptConnGroupIndex, ptDSCVendorIDDefinitionDSCIndex, 
                      ptDSCVendorIDDefinitionDSCDefinitionsIndex, 
                      ptDSCVendorIDDefinitionVendorIDDefinitionsIndex, 
                      ptDSCVendorIDDefinitionIndex }
    ::= { ptDSCVendorIDDefinitionTable 1 }

PtDSCVendorIDDefinitionEntry ::=
    SEQUENCE {
        ptDSCVendorIDDefinitionName     DisplayString,
        ptDSCVendorIDDefinitionVendorID Integer32,
        ptDSCVendorIDDefinitionDSCIndex Integer32,
        ptDSCVendorIDDefinitionDSCDefinitionsIndex          Integer32,
        ptDSCVendorIDDefinitionVendorIDDefinitionsIndex               Integer32,
        ptDSCVendorIDDefinitionParentOID OBJECT IDENTIFIER,
        ptDSCVendorIDDefinitionRowStatus RowStatus,
        ptDSCVendorIDDefinitionIndex    Integer32
    }

ptDSCVendorIDDefinitionName OBJECT-TYPE
    SYNTAX          DisplayString (SIZE(0..255))
    MAX-ACCESS      read-only
    STATUS          current
    DESCRIPTION     
            "String representation of the numeric Vendor ID. \nLeading and trailing whitespaces are trimmed. \nValid values: alphanumeric characters, dashes, underscores, spaces, and dots (maximum size of 64). Cannot start the name with reserved dsc_ or pt_ (case insensitive)."
    ::= { ptDSCVendorIDDefinitionEntry 1 }

ptDSCVendorIDDefinitionVendorID OBJECT-TYPE
    SYNTAX          Integer32 (-2147483648..2147483647)
    MAX-ACCESS      read-only
    STATUS          current
    DESCRIPTION     
            "A Vendor ID is a Diameter concept, defined in RFC6733. \nThe value 0 is reserved for base Diameter (as defined in RFC6733). \nOther Vendor ID values are managed by IANA. See \n http://www.iana.org/assignments/enterprise-numbers \nfor more details on specific Vendor ID assignments. \nValid values: integers."
    ::= { ptDSCVendorIDDefinitionEntry 2 }

ptDSCVendorIDDefinitionDSCIndex OBJECT-TYPE
    SYNTAX          Integer32 (-2147483648..2147483647)
    MAX-ACCESS      not-accessible
    STATUS          current
    DESCRIPTION     
            "This is the index of the parent type for this object.
             This parent type is DSC."
    ::= { ptDSCVendorIDDefinitionEntry 242 }

ptDSCVendorIDDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCVendorIDDefinitionEntry 243 }

ptDSCVendorIDDefinitionVendorIDDefinitionsIndex OBJECT-TYPE
    SYNTAX          Integer32 (-2147483648..2147483647)
    MAX-ACCESS      not-accessible
    STATUS          current
    DESCRIPTION     
            "This is the index of the parent type for this object.
             This parent type is VendorIDDefinitions."
    ::= { ptDSCVendorIDDefinitionEntry 244 }

ptDSCVendorIDDefinitionParentOID OBJECT-TYPE
    SYNTAX          OBJECT IDENTIFIER
    MAX-ACCESS      read-create
    STATUS          current
    DESCRIPTION     
            "The OID of the parent object for this instance"
    ::= { ptDSCVendorIDDefinitionEntry 253 }

ptDSCVendorIDDefinitionRowStatus OBJECT-TYPE
    SYNTAX          RowStatus
    MAX-ACCESS      read-create
    STATUS          current
    DESCRIPTION     
            "The row status for the DSCVendorIDDefinition table"
    ::= { ptDSCVendorIDDefinitionEntry 254 }

ptDSCVendorIDDefinitionIndex OBJECT-TYPE
    SYNTAX          Integer32 (-2147483648..2147483647)
    MAX-ACCESS      not-accessible
    STATUS          current
    DESCRIPTION     
            "The row number for the DSCVendorIDDefinition table"
    ::= { ptDSCVendorIDDefinitionEntry 255 }

ptDSCAVPDefinitions OBJECT IDENTIFIER
    ::= { ptDSCDSCDefinitions 1828 }

ptDSCAVPDefinitionsTable OBJECT-TYPE
    SYNTAX          SEQUENCE OF PtDSCAVPDefinitionsEntry
    MAX-ACCESS      not-accessible
    STATUS          current
    DESCRIPTION     
            "No description supplied in the proxy config file."
    ::= { ptDSCAVPDefinitions 1 }

ptDSCAVPDefinitionsEntry OBJECT-TYPE
    SYNTAX          PtDSCAVPDefinitionsEntry
    MAX-ACCESS      not-accessible
    STATUS          current
    DESCRIPTION     
            "A sequence of DSCAVPDefinitions attributes."
    INDEX           { ptConnGroupIndex, ptDSCAVPDefinitionsDSCIndex, 
                      ptDSCAVPDefinitionsDSCDefinitionsIndex, 
                      ptDSCAVPDefinitionsIndex }
    ::= { ptDSCAVPDefinitionsTable 1 }

PtDSCAVPDefinitionsEntry ::=
    SEQUENCE {
        ptDSCAVPDefinitionsDSCIndex     Integer32,
        ptDSCAVPDefinitionsDSCDefinitionsIndex      Integer32,
        ptDSCAVPDefinitionsParentOID    OBJECT IDENTIFIER,
        ptDSCAVPDefinitionsRowStatus    RowStatus,
        ptDSCAVPDefinitionsIndex        Integer32
    }

ptDSCAVPDefinitionsDSCIndex OBJECT-TYPE
    SYNTAX          Integer32 (-2147483648..2147483647)
    MAX-ACCESS      not-accessible
    STATUS          current
    DESCRIPTION     
            "This is the index of the parent type for this object.
             This parent type is DSC."
    ::= { ptDSCAVPDefinitionsEntry 242 }

ptDSCAVPDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCAVPDefinitionsEntry 243 }

ptDSCAVPDefinitionsParentOID OBJECT-TYPE
    SYNTAX          OBJECT IDENTIFIER
    MAX-ACCESS      read-create
    STATUS          current
    DESCRIPTION     
            "The OID of the parent object for this instance"
    ::= { ptDSCAVPDefinitionsEntry 253 }

ptDSCAVPDefinitionsRowStatus OBJECT-TYPE
    SYNTAX          RowStatus
    MAX-ACCESS      read-create
    STATUS          current
    DESCRIPTION     
            "The row status for the DSCAVPDefinitions table"
    ::= { ptDSCAVPDefinitionsEntry 254 }

ptDSCAVPDefinitionsIndex OBJECT-TYPE
    SYNTAX          Integer32 (-2147483648..2147483647)
    MAX-ACCESS      not-accessible
    STATUS          current
    DESCRIPTION     
            "The row number for the DSCAVPDefinitions table"
    ::= { ptDSCAVPDefinitionsEntry 255 }

ptDSCAVPDefinition OBJECT IDENTIFIER
    ::= { ptDSCAVPDefinitions 1829 }

ptDSCAVPDefinitionTable OBJECT-TYPE
    SYNTAX          SEQUENCE OF PtDSCAVPDefinitionEntry
    MAX-ACCESS      not-accessible
    STATUS          current
    DESCRIPTION     
            "No description supplied in the proxy config file."
    ::= { ptDSCAVPDefinition 1 }

ptDSCAVPDefinitionEntry OBJECT-TYPE
    SYNTAX          PtDSCAVPDefinitionEntry
    MAX-ACCESS      not-accessible
    STATUS          current
    DESCRIPTION     
            "A sequence of DSCAVPDefinition attributes."
    INDEX           { ptConnGroupIndex, ptDSCAVPDefinitionDSCIndex, 
                      ptDSCAVPDefinitionDSCDefinitionsIndex, 
                      ptDSCAVPDefinitionAVPDefinitionsIndex, 
                      ptDSCAVPDefinitionIndex }
    ::= { ptDSCAVPDefinitionTable 1 }

PtDSCAVPDefinitionEntry ::=
    SEQUENCE {
        ptDSCAVPDefinitionVendorID      DisplayString,
        ptDSCAVPDefinitionAVPCode       Integer32,
        ptDSCAVPDefinitionName          DisplayString,
        ptDSCAVPDefinitionAVPType       INTEGER,
        ptDSCAVPDefinitionComment       DisplayString,
        ptDSCAVPDefinitionDSCIndex      Integer32,
        ptDSCAVPDefinitionDSCDefinitionsIndex     Integer32,
        ptDSCAVPDefinitionAVPDefinitionsIndex     Integer32,
        ptDSCAVPDefinitionParentOID     OBJECT IDENTIFIER,
        ptDSCAVPDefinitionRowStatus     RowStatus,
        ptDSCAVPDefinitionIndex         Integer32
    }

ptDSCAVPDefinitionVendorID OBJECT-TYPE
    SYNTAX          DisplayString (SIZE(0..255))
    MAX-ACCESS      read-only
    STATUS          current
    DESCRIPTION     
            "Vendor ID Definition name responsible for the AVP. \nThe combination of Vendor ID and AVP Code uniquely identifies an AVP. \nValid values: name of existing Vendor ID Definition."
    ::= { ptDSCAVPDefinitionEntry 1 }

ptDSCAVPDefinitionAVPCode OBJECT-TYPE
    SYNTAX          Integer32 (-2147483648..2147483647)
    MAX-ACCESS      read-only
    STATUS          current
    DESCRIPTION     
            "Code of the AVP. \nThe combination of Vendor ID and AVP Code uniquely identifies an AVP. \nValid values: integers."
    ::= { ptDSCAVPDefinitionEntry 2 }

ptDSCAVPDefinitionName OBJECT-TYPE
    SYNTAX          DisplayString (SIZE(0..255))
    MAX-ACCESS      read-only
    STATUS          current
    DESCRIPTION     
            "String representation of the AVP Definition. \nLeading and trailing whitespaces are trimmed. \nValid values: alphanumeric characters, dashes, underscores, spaces, and dots (maximum size of 64). Cannot start the name with reserved dsc_ or pt_ (case insensitive)."
    ::= { ptDSCAVPDefinitionEntry 3 }

ptDSCAVPDefinitionAVPType OBJECT-TYPE
    SYNTAX          INTEGER { utf8string(10), octetstring(20), 
                        unsigned32(30), unsigned64(40), integer32(50), 
                        integer64(51), time(60), grouped(70), 
                        enumerated(80), diameteridentity(90), 
                        diameteruri(100), ipfilterrule(110), 
                        address(120), unknown(130), float32(140), 
                        float64(150) }
    MAX-ACCESS      read-only
    STATUS          current
    DESCRIPTION     
            "AVP Type defines the validation and encoding format of the AVP values. \nImportant for Modification Record commands affecting the AVP values. \nValid values: UTF8Strings, OctetString, Unsigned32, Unsigned64, Integer32, Integer64, Time, Grouped, Enumerated, DiameterIdentity, DiameterURI, IPFilterRule, Address, Float32, Float64, and Unknown (as per RFC6733). \nDefault value: UTF8String (reference only)."
    ::= { ptDSCAVPDefinitionEntry 4 }

ptDSCAVPDefinitionComment OBJECT-TYPE
    SYNTAX          DisplayString (SIZE(0..255))
    MAX-ACCESS      read-create
    STATUS          current
    DESCRIPTION     
            "AVP Definition optional comment for supplementary information. \nOften includes the specification reference for the AVP definition. \nValid values: free-form string of maximum size 64 characters."
    ::= { ptDSCAVPDefinitionEntry 5 }

ptDSCAVPDefinitionDSCIndex OBJECT-TYPE
    SYNTAX          Integer32 (-2147483648..2147483647)
    MAX-ACCESS      not-accessible
    STATUS          current
    DESCRIPTION     
            "This is the index of the parent type for this object.
             This parent type is DSC."
    ::= { ptDSCAVPDefinitionEntry 242 }

ptDSCAVPDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCAVPDefinitionEntry 243 }

ptDSCAVPDefinitionAVPDefinitionsIndex OBJECT-TYPE
    SYNTAX          Integer32 (-2147483648..2147483647)
    MAX-ACCESS      not-accessible
    STATUS          current
    DESCRIPTION     
            "This is the index of the parent type for this object.
             This parent type is AVPDefinitions."
    ::= { ptDSCAVPDefinitionEntry 244 }

ptDSCAVPDefinitionParentOID OBJECT-TYPE
    SYNTAX          OBJECT IDENTIFIER
    MAX-ACCESS      read-create
    STATUS          current
    DESCRIPTION     
            "The OID of the parent object for this instance"
    ::= { ptDSCAVPDefinitionEntry 253 }

ptDSCAVPDefinitionRowStatus OBJECT-TYPE
    SYNTAX          RowStatus
    MAX-ACCESS      read-create
    STATUS          current
    DESCRIPTION     
            "The row status for the DSCAVPDefinition table"
    ::= { ptDSCAVPDefinitionEntry 254 }

ptDSCAVPDefinitionIndex OBJECT-TYPE
    SYNTAX          Integer32 (-2147483648..2147483647)
    MAX-ACCESS      not-accessible
    STATUS          current
    DESCRIPTION     
            "The row number for the DSCAVPDefinition table"
    ::= { ptDSCAVPDefinitionEntry 255 }

ptDSCAVPAliasDefinitions OBJECT IDENTIFIER
    ::= { ptDSCDSCDefinitions 1832 }

ptDSCAVPAliasDefinitionsTable OBJECT-TYPE
    SYNTAX          SEQUENCE OF PtDSCAVPAliasDefinitionsEntry
    MAX-ACCESS      not-accessible
    STATUS          current
    DESCRIPTION     
            "No description supplied in the proxy config file."
    ::= { ptDSCAVPAliasDefinitions 1 }

ptDSCAVPAliasDefinitionsEntry OBJECT-TYPE
    SYNTAX          PtDSCAVPAliasDefinitionsEntry
    MAX-ACCESS      not-accessible
    STATUS          current
    DESCRIPTION     
            "A sequence of DSCAVPAliasDefinitions attributes."
    INDEX           { ptConnGroupIndex, ptDSCAVPAliasDefinitionsDSCIndex, 
                      ptDSCAVPAliasDefinitionsDSCDefinitionsIndex, 
                      ptDSCAVPAliasDefinitionsIndex }
    ::= { ptDSCAVPAliasDefinitionsTable 1 }

PtDSCAVPAliasDefinitionsEntry ::=
    SEQUENCE {
        ptDSCAVPAliasDefinitionsDSCIndex Integer32,
        ptDSCAVPAliasDefinitionsDSCDefinitionsIndex           Integer32,
        ptDSCAVPAliasDefinitionsParentOID OBJECT IDENTIFIER,
        ptDSCAVPAliasDefinitionsRowStatus RowStatus,
        ptDSCAVPAliasDefinitionsIndex   Integer32
    }

ptDSCAVPAliasDefinitionsDSCIndex OBJECT-TYPE
    SYNTAX          Integer32 (-2147483648..2147483647)
    MAX-ACCESS      not-accessible
    STATUS          current
    DESCRIPTION     
            "This is the index of the parent type for this object.
             This parent type is DSC."
    ::= { ptDSCAVPAliasDefinitionsEntry 242 }

ptDSCAVPAliasDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCAVPAliasDefinitionsEntry 243 }

ptDSCAVPAliasDefinitionsParentOID OBJECT-TYPE
    SYNTAX          OBJECT IDENTIFIER
    MAX-ACCESS      read-create
    STATUS          current
    DESCRIPTION     
            "The OID of the parent object for this instance"
    ::= { ptDSCAVPAliasDefinitionsEntry 253 }

ptDSCAVPAliasDefinitionsRowStatus OBJECT-TYPE
    SYNTAX          RowStatus
    MAX-ACCESS      read-create
    STATUS          current
    DESCRIPTION     
            "The row status for the DSCAVPAliasDefinitions table"
    ::= { ptDSCAVPAliasDefinitionsEntry 254 }

ptDSCAVPAliasDefinitionsIndex OBJECT-TYPE
    SYNTAX          Integer32 (-2147483648..2147483647)
    MAX-ACCESS      not-accessible
    STATUS          current
    DESCRIPTION     
            "The row number for the DSCAVPAliasDefinitions table"
    ::= { ptDSCAVPAliasDefinitionsEntry 255 }

ptDSCAVPAliasDefinition OBJECT IDENTIFIER
    ::= { ptDSCAVPAliasDefinitions 1833 }

ptDSCAVPAliasDefinitionTable OBJECT-TYPE
    SYNTAX          SEQUENCE OF PtDSCAVPAliasDefinitionEntry
    MAX-ACCESS      not-accessible
    STATUS          current
    DESCRIPTION     
            "No description supplied in the proxy config file."
    ::= { ptDSCAVPAliasDefinition 1 }

ptDSCAVPAliasDefinitionEntry OBJECT-TYPE
    SYNTAX          PtDSCAVPAliasDefinitionEntry
    MAX-ACCESS      not-accessible
    STATUS          current
    DESCRIPTION     
            "A sequence of DSCAVPAliasDefinition attributes."
    INDEX           { ptConnGroupIndex, ptDSCAVPAliasDefinitionDSCIndex, 
                      ptDSCAVPAliasDefinitionDSCDefinitionsIndex, 
                      ptDSCAVPAliasDefinitionAVPAliasDefinitionsIndex, 
                      ptDSCAVPAliasDefinitionIndex }
    ::= { ptDSCAVPAliasDefinitionTable 1 }

PtDSCAVPAliasDefinitionEntry ::=
    SEQUENCE {
        ptDSCAVPAliasDefinitionName     DisplayString,
        ptDSCAVPAliasDefinitionAVPName  DisplayString,
        ptDSCAVPAliasDefinitionAVPInstance  INTEGER,
        ptDSCAVPAliasDefinitionNestedAVPAlias     DisplayString,
        ptDSCAVPAliasDefinitionDSCIndex Integer32,
        ptDSCAVPAliasDefinitionDSCDefinitionsIndex          Integer32,
        ptDSCAVPAliasDefinitionAVPAliasDefinitionsIndex               Integer32,
        ptDSCAVPAliasDefinitionParentOID OBJECT IDENTIFIER,
        ptDSCAVPAliasDefinitionRowStatus RowStatus,
        ptDSCAVPAliasDefinitionIndex    Integer32
    }

ptDSCAVPAliasDefinitionName OBJECT-TYPE
    SYNTAX          DisplayString (SIZE(0..255))
    MAX-ACCESS      read-only
    STATUS          current
    DESCRIPTION     
            "String representation of the AVP Alias definition. \nLeading and trailing whitespaces are trimmed. \nValid values: alphanumeric characters, dashes, underscores, spaces, and dots (maximum size of 64). Cannot start the name with reserved dsc_ or pt_ (case insensitive)."
    ::= { ptDSCAVPAliasDefinitionEntry 1 }

ptDSCAVPAliasDefinitionAVPName OBJECT-TYPE
    SYNTAX          DisplayString (SIZE(0..255))
    MAX-ACCESS      read-only
    STATUS          current
    DESCRIPTION     
            "Associated AVP Definition Name. \nValid values: Existing AVP Definition Name."
    ::= { ptDSCAVPAliasDefinitionEntry 2 }

ptDSCAVPAliasDefinitionAVPInstance OBJECT-TYPE
    SYNTAX          INTEGER { first(100), last(101), any(102) }
    MAX-ACCESS      read-only
    STATUS          current
    DESCRIPTION     
            "AVP Instance (FIRST/LAST/ANY/1..10) \nLocation or list of the AVP in the Diameter message or grouped AVP. \nDefault value: FIRST."
    ::= { ptDSCAVPAliasDefinitionEntry 3 }

ptDSCAVPAliasDefinitionNestedAVPAlias OBJECT-TYPE
    SYNTAX          DisplayString (SIZE(0..255))
    MAX-ACCESS      read-only
    STATUS          current
    DESCRIPTION     
            "Nested AVP Alias. \nIf unnested, set to empty string. Else, set to the associated AVP \nAlias Definition name of the nested AVP. \nValid values: Existing AVP Alias Definition Name or empty string. \nDefault value: empty string. \nExample: \nName: ExpRes-ExpResCo. \nAVP Name: Experimental-Result. \nNested AVP Alias: ExpResCo (Existing AVP Alias Name for Experimental-Result-Code AVP)."
    ::= { ptDSCAVPAliasDefinitionEntry 4 }

ptDSCAVPAliasDefinitionDSCIndex OBJECT-TYPE
    SYNTAX          Integer32 (-2147483648..2147483647)
    MAX-ACCESS      not-accessible
    STATUS          current
    DESCRIPTION     
            "This is the index of the parent type for this object.
             This parent type is DSC."
    ::= { ptDSCAVPAliasDefinitionEntry 242 }

ptDSCAVPAliasDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCAVPAliasDefinitionEntry 243 }

ptDSCAVPAliasDefinitionAVPAliasDefinitionsIndex OBJECT-TYPE
    SYNTAX          Integer32 (-2147483648..2147483647)
    MAX-ACCESS      not-accessible
    STATUS          current
    DESCRIPTION     
            "This is the index of the parent type for this object.
             This parent type is AVPAliasDefinitions."
    ::= { ptDSCAVPAliasDefinitionEntry 244 }

ptDSCAVPAliasDefinitionParentOID OBJECT-TYPE
    SYNTAX          OBJECT IDENTIFIER
    MAX-ACCESS      read-create
    STATUS          current
    DESCRIPTION     
            "The OID of the parent object for this instance"
    ::= { ptDSCAVPAliasDefinitionEntry 253 }

ptDSCAVPAliasDefinitionRowStatus OBJECT-TYPE
    SYNTAX          RowStatus
    MAX-ACCESS      read-create
    STATUS          current
    DESCRIPTION     
            "The row status for the DSCAVPAliasDefinition table"
    ::= { ptDSCAVPAliasDefinitionEntry 254 }

ptDSCAVPAliasDefinitionIndex OBJECT-TYPE
    SYNTAX          Integer32 (-2147483648..2147483647)
    MAX-ACCESS      not-accessible
    STATUS          current
    DESCRIPTION     
            "The row number for the DSCAVPAliasDefinition table"
    ::= { ptDSCAVPAliasDefinitionEntry 255 }

ptDSCCommandCodeDefinitions OBJECT IDENTIFIER
    ::= { ptDSCDSCDefinitions 1838 }

ptDSCCommandCodeDefinitionsTable OBJECT-TYPE
    SYNTAX          SEQUENCE OF PtDSCCommandCodeDefinitionsEntry
    MAX-ACCESS      not-accessible
    STATUS          current
    DESCRIPTION     
            "No description supplied in the proxy config file."
    ::= { ptDSCCommandCodeDefinitions 1 }

ptDSCCommandCodeDefinitionsEntry OBJECT-TYPE
    SYNTAX          PtDSCCommandCodeDefinitionsEntry
    MAX-ACCESS      not-accessible
    STATUS          current
    DESCRIPTION     
            "A sequence of DSCCommandCodeDefinitions attributes."
    INDEX           { ptConnGroupIndex, 
                      ptDSCCommandCodeDefinitionsDSCIndex, 
                      ptDSCCommandCodeDefinitionsDSCDefinitionsIndex, 
                      ptDSCCommandCodeDefinitionsIndex }
    ::= { ptDSCCommandCodeDefinitionsTable 1 }

PtDSCCommandCodeDefinitionsEntry ::=
    SEQUENCE {
        ptDSCCommandCodeDefinitionsDSCIndex   Integer32,
        ptDSCCommandCodeDefinitionsDSCDefinitionsIndex              Integer32,
        ptDSCCommandCodeDefinitionsParentOID    OBJECT IDENTIFIER,
        ptDSCCommandCodeDefinitionsRowStatus    RowStatus,
        ptDSCCommandCodeDefinitionsIndex Integer32
    }

ptDSCCommandCodeDefinitionsDSCIndex OBJECT-TYPE
    SYNTAX          Integer32 (-2147483648..2147483647)
    MAX-ACCESS      not-accessible
    STATUS          current
    DESCRIPTION     
            "This is the index of the parent type for this object.
             This parent type is DSC."
    ::= { ptDSCCommandCodeDefinitionsEntry 242 }

ptDSCCommandCodeDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCCommandCodeDefinitionsEntry 243 }

ptDSCCommandCodeDefinitionsParentOID OBJECT-TYPE
    SYNTAX          OBJECT IDENTIFIER
    MAX-ACCESS      read-create
    STATUS          current
    DESCRIPTION     
            "The OID of the parent object for this instance"
    ::= { ptDSCCommandCodeDefinitionsEntry 253 }

ptDSCCommandCodeDefinitionsRowStatus OBJECT-TYPE
    SYNTAX          RowStatus
    MAX-ACCESS      read-create
    STATUS          current
    DESCRIPTION     
            "The row status for the DSCCommandCodeDefinitions table"
    ::= { ptDSCCommandCodeDefinitionsEntry 254 }

ptDSCCommandCodeDefinitionsIndex OBJECT-TYPE
    SYNTAX          Integer32 (-2147483648..2147483647)
    MAX-ACCESS      not-accessible
    STATUS          current
    DESCRIPTION     
            "The row number for the DSCCommandCodeDefinitions table"
    ::= { ptDSCCommandCodeDefinitionsEntry 255 }

ptDSCCommandCodeDefinition OBJECT IDENTIFIER
    ::= { ptDSCCommandCodeDefinitions 1839 }

ptDSCCommandCodeDefinitionTable OBJECT-TYPE
    SYNTAX          SEQUENCE OF PtDSCCommandCodeDefinitionEntry
    MAX-ACCESS      not-accessible
    STATUS          current
    DESCRIPTION     
            "No description supplied in the proxy config file."
    ::= { ptDSCCommandCodeDefinition 1 }

ptDSCCommandCodeDefinitionEntry OBJECT-TYPE
    SYNTAX          PtDSCCommandCodeDefinitionEntry
    MAX-ACCESS      not-accessible
    STATUS          current
    DESCRIPTION     
            "A sequence of DSCCommandCodeDefinition attributes."
    INDEX           { ptConnGroupIndex, 
                      ptDSCCommandCodeDefinitionDSCIndex, 
                      ptDSCCommandCodeDefinitionDSCDefinitionsIndex, 
                      ptDSCCommandCodeDefinitionCommandCodeDefinitionsIndex, 
                      ptDSCCommandCodeDefinitionIndex }
    ::= { ptDSCCommandCodeDefinitionTable 1 }

PtDSCCommandCodeDefinitionEntry ::=
    SEQUENCE {
        ptDSCCommandCodeDefinitionCommandCode     Integer32,
        ptDSCCommandCodeDefinitionName  DisplayString,
        ptDSCCommandCodeDefinitionImportance    Integer32,
        ptDSCCommandCodeDefinitionComment DisplayString,
        ptDSCCommandCodeDefinitionDSCIndex  Integer32,
        ptDSCCommandCodeDefinitionDSCDefinitionsIndex             Integer32,
        ptDSCCommandCodeDefinitionCommandCodeDefinitionsIndex                     Integer32,
        ptDSCCommandCodeDefinitionParentOID   OBJECT IDENTIFIER,
        ptDSCCommandCodeDefinitionRowStatus   RowStatus,
        ptDSCCommandCodeDefinitionIndex Integer32
    }

ptDSCCommandCodeDefinitionCommandCode OBJECT-TYPE
    SYNTAX          Integer32 (-2147483648..2147483647)
    MAX-ACCESS      read-only
    STATUS          current
    DESCRIPTION     
            "Associated Command Code. \nValid values: 0 to 16777215."
    ::= { ptDSCCommandCodeDefinitionEntry 1 }

ptDSCCommandCodeDefinitionName OBJECT-TYPE
    SYNTAX          DisplayString (SIZE(0..255))
    MAX-ACCESS      read-only
    STATUS          current
    DESCRIPTION     
            "String representation of the Command Code definition. \nUse abbreviation where possible for cross-referencing. \nName will be moved to uppercase as required. \nValid values: alphanumeric characters ending with 'R' (maximum size of 10)."
    ::= { ptDSCCommandCodeDefinitionEntry 2 }

ptDSCCommandCodeDefinitionImportance OBJECT-TYPE
    SYNTAX          Integer32
    MAX-ACCESS      read-create
    STATUS          current
    DESCRIPTION     
            "Command Code Priority (0..3) \nDefault value: 1."
    ::= { ptDSCCommandCodeDefinitionEntry 3 }

ptDSCCommandCodeDefinitionComment OBJECT-TYPE
    SYNTAX          DisplayString (SIZE(0..255))
    MAX-ACCESS      read-create
    STATUS          current
    DESCRIPTION     
            "Command Code Definition optional comment for supplementary information. \nWhen an abbreviation is used in the 'Name' attribute, the full name should be provided. \nShould also include the corresponding specifications document reference. \nValid values: free-form string of maximum size 64 characters."
    ::= { ptDSCCommandCodeDefinitionEntry 4 }

ptDSCCommandCodeDefinitionDSCIndex OBJECT-TYPE
    SYNTAX          Integer32 (-2147483648..2147483647)
    MAX-ACCESS      not-accessible
    STATUS          current
    DESCRIPTION     
            "This is the index of the parent type for this object.
             This parent type is DSC."
    ::= { ptDSCCommandCodeDefinitionEntry 242 }

ptDSCCommandCodeDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCCommandCodeDefinitionEntry 243 }

ptDSCCommandCodeDefinitionCommandCodeDefinitionsIndex OBJECT-TYPE
    SYNTAX          Integer32 (-2147483648..2147483647)
    MAX-ACCESS      not-accessible
    STATUS          current
    DESCRIPTION     
            "This is the index of the parent type for this object.
             This parent type is CommandCodeDefinitions."
    ::= { ptDSCCommandCodeDefinitionEntry 244 }

ptDSCCommandCodeDefinitionParentOID OBJECT-TYPE
    SYNTAX          OBJECT IDENTIFIER
    MAX-ACCESS      read-create
    STATUS          current
    DESCRIPTION     
            "The OID of the parent object for this instance"
    ::= { ptDSCCommandCodeDefinitionEntry 253 }

ptDSCCommandCodeDefinitionRowStatus OBJECT-TYPE
    SYNTAX          RowStatus
    MAX-ACCESS      read-create
    STATUS          current
    DESCRIPTION     
            "The row status for the DSCCommandCodeDefinition table"
    ::= { ptDSCCommandCodeDefinitionEntry 254 }

ptDSCCommandCodeDefinitionIndex OBJECT-TYPE
    SYNTAX          Integer32 (-2147483648..2147483647)
    MAX-ACCESS      not-accessible
    STATUS          current
    DESCRIPTION     
            "The row number for the DSCCommandCodeDefinition table"
    ::= { ptDSCCommandCodeDefinitionEntry 255 }

ptDSCRealmDefinitions OBJECT IDENTIFIER
    ::= { ptDSCDSCDefinitions 1848 }

ptDSCRealmDefinitionsTable OBJECT-TYPE
    SYNTAX          SEQUENCE OF PtDSCRealmDefinitionsEntry
    MAX-ACCESS      not-accessible
    STATUS          current
    DESCRIPTION     
            "No description supplied in the proxy config file."
    ::= { ptDSCRealmDefinitions 1 }

ptDSCRealmDefinitionsEntry OBJECT-TYPE
    SYNTAX          PtDSCRealmDefinitionsEntry
    MAX-ACCESS      not-accessible
    STATUS          current
    DESCRIPTION     
            "A sequence of DSCRealmDefinitions attributes."
    INDEX           { ptConnGroupIndex, ptDSCRealmDefinitionsDSCIndex, 
                      ptDSCRealmDefinitionsDSCDefinitionsIndex, 
                      ptDSCRealmDefinitionsIndex }
    ::= { ptDSCRealmDefinitionsTable 1 }

PtDSCRealmDefinitionsEntry ::=
    SEQUENCE {
        ptDSCRealmDefinitionsDSCIndex   Integer32,
        ptDSCRealmDefinitionsDSCDefinitionsIndex        Integer32,
        ptDSCRealmDefinitionsParentOID  OBJECT IDENTIFIER,
        ptDSCRealmDefinitionsRowStatus  RowStatus,
        ptDSCRealmDefinitionsIndex      Integer32
    }

ptDSCRealmDefinitionsDSCIndex OBJECT-TYPE
    SYNTAX          Integer32 (-2147483648..2147483647)
    MAX-ACCESS      not-accessible
    STATUS          current
    DESCRIPTION     
            "This is the index of the parent type for this object.
             This parent type is DSC."
    ::= { ptDSCRealmDefinitionsEntry 242 }

ptDSCRealmDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCRealmDefinitionsEntry 243 }

ptDSCRealmDefinitionsParentOID OBJECT-TYPE
    SYNTAX          OBJECT IDENTIFIER
    MAX-ACCESS      read-create
    STATUS          current
    DESCRIPTION     
            "The OID of the parent object for this instance"
    ::= { ptDSCRealmDefinitionsEntry 253 }

ptDSCRealmDefinitionsRowStatus OBJECT-TYPE
    SYNTAX          RowStatus
    MAX-ACCESS      read-create
    STATUS          current
    DESCRIPTION     
            "The row status for the DSCRealmDefinitions table"
    ::= { ptDSCRealmDefinitionsEntry 254 }

ptDSCRealmDefinitionsIndex OBJECT-TYPE
    SYNTAX          Integer32 (-2147483648..2147483647)
    MAX-ACCESS      not-accessible
    STATUS          current
    DESCRIPTION     
            "The row number for the DSCRealmDefinitions table"
    ::= { ptDSCRealmDefinitionsEntry 255 }

ptDSCRealmDefinition OBJECT IDENTIFIER
    ::= { ptDSCRealmDefinitions 1849 }

ptDSCRealmDefinitionTable OBJECT-TYPE
    SYNTAX          SEQUENCE OF PtDSCRealmDefinitionEntry
    MAX-ACCESS      not-accessible
    STATUS          current
    DESCRIPTION     
            "No description supplied in the proxy config file."
    ::= { ptDSCRealmDefinition 1 }

ptDSCRealmDefinitionEntry OBJECT-TYPE
    SYNTAX          PtDSCRealmDefinitionEntry
    MAX-ACCESS      not-accessible
    STATUS          current
    DESCRIPTION     
            "A sequence of DSCRealmDefinition attributes."
    INDEX           { ptConnGroupIndex, ptDSCRealmDefinitionDSCIndex, 
                      ptDSCRealmDefinitionDSCDefinitionsIndex, 
                      ptDSCRealmDefinitionRealmDefinitionsIndex, 
                      ptDSCRealmDefinitionIndex }
    ::= { ptDSCRealmDefinitionTable 1 }

PtDSCRealmDefinitionEntry ::=
    SEQUENCE {
        ptDSCRealmDefinitionRealm       DisplayString,
        ptDSCRealmDefinitionAlias       DisplayString,
        ptDSCRealmDefinitionComment     DisplayString,
        ptDSCRealmDefinitionDSCIndex    Integer32,
        ptDSCRealmDefinitionDSCDefinitionsIndex       Integer32,
        ptDSCRealmDefinitionRealmDefinitionsIndex         Integer32,
        ptDSCRealmDefinitionParentOID   OBJECT IDENTIFIER,
        ptDSCRealmDefinitionRowStatus   RowStatus,
        ptDSCRealmDefinitionIndex       Integer32
    }

ptDSCRealmDefinitionRealm OBJECT-TYPE
    SYNTAX          DisplayString (SIZE(0..255))
    MAX-ACCESS      read-create
    STATUS          current
    DESCRIPTION     
            "Realm definition. \nValid values: FQDN format with at least one dot (.) character."
    ::= { ptDSCRealmDefinitionEntry 1 }

ptDSCRealmDefinitionAlias OBJECT-TYPE
    SYNTAX          DisplayString (SIZE(0..255))
    MAX-ACCESS      read-create
    STATUS          current
    DESCRIPTION     
            "Alias used to identify the Realm. \nUsed as a short name to identify the realm for ease of provisioning. \nValid values: alphanumeric characters, dashes, underscores, spaces, and dots (maximum size of 64). Cannot start the name with reserved dsc_ or pt_ (case insensitive)."
    ::= { ptDSCRealmDefinitionEntry 2 }

ptDSCRealmDefinitionComment OBJECT-TYPE
    SYNTAX          DisplayString (SIZE(0..255))
    MAX-ACCESS      read-create
    STATUS          current
    DESCRIPTION     
            "Realm Definition optional comment for supplementary information. \nValid values: free-form string of maximum size 64 characters."
    ::= { ptDSCRealmDefinitionEntry 3 }

ptDSCRealmDefinitionDSCIndex OBJECT-TYPE
    SYNTAX          Integer32 (-2147483648..2147483647)
    MAX-ACCESS      not-accessible
    STATUS          current
    DESCRIPTION     
            "This is the index of the parent type for this object.
             This parent type is DSC."
    ::= { ptDSCRealmDefinitionEntry 242 }

ptDSCRealmDefinitionDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCRealmDefinitionEntry 243 }

ptDSCRealmDefinitionRealmDefinitionsIndex OBJECT-TYPE
    SYNTAX          Integer32 (-2147483648..2147483647)
    MAX-ACCESS      not-accessible
    STATUS          current
    DESCRIPTION     
            "This is the index of the parent type for this object.
             This parent type is RealmDefinitions."
    ::= { ptDSCRealmDefinitionEntry 244 }

ptDSCRealmDefinitionParentOID OBJECT-TYPE
    SYNTAX          OBJECT IDENTIFIER
    MAX-ACCESS      read-create
    STATUS          current
    DESCRIPTION     
            "The OID of the parent object for this instance"
    ::= { ptDSCRealmDefinitionEntry 253 }

ptDSCRealmDefinitionRowStatus OBJECT-TYPE
    SYNTAX          RowStatus
    MAX-ACCESS      read-create
    STATUS          current
    DESCRIPTION     
            "The row status for the DSCRealmDefinition table"
    ::= { ptDSCRealmDefinitionEntry 254 }

ptDSCRealmDefinitionIndex OBJECT-TYPE
    SYNTAX          Integer32 (-2147483648..2147483647)
    MAX-ACCESS      not-accessible
    STATUS          current
    DESCRIPTION     
            "The row number for the DSCRealmDefinition table"
    ::= { ptDSCRealmDefinitionEntry 255 }

ptDSCMobileCodesDefinitions OBJECT IDENTIFIER
    ::= { ptDSCDSCDefinitions 1861 }

ptDSCMobileCodesDefinitionsTable OBJECT-TYPE
    SYNTAX          SEQUENCE OF PtDSCMobileCodesDefinitionsEntry
    MAX-ACCESS      not-accessible
    STATUS          current
    DESCRIPTION     
            "No description supplied in the proxy config file."
    ::= { ptDSCMobileCodesDefinitions 1 }

ptDSCMobileCodesDefinitionsEntry OBJECT-TYPE
    SYNTAX          PtDSCMobileCodesDefinitionsEntry
    MAX-ACCESS      not-accessible
    STATUS          current
    DESCRIPTION     
            "A sequence of DSCMobileCodesDefinitions attributes."
    INDEX           { ptConnGroupIndex, 
                      ptDSCMobileCodesDefinitionsDSCIndex, 
                      ptDSCMobileCodesDefinitionsDSCDefinitionsIndex, 
                      ptDSCMobileCodesDefinitionsIndex }
    ::= { ptDSCMobileCodesDefinitionsTable 1 }

PtDSCMobileCodesDefinitionsEntry ::=
    SEQUENCE {
        ptDSCMobileCodesDefinitionsSearchType     INTEGER,
        ptDSCMobileCodesDefinitionsDSCIndex   Integer32,
        ptDSCMobileCodesDefinitionsDSCDefinitionsIndex              Integer32,
        ptDSCMobileCodesDefinitionsParentOID    OBJECT IDENTIFIER,
        ptDSCMobileCodesDefinitionsRowStatus    RowStatus,
        ptDSCMobileCodesDefinitionsIndex Integer32
    }

ptDSCMobileCodesDefinitionsSearchType OBJECT-TYPE
    SYNTAX          INTEGER { exactMatch(1), longestFromRight(2), 
                        longestFromLeft(3) }
    MAX-ACCESS      read-only
    STATUS          current
    DESCRIPTION     
            "Search Type (LONGEST FROM LEFT) \nMobile Codes represent the IMSI Mobile Code (MCC) and Mobile Network Code (MNC) values. \nThis table defines the MCC MNC values whose MNC values are 3 digits long. It is used to lookup the length of the MNC value ( 2 or 3 digits ) based on the MCC value. The Diameter Routing Modification command replace-dest-realm-from-imsi perfoms a lookup of the AVP IMSI in this table. \nWhen looking up MCC MNC values, the search type is used to figure out the MCC and MNC digits from the IMSI value. \nIf the search matches an entry in the table, the MNC is 3 digits. If no match is found, the MNC is 2 digits. \nPopulate the table with MCC whose MNC values are all 3 digits. If an MCC value has both 2 digits and 3 digits MNC values then include only the 3 digits MNC values in the table using the format MCCMNC (6 digits). \nDefault value: LONGEST FROM LEFT."
    ::= { ptDSCMobileCodesDefinitionsEntry 1 }

ptDSCMobileCodesDefinitionsDSCIndex OBJECT-TYPE
    SYNTAX          Integer32 (-2147483648..2147483647)
    MAX-ACCESS      not-accessible
    STATUS          current
    DESCRIPTION     
            "This is the index of the parent type for this object.
             This parent type is DSC."
    ::= { ptDSCMobileCodesDefinitionsEntry 242 }

ptDSCMobileCodesDefinitionsDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCMobileCodesDefinitionsEntry 243 }

ptDSCMobileCodesDefinitionsParentOID OBJECT-TYPE
    SYNTAX          OBJECT IDENTIFIER
    MAX-ACCESS      read-create
    STATUS          current
    DESCRIPTION     
            "The OID of the parent object for this instance"
    ::= { ptDSCMobileCodesDefinitionsEntry 253 }

ptDSCMobileCodesDefinitionsRowStatus OBJECT-TYPE
    SYNTAX          RowStatus
    MAX-ACCESS      read-create
    STATUS          current
    DESCRIPTION     
            "The row status for the DSCMobileCodesDefinitions table"
    ::= { ptDSCMobileCodesDefinitionsEntry 254 }

ptDSCMobileCodesDefinitionsIndex OBJECT-TYPE
    SYNTAX          Integer32 (-2147483648..2147483647)
    MAX-ACCESS      not-accessible
    STATUS          current
    DESCRIPTION     
            "The row number for the DSCMobileCodesDefinitions table"
    ::= { ptDSCMobileCodesDefinitionsEntry 255 }

ptDSCIMSIMobileCode OBJECT IDENTIFIER
    ::= { ptDSCMobileCodesDefinitions 1862 }

ptDSCIMSIMobileCodeTable OBJECT-TYPE
    SYNTAX          SEQUENCE OF PtDSCIMSIMobileCodeEntry
    MAX-ACCESS      not-accessible
    STATUS          current
    DESCRIPTION     
            "No description supplied in the proxy config file."
    ::= { ptDSCIMSIMobileCode 1 }

ptDSCIMSIMobileCodeEntry OBJECT-TYPE
    SYNTAX          PtDSCIMSIMobileCodeEntry
    MAX-ACCESS      not-accessible
    STATUS          current
    DESCRIPTION     
            "A sequence of DSCIMSIMobileCode attributes."
    INDEX           { ptConnGroupIndex, ptDSCIMSIMobileCodeDSCIndex, 
                      ptDSCIMSIMobileCodeDSCDefinitionsIndex, 
                      ptDSCIMSIMobileCodeMobileCodesDefinitionsIndex, 
                      ptDSCIMSIMobileCodeIndex }
    ::= { ptDSCIMSIMobileCodeTable 1 }

PtDSCIMSIMobileCodeEntry ::=
    SEQUENCE {
        ptDSCIMSIMobileCodeMCCMNC       DisplayString,
        ptDSCIMSIMobileCodeDSCIndex     Integer32,
        ptDSCIMSIMobileCodeDSCDefinitionsIndex      Integer32,
        ptDSCIMSIMobileCodeMobileCodesDefinitionsIndex              Integer32,
        ptDSCIMSIMobileCodeParentOID    OBJECT IDENTIFIER,
        ptDSCIMSIMobileCodeRowStatus    RowStatus,
        ptDSCIMSIMobileCodeIndex        Integer32
    }

ptDSCIMSIMobileCodeMCCMNC OBJECT-TYPE
    SYNTAX          DisplayString (SIZE(0..255))
    MAX-ACCESS      read-only
    STATUS          current
    DESCRIPTION     
            "Mobile Country Code/Mobile Network Code combination \nA 3 digits MCCMNC value defines and groups all MCC entries that have only 3 digits MNC values. \nA 6 digits MCCMNC value defines MCC MNC entieis that have both 2 and 3 digits MNC values by \nincluding the exact 3 digits MNC value. \nBy default, an MCCMNC entry that does not exist in this table is assumed to have 2 digits MNC values. \nExample: 123456 (MCC is 132 and MNC is 456, other IMSI values that start with 123 have 2 digits MNC). \n789 (all IMSI values that start with 789 have 3 digits MNCs). \nValid values: 3 digits or 6 digits integer."
    ::= { ptDSCIMSIMobileCodeEntry 1 }

ptDSCIMSIMobileCodeDSCIndex OBJECT-TYPE
    SYNTAX          Integer32 (-2147483648..2147483647)
    MAX-ACCESS      not-accessible
    STATUS          current
    DESCRIPTION     
            "This is the index of the parent type for this object.
             This parent type is DSC."
    ::= { ptDSCIMSIMobileCodeEntry 242 }

ptDSCIMSIMobileCodeDSCDefinitionsIndex OBJECT-TYPE
    SYNTAX          Integer32 (-2147483648..2147483647)
    MAX-ACCESS      not-accessible
    STATUS          current
    DESCRIPTION     
            "This is the index of the parent type for this object.
             This parent type is DSCDefinitions."
    ::= { ptDSCIMSIMobileCodeEntry 243 }

ptDSCIMSIMobileCodeMobileCodesDefinitionsIndex OBJECT-TYPE
    SYNTAX          Integer32 (-2147483648..2147483647)
    MAX-ACCESS      not-accessible
    STATUS          current
    DESCRIPTION     
            "This is the index of the parent type for this object.
             This parent type is MobileCodesDefinitions."
    ::= { ptDSCIMSIMobileCodeEntry 244 }

ptDSCIMSIMobileCodeParentOID OBJECT-TYPE
    SYNTAX          OBJECT IDENTIFIER
    MAX-ACCESS      read-create
    STATUS          current
    DESCRIPTION     
            "The OID of the parent object for this instance"
    ::= { ptDSCIMSIMobileCodeEntry 253 }

ptDSCIMSIMobileCodeRowStatus OBJECT-TYPE
    SYNTAX          RowStatus
    MAX-ACCESS      read-create
    STATUS          current
    DESCRIPTION     
            "The row status for the DSCIMSIMobileCode table"
    ::= { ptDSCIMSIMobileCodeEntry 254 }

ptDSCIMSIMobileCodeIndex OBJECT-TYPE
    SYNTAX          Integer32 (-2147483648..2147483647)
    MAX-ACCESS      not-accessible
    STATUS          current
    DESCRIPTION     
            "The row number for the DSCIMSIMobileCode table"
    ::= { ptDSCIMSIMobileCodeEntry 255 }

ptiwfIWFConfiguration OBJECT IDENTIFIER
    ::= { ptConnGroup 1901 }

ptiwfIWFConfigurationTable OBJECT-TYPE
    SYNTAX          SEQUENCE OF PtiwfIWFConfigurationEntry
    MAX-ACCESS      not-accessible
    STATUS          current
    DESCRIPTION     
            "No description supplied in the proxy config file."
    ::= { ptiwfIWFConfiguration 1 }

ptiwfIWFConfigurationEntry OBJECT-TYPE
    SYNTAX          PtiwfIWFConfigurationEntry
    MAX-ACCESS      not-accessible
    STATUS          current
    DESCRIPTION     
            "A sequence of iwfIWFConfiguration attributes."
    INDEX           { ptConnGroupIndex, ptiwfIWFConfigurationIndex }
    ::= { ptiwfIWFConfigurationTable 1 }

PtiwfIWFConfigurationEntry ::=
    SEQUENCE {
        ptiwfIWFConfigurationIWFLicense INTEGER,
        ptiwfIWFConfigurationIWFHSSLicense  INTEGER,
        ptiwfIWFConfigurationIWFEIRLicense  INTEGER,
        ptiwfIWFConfigurationIWFSMSLicense  INTEGER,
        ptiwfIWFConfigurationTransactionTimeout       Integer32,
        ptiwfIWFConfigurationMaxTracingPerInterval          INTEGER,
        ptiwfIWFConfigurationTracingInterval    INTEGER,
        ptiwfIWFConfigurationErrors     INTEGER,
        ptiwfIWFConfigurationSetupManagement    INTEGER,
        ptiwfIWFConfigurationExecutionTrace   INTEGER,
        ptiwfIWFConfigurationDistributionManagement           INTEGER,
        ptiwfIWFConfigurationActions    INTEGER,
        ptiwfIWFConfigurationParentOID  OBJECT IDENTIFIER,
        ptiwfIWFConfigurationRowStatus  RowStatus,
        ptiwfIWFConfigurationIndex      Integer32
    }

ptiwfIWFConfigurationIWFLicense OBJECT-TYPE
    SYNTAX          INTEGER { unlicensed(0), licensed(1) }
    MAX-ACCESS      read-only
    STATUS          current
    DESCRIPTION     
            "IWF feature license (UNLICENSED/LICENSED). \nIf the IWF is unlicensed, the IWF (SS7 and Diameter) traffic cannot be activated."
    ::= { ptiwfIWFConfigurationEntry 1 }

ptiwfIWFConfigurationIWFHSSLicense OBJECT-TYPE
    SYNTAX          INTEGER { unlicensed(0), licensed(1) }
    MAX-ACCESS      read-only
    STATUS          current
    DESCRIPTION     
            "IWF HSS mapping license (UNLICENSED/LICENSED). \nIf the IWF HSS is unlicensed, related HSS traffic scenarios trigger appropriate error handling. A Diameter UNABLE_TO_DELIVER is returned for unsupported Diameter requests while a TCAP Abort due to procedure failure is returned for unsupported TCAP operations."
    ::= { ptiwfIWFConfigurationEntry 2 }

ptiwfIWFConfigurationIWFEIRLicense OBJECT-TYPE
    SYNTAX          INTEGER { unlicensed(0), licensed(1) }
    MAX-ACCESS      read-only
    STATUS          current
    DESCRIPTION     
            "IWF EIR mapping license (UNLICENSED/LICENSED). \nIf the IWF EIR is unlicensed, the EIR traffic scenario triggers appropriate error handling. A Diameter UNABLE_TO_DELIVER is returned for unsupported Diameter requests while a TCAP Abort due to procedure failure is returned for unsupported TCAP operations."
    ::= { ptiwfIWFConfigurationEntry 3 }

ptiwfIWFConfigurationIWFSMSLicense OBJECT-TYPE
    SYNTAX          INTEGER { unlicensed(0), licensed(1) }
    MAX-ACCESS      read-only
    STATUS          current
    DESCRIPTION     
            "IWF SMS mapping license (UNLICENSED/LICENSED). \nIf the IWF SMS is unlicensed, related SMS traffic scenarios trigger appropriate error handling. A Diameter UNABLE_TO_DELIVER is returned for unsupported Diameter requests while a TCAP Abort due to procedure failure is returned for unsupported TCAP operations."
    ::= { ptiwfIWFConfigurationEntry 4 }

ptiwfIWFConfigurationTransactionTimeout OBJECT-TYPE
    SYNTAX          Integer32 (10..1800)
    MAX-ACCESS      read-create
    STATUS          current
    DESCRIPTION     
            "IWF Transaction Timeout (10 to 1800 seconds). \nPending transaction timeout for both the SS7 and Diameter networks in seconds. \nDefault value: 120 seconds."
    ::= { ptiwfIWFConfigurationEntry 5 }

ptiwfIWFConfigurationMaxTracingPerInterval OBJECT-TYPE
    SYNTAX          INTEGER { disabled(0) }
    MAX-ACCESS      read-create
    STATUS          current
    DESCRIPTION     
            "Maximum number of traced messages logged in the given interval (0 to 99). \nMessage tracing, if enabled, assigns a unique identifier to incoming messages matching a Node Mapping record. The message can then be traced throughout the SS7 and Diameter applications for debugging purposes. \nIf a Diameter or SS7 message is already traced, IWF uses the provided message ID. \nSet to 0 to disable message tracing. \nDefault value: 10."
    ::= { ptiwfIWFConfigurationEntry 6 }

ptiwfIWFConfigurationTracingInterval OBJECT-TYPE
    SYNTAX          INTEGER { five(300000), ten(600000), fifteen(900000), 
                        twenty(1200000), thirty(1800000) }
    MAX-ACCESS      read-create
    STATUS          current
    DESCRIPTION     
            "Message Tracing logging interval (5, 10, 15, 20, and 30 minutes). \nDefault value: FIVE (5) minutes."
    ::= { ptiwfIWFConfigurationEntry 7 }

ptiwfIWFConfigurationErrors OBJECT-TYPE
    SYNTAX          INTEGER { notLogged(0), logged(1) }
    MAX-ACCESS      read-create
    STATUS          current
    DESCRIPTION     
            "Enable or disable the logging of IWF error messages to the debuglog (NOT LOGGED/LOGGED). \nThe logging of IWF errors should be set to LOGGED for all production systems. \nDefault value: LOGGED."
    ::= { ptiwfIWFConfigurationEntry 8 }

ptiwfIWFConfigurationSetupManagement OBJECT-TYPE
    SYNTAX          INTEGER { notLogged(0), logged(1) }
    MAX-ACCESS      read-create
    STATUS          current
    DESCRIPTION     
            "Enable or disable the logging of startup and setup information to the debuglog (NOT LOGGED/LOGGED). \nThese logs are not related to traffic processing and have no impact on the performance of a running system. \nThe logging of IWF startup and setup information should be set to LOGGED for most production systems. \nDefault value: LOGGED."
    ::= { ptiwfIWFConfigurationEntry 9 }

ptiwfIWFConfigurationExecutionTrace OBJECT-TYPE
    SYNTAX          INTEGER { notLogged(0), logged(1) }
    MAX-ACCESS      read-create
    STATUS          current
    DESCRIPTION     
            "Enable or disable the logging of the internal execution of the IWF traffic to the debuglog (NOT LOGGED/LOGGED). \nThe resultant messages are intended for Sonus Networks engineering staff and are not intended for customer use. \nThe logging of execution trace must be set to NOT LOGGED on all production systems so that the CPU is not unduly taxed. \nDefault value: NOT LOGGED."
    ::= { ptiwfIWFConfigurationEntry 10 }

ptiwfIWFConfigurationDistributionManagement OBJECT-TYPE
    SYNTAX          INTEGER { notLogged(0), logged(1) }
    MAX-ACCESS      read-create
    STATUS          current
    DESCRIPTION     
            "Enable or disable the logging of inter-IWF process communication to the debuglog (NOT LOGGED/LOGGED). \nThe resultant messages are intended for Sonus Networks engineering staff and are not intended for customer use. \nThe logging of inter-process communication must be set to NOT LOGGED on all production systems so that the CPU is not unduly taxed. \nDefault value: NOT LOGGED."
    ::= { ptiwfIWFConfigurationEntry 11 }

ptiwfIWFConfigurationActions OBJECT-TYPE
    SYNTAX          INTEGER { activateTraffic(1), deactivateTraffic(2), 
                        resetTracing(3), restoreDebugDefaults(4) }
    MAX-ACCESS      read-create
    STATUS          current
    DESCRIPTION     
            "The OID of all possible actions for this instance"
    ::= { ptiwfIWFConfigurationEntry 252 }

ptiwfIWFConfigurationParentOID OBJECT-TYPE
    SYNTAX          OBJECT IDENTIFIER
    MAX-ACCESS      read-create
    STATUS          current
    DESCRIPTION     
            "The OID of the parent object for this instance"
    ::= { ptiwfIWFConfigurationEntry 253 }

ptiwfIWFConfigurationRowStatus OBJECT-TYPE
    SYNTAX          RowStatus
    MAX-ACCESS      read-create
    STATUS          current
    DESCRIPTION     
            "The row status for the iwfIWFConfiguration table"
    ::= { ptiwfIWFConfigurationEntry 254 }

ptiwfIWFConfigurationIndex OBJECT-TYPE
    SYNTAX          Integer32 (-2147483648..2147483647)
    MAX-ACCESS      not-accessible
    STATUS          current
    DESCRIPTION     
            "The row number for the iwfIWFConfiguration table"
    ::= { ptiwfIWFConfigurationEntry 255 }

ptiwfIWFDiameter OBJECT IDENTIFIER
    ::= { ptConnGroup 1902 }

ptiwfIWFDiameterTable OBJECT-TYPE
    SYNTAX          SEQUENCE OF PtiwfIWFDiameterEntry
    MAX-ACCESS      not-accessible
    STATUS          current
    DESCRIPTION     
            "No description supplied in the proxy config file."
    ::= { ptiwfIWFDiameter 1 }

ptiwfIWFDiameterEntry OBJECT-TYPE
    SYNTAX          PtiwfIWFDiameterEntry
    MAX-ACCESS      not-accessible
    STATUS          current
    DESCRIPTION     
            "A sequence of iwfIWFDiameter attributes."
    INDEX           { ptConnGroupIndex, ptiwfIWFDiameterIndex }
    ::= { ptiwfIWFDiameterTable 1 }

PtiwfIWFDiameterEntry ::=
    SEQUENCE {
        ptiwfIWFDiameterIWFDiameterID   DisplayString,
        ptiwfIWFDiameterIWFDiameterRealm DisplayString,
        ptiwfIWFDiameterDSCDiameterID   DisplayString,
        ptiwfIWFDiameterDSCDiameterRealm DisplayString,
        ptiwfIWFDiameterDSCIWFUAPort    Integer32,
        ptiwfIWFDiameterConnectivityStatus  INTEGER,
        ptiwfIWFDiameterParentOID       OBJECT IDENTIFIER,
        ptiwfIWFDiameterRowStatus       RowStatus,
        ptiwfIWFDiameterIndex           Integer32
    }

ptiwfIWFDiameterIWFDiameterID OBJECT-TYPE
    SYNTAX          DisplayString (SIZE(0..255))
    MAX-ACCESS      read-create
    STATUS          current
    DESCRIPTION     
            "Diameter Identifier of the IWF. \nCan only be modified when the IWF traffic is deactivated. \nValid values: FQDN format (as per the DSC Node Diameter ID validation)."
    ::= { ptiwfIWFDiameterEntry 1 }

ptiwfIWFDiameterIWFDiameterRealm OBJECT-TYPE
    SYNTAX          DisplayString (SIZE(0..255))
    MAX-ACCESS      read-create
    STATUS          current
    DESCRIPTION     
            "Diameter Realm of the IWF. \nCan only be modified when the IWF traffic is deactivated. \nValid values: FQDN format (as per the DSC Realm Definition validation)."
    ::= { ptiwfIWFDiameterEntry 2 }

ptiwfIWFDiameterDSCDiameterID OBJECT-TYPE
    SYNTAX          DisplayString (SIZE(0..255))
    MAX-ACCESS      read-create
    STATUS          current
    DESCRIPTION     
            "Diameter Identifier of the DSC. \nCan only be modified when the IWF traffic is deactivated. \nValid values: FQDN format (as per the DSC Node Diameter ID validation)."
    ::= { ptiwfIWFDiameterEntry 3 }

ptiwfIWFDiameterDSCDiameterRealm OBJECT-TYPE
    SYNTAX          DisplayString (SIZE(0..255))
    MAX-ACCESS      read-create
    STATUS          current
    DESCRIPTION     
            "Diameter Realm of the DSC. \nCan only be modified when the IWF traffic is deactivated. \nValid values: FQDN format (as per the DSC Realm Definition validation)."
    ::= { ptiwfIWFDiameterEntry 4 }

ptiwfIWFDiameterDSCIWFUAPort OBJECT-TYPE
    SYNTAX          Integer32 (-2147483648..2147483647)
    MAX-ACCESS      read-create
    STATUS          current
    DESCRIPTION     
            "Associated DSC IWF UA port for Diameter routing (1-65535). \nThe IWF will connect locally on each slot to this port. The DSC must define an associated TCP Transport Server as well as an ADN of type UA. Corresponding ADN Connections Transport Type should be set to SERVER ONLY. \nCan only be modified when the IWF traffic is deactivated. \nDefault value: 8204."
    ::= { ptiwfIWFDiameterEntry 5 }

ptiwfIWFDiameterConnectivityStatus OBJECT-TYPE
    SYNTAX          INTEGER { inactive(0), notConnected(1), connected(2) }
    MAX-ACCESS      read-only
    STATUS          current
    DESCRIPTION     
            "Diameter Connectivity Status (INACTIVE, NOT CONNECTED, CONNECTED). \nBased on the per slot connectivity status. \nCONNECTED will be displayed as soon as a Diameter connection on any slot is connected. \nAssociated to alarm 1901 (IWF Diameter Down)."
    ::= { ptiwfIWFDiameterEntry 7 }

ptiwfIWFDiameterParentOID OBJECT-TYPE
    SYNTAX          OBJECT IDENTIFIER
    MAX-ACCESS      read-create
    STATUS          current
    DESCRIPTION     
            "The OID of the parent object for this instance"
    ::= { ptiwfIWFDiameterEntry 253 }

ptiwfIWFDiameterRowStatus OBJECT-TYPE
    SYNTAX          RowStatus
    MAX-ACCESS      read-create
    STATUS          current
    DESCRIPTION     
            "The row status for the iwfIWFDiameter table"
    ::= { ptiwfIWFDiameterEntry 254 }

ptiwfIWFDiameterIndex OBJECT-TYPE
    SYNTAX          Integer32 (-2147483648..2147483647)
    MAX-ACCESS      not-accessible
    STATUS          current
    DESCRIPTION     
            "The row number for the iwfIWFDiameter table"
    ::= { ptiwfIWFDiameterEntry 255 }

ptiwfDiameterConnections OBJECT IDENTIFIER
    ::= { ptiwfIWFDiameter 1903 }

ptiwfDiameterConnectionsTable OBJECT-TYPE
    SYNTAX          SEQUENCE OF PtiwfDiameterConnectionsEntry
    MAX-ACCESS      not-accessible
    STATUS          current
    DESCRIPTION     
            "No description supplied in the proxy config file."
    ::= { ptiwfDiameterConnections 1 }

ptiwfDiameterConnectionsEntry OBJECT-TYPE
    SYNTAX          PtiwfDiameterConnectionsEntry
    MAX-ACCESS      not-accessible
    STATUS          current
    DESCRIPTION     
            "A sequence of iwfDiameterConnections attributes."
    INDEX           { ptConnGroupIndex, 
                      ptiwfDiameterConnectionsIWFDiameterIndex, 
                      ptiwfDiameterConnectionsIndex }
    ::= { ptiwfDiameterConnectionsTable 1 }

PtiwfDiameterConnectionsEntry ::=
    SEQUENCE {
        ptiwfDiameterConnectionsIWFDiameterIndex        Integer32,
        ptiwfDiameterConnectionsParentOID OBJECT IDENTIFIER,
        ptiwfDiameterConnectionsRowStatus RowStatus,
        ptiwfDiameterConnectionsIndex   Integer32
    }

ptiwfDiameterConnectionsIWFDiameterIndex OBJECT-TYPE
    SYNTAX          Integer32 (-2147483648..2147483647)
    MAX-ACCESS      not-accessible
    STATUS          current
    DESCRIPTION     
            "This is the index of the parent type for this object.
             This parent type is IWFDiameter."
    ::= { ptiwfDiameterConnectionsEntry 242 }

ptiwfDiameterConnectionsParentOID OBJECT-TYPE
    SYNTAX          OBJECT IDENTIFIER
    MAX-ACCESS      read-create
    STATUS          current
    DESCRIPTION     
            "The OID of the parent object for this instance"
    ::= { ptiwfDiameterConnectionsEntry 253 }

ptiwfDiameterConnectionsRowStatus OBJECT-TYPE
    SYNTAX          RowStatus
    MAX-ACCESS      read-create
    STATUS          current
    DESCRIPTION     
            "The row status for the iwfDiameterConnections table"
    ::= { ptiwfDiameterConnectionsEntry 254 }

ptiwfDiameterConnectionsIndex OBJECT-TYPE
    SYNTAX          Integer32 (-2147483648..2147483647)
    MAX-ACCESS      not-accessible
    STATUS          current
    DESCRIPTION     
            "The row number for the iwfDiameterConnections table"
    ::= { ptiwfDiameterConnectionsEntry 255 }

ptiwfDiameterConnection OBJECT IDENTIFIER
    ::= { ptiwfDiameterConnections 1904 }

ptiwfDiameterConnectionTable OBJECT-TYPE
    SYNTAX          SEQUENCE OF PtiwfDiameterConnectionEntry
    MAX-ACCESS      not-accessible
    STATUS          current
    DESCRIPTION     
            "No description supplied in the proxy config file."
    ::= { ptiwfDiameterConnection 1 }

ptiwfDiameterConnectionEntry OBJECT-TYPE
    SYNTAX          PtiwfDiameterConnectionEntry
    MAX-ACCESS      not-accessible
    STATUS          current
    DESCRIPTION     
            "A sequence of iwfDiameterConnection attributes."
    INDEX           { ptConnGroupIndex, 
                      ptiwfDiameterConnectionIWFDiameterIndex, 
                      ptiwfDiameterConnectionDiameterConnectionsIndex, 
                      ptiwfDiameterConnectionIndex }
    ::= { ptiwfDiameterConnectionTable 1 }

PtiwfDiameterConnectionEntry ::=
    SEQUENCE {
        ptiwfDiameterConnectionSlot     Integer32,
        ptiwfDiameterConnectionConnectivityStatus         INTEGER,
        ptiwfDiameterConnectionIWFDiameterIndex       Integer32,
        ptiwfDiameterConnectionDiameterConnectionsIndex               Integer32,
        ptiwfDiameterConnectionParentOID OBJECT IDENTIFIER,
        ptiwfDiameterConnectionRowStatus RowStatus,
        ptiwfDiameterConnectionIndex    Integer32
    }

ptiwfDiameterConnectionSlot OBJECT-TYPE
    SYNTAX          Integer32 (-2147483648..2147483647)
    MAX-ACCESS      read-only
    STATUS          current
    DESCRIPTION     
            "Associated slot of the Routing CPU for this Diameter Connection."
    ::= { ptiwfDiameterConnectionEntry 1 }

ptiwfDiameterConnectionConnectivityStatus OBJECT-TYPE
    SYNTAX          INTEGER { inactive(0), notConnected(1), connected(2) }
    MAX-ACCESS      read-only
    STATUS          current
    DESCRIPTION     
            "Diameter Connectivity Status (INACTIVE, NOT CONNECTED, CONNECTED). \nAssociated to alarm 1903 (IWF Diameter Connection Down)."
    ::= { ptiwfDiameterConnectionEntry 2 }

ptiwfDiameterConnectionIWFDiameterIndex OBJECT-TYPE
    SYNTAX          Integer32 (-2147483648..2147483647)
    MAX-ACCESS      not-accessible
    STATUS          current
    DESCRIPTION     
            "This is the index of the parent type for this object.
             This parent type is IWFDiameter."
    ::= { ptiwfDiameterConnectionEntry 242 }

ptiwfDiameterConnectionDiameterConnectionsIndex OBJECT-TYPE
    SYNTAX          Integer32 (-2147483648..2147483647)
    MAX-ACCESS      not-accessible
    STATUS          current
    DESCRIPTION     
            "This is the index of the parent type for this object.
             This parent type is DiameterConnections."
    ::= { ptiwfDiameterConnectionEntry 243 }

ptiwfDiameterConnectionParentOID OBJECT-TYPE
    SYNTAX          OBJECT IDENTIFIER
    MAX-ACCESS      read-create
    STATUS          current
    DESCRIPTION     
            "The OID of the parent object for this instance"
    ::= { ptiwfDiameterConnectionEntry 253 }

ptiwfDiameterConnectionRowStatus OBJECT-TYPE
    SYNTAX          RowStatus
    MAX-ACCESS      read-create
    STATUS          current
    DESCRIPTION     
            "The row status for the iwfDiameterConnection table"
    ::= { ptiwfDiameterConnectionEntry 254 }

ptiwfDiameterConnectionIndex OBJECT-TYPE
    SYNTAX          Integer32 (-2147483648..2147483647)
    MAX-ACCESS      not-accessible
    STATUS          current
    DESCRIPTION     
            "The row number for the iwfDiameterConnection table"
    ::= { ptiwfDiameterConnectionEntry 255 }

ptiwfIWFSS7 OBJECT IDENTIFIER
    ::= { ptConnGroup 1905 }

ptiwfIWFSS7Table OBJECT-TYPE
    SYNTAX          SEQUENCE OF PtiwfIWFSS7Entry
    MAX-ACCESS      not-accessible
    STATUS          current
    DESCRIPTION     
            "No description supplied in the proxy config file."
    ::= { ptiwfIWFSS7 1 }

ptiwfIWFSS7Entry OBJECT-TYPE
    SYNTAX          PtiwfIWFSS7Entry
    MAX-ACCESS      not-accessible
    STATUS          current
    DESCRIPTION     
            "A sequence of iwfIWFSS7 attributes."
    INDEX           { ptConnGroupIndex, ptiwfIWFSS7Index }
    ::= { ptiwfIWFSS7Table 1 }

PtiwfIWFSS7Entry ::=
    SEQUENCE {
        ptiwfIWFSS7SCCPNA               Integer32,
        ptiwfIWFSS7DPC                  Integer32,
        ptiwfIWFSS7SCCPPAEncoding       INTEGER,
        ptiwfIWFSS7PCDisplayFormat      DisplayString,
        ptiwfIWFSS7PCRoutingFormat      DisplayString,
        ptiwfIWFSS7SCCPFiller           INTEGER,
        ptiwfIWFSS7ConnectivityStatus   INTEGER,
        ptiwfIWFSS7SGSNSS7Number        DisplayString,
        ptiwfIWFSS7IMSIRealm            DisplayString,
        ptiwfIWFSS7MateSTPLPC           Integer32,
        ptiwfIWFSS7MateSTPID            INTEGER,
        ptiwfIWFSS7HLRSS7Number         DisplayString,
        ptiwfIWFSS7ParentOID            OBJECT IDENTIFIER,
        ptiwfIWFSS7RowStatus            RowStatus,
        ptiwfIWFSS7Index                Integer32
    }

ptiwfIWFSS7SCCPNA OBJECT-TYPE
    SYNTAX          Integer32 (1..99)
    MAX-ACCESS      read-create
    STATUS          current
    DESCRIPTION     
            "Associated SCCP NA responsible for the IWF traffic (1 to 99). \nCan only be modified when the IWF traffic is deactivated. \nDefault value: 1"
    ::= { ptiwfIWFSS7Entry 1 }

ptiwfIWFSS7DPC OBJECT-TYPE
    SYNTAX          Integer32 (-2147483648..2147483647)
    MAX-ACCESS      read-create
    STATUS          current
    DESCRIPTION     
            "DPC of the SS7/MAP queries initiated by the IWF. \nWhen set, can never be reset to UNSET. \nTraffic cannot be activated if set to UNSET. \nValid values: point code format. \nDefault value: UNSET (start-up only)."
    ::= { ptiwfIWFSS7Entry 2 }

ptiwfIWFSS7SCCPPAEncoding OBJECT-TYPE
    SYNTAX          INTEGER { unset(-1), ansi(0), itu(1) }
    MAX-ACCESS      read-create
    STATUS          current
    DESCRIPTION     
            "SCCP Called and Calling Party Address encoding (UNSET, ANSI, ITU). \nUsed in the encoding of the 8th bit of the GTAI octet and the validation of the GTI. \nWhen set, can never be reset to UNSET. \nCan only be modified when the IWF traffic is deactivated. \nTraffic cannot be activated if set to UNSET. \nDefault value: UNSET (start-up only)."
    ::= { ptiwfIWFSS7Entry 3 }

ptiwfIWFSS7PCDisplayFormat OBJECT-TYPE
    SYNTAX          DisplayString (SIZE(0..255))
    MAX-ACCESS      read-create
    STATUS          current
    DESCRIPTION     
            "Point Code Display Format based on the SS7 Variant. \nMust be 14-bit compatible for ITU based SS7 variants, 16-bit for Japan, and 24-bit for ANSI and CHINA. \nWhen set, can never be reset to Undefined. \nCan only be modified when the IWF traffic is deactivated. \nTraffic cannot be activated if set to Undefined. \nValid values: Undefined, 8.8.8, 3.8.3, ff-ff, 4.4.6, 5.4.7, 3.4.7, 4.3.7, 4.6.4, 6.4.4, 4.7.3, 5.4.5, and Decimal. Note that the dash delimiter is also accepted (for example 8-8-8). \nDefault value: Undefined (start-up only)."
    ::= { ptiwfIWFSS7Entry 4 }

ptiwfIWFSS7PCRoutingFormat OBJECT-TYPE
    SYNTAX          DisplayString (SIZE(0..255))
    MAX-ACCESS      read-create
    STATUS          current
    DESCRIPTION     
            "Point Code Routing Format based on the SS7 Variant. \nMust be 14-bit compatible for ITU based SS7 variants, 16-bit for Japan, and 24-bit for ANSI and CHINA. The x-y or x-y-z fields must be 8-bit or less. \nWhen set, can never be reset to Undefined. \nCan only be modified when the IWF traffic is deactivated. \nTraffic cannot be activated if set to Undefined. \nValid values: Undefined, 8.8.8, 3.8.3, 4.4.6, 5.4.7, 3.4.7, 4.3.7, 4.6.4, 6.4.4, 4.7.3, and 5.4.5. \nDefault value: Undefined (start-up only)."
    ::= { ptiwfIWFSS7Entry 5 }

ptiwfIWFSS7SCCPFiller OBJECT-TYPE
    SYNTAX          INTEGER { zero(0), f(15) }
    MAX-ACCESS      read-create
    STATUS          current
    DESCRIPTION     
            "SCCP digits filler for Called and Calling PA encoding of odd length (ZERO, F). \nDefault value: F."
    ::= { ptiwfIWFSS7Entry 6 }

ptiwfIWFSS7ConnectivityStatus OBJECT-TYPE
    SYNTAX          INTEGER { inactive(0), notConnected(1), connected(2) }
    MAX-ACCESS      read-only
    STATUS          current
    DESCRIPTION     
            "SCCP NA Connectivity Status (INACTIVE, NOT CONNECTED, CONNECTED). \nBased on the per slot connectivity status. \nCONNECTED will be displayed as soon as an SCCP connection on any slot is connected. \nAssociated to alarm 1907 (IWF SS7 Down)."
    ::= { ptiwfIWFSS7Entry 7 }

ptiwfIWFSS7SGSNSS7Number OBJECT-TYPE
    SYNTAX          DisplayString (SIZE(0..255))
    MAX-ACCESS      read-create
    STATUS          current
    DESCRIPTION     
            "Digit representation of the SGSN. \nUsed as the MAP PurgeMS argument for sgsn-Number encoding in scenario 4.1 and the MAP UpdateGrpsLocation argument for sgsn-Number encoding in scenario 2.1 and 8.1. \nWhen set, can never be reset to an empty string. \nTraffic cannot be activated if set to an empty string. \nValid values: hexadecimal digit string (maximum size of 32). \nDefault value: empty string (start-up only)."
    ::= { ptiwfIWFSS7Entry 8 }

ptiwfIWFSS7IMSIRealm OBJECT-TYPE
    SYNTAX          DisplayString (SIZE(0..255))
    MAX-ACCESS      read-create
    STATUS          current
    DESCRIPTION     
            "User-Name AVP encoded as per NAI format <imsi>@<IMF IMSI Realm>. \nIf set to an empty string, the IMSI is set directly to User-Name AVP. \nValid values: FQDN format (as per the DSC ADN Diameter ID validation)). \nDefault value: empty string (start-up only)."
    ::= { ptiwfIWFSS7Entry 9 }

ptiwfIWFSS7MateSTPLPC OBJECT-TYPE
    SYNTAX          Integer32 (-2147483648..2147483647)
    MAX-ACCESS      read-create
    STATUS          current
    DESCRIPTION     
            "Local Point Code of the mate STP. \nValid values: point code format. \nDefault value: UNSET."
    ::= { ptiwfIWFSS7Entry 10 }

ptiwfIWFSS7MateSTPID OBJECT-TYPE
    SYNTAX          INTEGER { notApplicable(-1), stp2(0), stp1(1) }
    MAX-ACCESS      read-create
    STATUS          current
    DESCRIPTION     
            "Identifier of the mate STP (NOT APPLICABLE, STP1, STP2). \nBy default, set to NOT APPLICABLE for a non mated-pair deployments. \nIn a mated-pair IWF deployment, the ID must be unique to differentiate between the 2 systems. \nDefault value: NOT APPLICABLE."
    ::= { ptiwfIWFSS7Entry 11 }

ptiwfIWFSS7HLRSS7Number OBJECT-TYPE
    SYNTAX          DisplayString (SIZE(0..255))
    MAX-ACCESS      read-create
    STATUS          current
    DESCRIPTION     
            "Digit representation of the HLR. \nUsed as the MAP Reset argument for the sendingNodenumber hlr-Number encoding in scenario 7.2 and as the MAP UpdateGprsLocation response for the hlr-Number encoding in scenario 2.2 and 8.2. \nWhen set, can never be reset to an empty string. \nTraffic cannot be activated if set to an empty string. \nValid values: hexadecimal digit string (maximum size of 32). \nDefault value: empty string (start-up only)."
    ::= { ptiwfIWFSS7Entry 12 }

ptiwfIWFSS7ParentOID OBJECT-TYPE
    SYNTAX          OBJECT IDENTIFIER
    MAX-ACCESS      read-create
    STATUS          current
    DESCRIPTION     
            "The OID of the parent object for this instance"
    ::= { ptiwfIWFSS7Entry 253 }

ptiwfIWFSS7RowStatus OBJECT-TYPE
    SYNTAX          RowStatus
    MAX-ACCESS      read-create
    STATUS          current
    DESCRIPTION     
            "The row status for the iwfIWFSS7 table"
    ::= { ptiwfIWFSS7Entry 254 }

ptiwfIWFSS7Index OBJECT-TYPE
    SYNTAX          Integer32 (-2147483648..2147483647)
    MAX-ACCESS      not-accessible
    STATUS          current
    DESCRIPTION     
            "The row number for the iwfIWFSS7 table"
    ::= { ptiwfIWFSS7Entry 255 }

ptiwfSCCPConnections OBJECT IDENTIFIER
    ::= { ptiwfIWFSS7 1906 }

ptiwfSCCPConnectionsTable OBJECT-TYPE
    SYNTAX          SEQUENCE OF PtiwfSCCPConnectionsEntry
    MAX-ACCESS      not-accessible
    STATUS          current
    DESCRIPTION     
            "No description supplied in the proxy config file."
    ::= { ptiwfSCCPConnections 1 }

ptiwfSCCPConnectionsEntry OBJECT-TYPE
    SYNTAX          PtiwfSCCPConnectionsEntry
    MAX-ACCESS      not-accessible
    STATUS          current
    DESCRIPTION     
            "A sequence of iwfSCCPConnections attributes."
    INDEX           { ptConnGroupIndex, ptiwfSCCPConnectionsIWFSS7Index, 
                      ptiwfSCCPConnectionsIndex }
    ::= { ptiwfSCCPConnectionsTable 1 }

PtiwfSCCPConnectionsEntry ::=
    SEQUENCE {
        ptiwfSCCPConnectionsIWFSS7Index Integer32,
        ptiwfSCCPConnectionsParentOID   OBJECT IDENTIFIER,
        ptiwfSCCPConnectionsRowStatus   RowStatus,
        ptiwfSCCPConnectionsIndex       Integer32
    }

ptiwfSCCPConnectionsIWFSS7Index OBJECT-TYPE
    SYNTAX          Integer32 (-2147483648..2147483647)
    MAX-ACCESS      not-accessible
    STATUS          current
    DESCRIPTION     
            "This is the index of the parent type for this object.
             This parent type is IWFSS7."
    ::= { ptiwfSCCPConnectionsEntry 242 }

ptiwfSCCPConnectionsParentOID OBJECT-TYPE
    SYNTAX          OBJECT IDENTIFIER
    MAX-ACCESS      read-create
    STATUS          current
    DESCRIPTION     
            "The OID of the parent object for this instance"
    ::= { ptiwfSCCPConnectionsEntry 253 }

ptiwfSCCPConnectionsRowStatus OBJECT-TYPE
    SYNTAX          RowStatus
    MAX-ACCESS      read-create
    STATUS          current
    DESCRIPTION     
            "The row status for the iwfSCCPConnections table"
    ::= { ptiwfSCCPConnectionsEntry 254 }

ptiwfSCCPConnectionsIndex OBJECT-TYPE
    SYNTAX          Integer32 (-2147483648..2147483647)
    MAX-ACCESS      not-accessible
    STATUS          current
    DESCRIPTION     
            "The row number for the iwfSCCPConnections table"
    ::= { ptiwfSCCPConnectionsEntry 255 }

ptiwfSCCPConnection OBJECT IDENTIFIER
    ::= { ptiwfSCCPConnections 1907 }

ptiwfSCCPConnectionTable OBJECT-TYPE
    SYNTAX          SEQUENCE OF PtiwfSCCPConnectionEntry
    MAX-ACCESS      not-accessible
    STATUS          current
    DESCRIPTION     
            "No description supplied in the proxy config file."
    ::= { ptiwfSCCPConnection 1 }

ptiwfSCCPConnectionEntry OBJECT-TYPE
    SYNTAX          PtiwfSCCPConnectionEntry
    MAX-ACCESS      not-accessible
    STATUS          current
    DESCRIPTION     
            "A sequence of iwfSCCPConnection attributes."
    INDEX           { ptConnGroupIndex, ptiwfSCCPConnectionIWFSS7Index, 
                      ptiwfSCCPConnectionSCCPConnectionsIndex, 
                      ptiwfSCCPConnectionIndex }
    ::= { ptiwfSCCPConnectionTable 1 }

PtiwfSCCPConnectionEntry ::=
    SEQUENCE {
        ptiwfSCCPConnectionSlot         Integer32,
        ptiwfSCCPConnectionConnectivityStatus     INTEGER,
        ptiwfSCCPConnectionHostname     DisplayString,
        ptiwfSCCPConnectionIWFSS7Index  Integer32,
        ptiwfSCCPConnectionSCCPConnectionsIndex       Integer32,
        ptiwfSCCPConnectionParentOID    OBJECT IDENTIFIER,
        ptiwfSCCPConnectionRowStatus    RowStatus,
        ptiwfSCCPConnectionIndex        Integer32
    }

ptiwfSCCPConnectionSlot OBJECT-TYPE
    SYNTAX          Integer32 (-2147483648..2147483647)
    MAX-ACCESS      read-only
    STATUS          current
    DESCRIPTION     
            "Associated slot of the Application or Routing CPU of the IWF for this SCCP connection. \nOnly one SCCP Connection per slot. \nValid values: integers between 1 and 65535 inclusive."
    ::= { ptiwfSCCPConnectionEntry 1 }

ptiwfSCCPConnectionConnectivityStatus OBJECT-TYPE
    SYNTAX          INTEGER { inactive(0), notConnected(1), connected(2) }
    MAX-ACCESS      read-only
    STATUS          current
    DESCRIPTION     
            "SCCP Connectivity Status (INACTIVE, NOT CONNECTED, CONNECTED). \nAssociated to alarm 1909 (IWF SCCP Connection Down)."
    ::= { ptiwfSCCPConnectionEntry 2 }

ptiwfSCCPConnectionHostname OBJECT-TYPE
    SYNTAX          DisplayString (SIZE(0..255))
    MAX-ACCESS      read-create
    STATUS          current
    DESCRIPTION     
            "Associated hostname of the Routing CPU for this SCCP connection. \nBy default, set to localhost when the IWF and the SCCP run on the same CPU \nIf not set to localhost, the host must be unique across all slots. \nValid values: alphanumeric characters, dashes, underscores, and periods. Length must be between 1 and 32 inclusive. Must start with alphabetic, and end with alphanumeric character."
    ::= { ptiwfSCCPConnectionEntry 3 }

ptiwfSCCPConnectionIWFSS7Index OBJECT-TYPE
    SYNTAX          Integer32 (-2147483648..2147483647)
    MAX-ACCESS      not-accessible
    STATUS          current
    DESCRIPTION     
            "This is the index of the parent type for this object.
             This parent type is IWFSS7."
    ::= { ptiwfSCCPConnectionEntry 242 }

ptiwfSCCPConnectionSCCPConnectionsIndex OBJECT-TYPE
    SYNTAX          Integer32 (-2147483648..2147483647)
    MAX-ACCESS      not-accessible
    STATUS          current
    DESCRIPTION     
            "This is the index of the parent type for this object.
             This parent type is SCCPConnections."
    ::= { ptiwfSCCPConnectionEntry 243 }

ptiwfSCCPConnectionParentOID OBJECT-TYPE
    SYNTAX          OBJECT IDENTIFIER
    MAX-ACCESS      read-create
    STATUS          current
    DESCRIPTION     
            "The OID of the parent object for this instance"
    ::= { ptiwfSCCPConnectionEntry 253 }

ptiwfSCCPConnectionRowStatus OBJECT-TYPE
    SYNTAX          RowStatus
    MAX-ACCESS      read-create
    STATUS          current
    DESCRIPTION     
            "The row status for the iwfSCCPConnection table"
    ::= { ptiwfSCCPConnectionEntry 254 }

ptiwfSCCPConnectionIndex OBJECT-TYPE
    SYNTAX          Integer32 (-2147483648..2147483647)
    MAX-ACCESS      not-accessible
    STATUS          current
    DESCRIPTION     
            "The row number for the iwfSCCPConnection table"
    ::= { ptiwfSCCPConnectionEntry 255 }

ptiwfSCCPRegistrations OBJECT IDENTIFIER
    ::= { ptiwfIWFSS7 1908 }

ptiwfSCCPRegistrationsTable OBJECT-TYPE
    SYNTAX          SEQUENCE OF PtiwfSCCPRegistrationsEntry
    MAX-ACCESS      not-accessible
    STATUS          current
    DESCRIPTION     
            "No description supplied in the proxy config file."
    ::= { ptiwfSCCPRegistrations 1 }

ptiwfSCCPRegistrationsEntry OBJECT-TYPE
    SYNTAX          PtiwfSCCPRegistrationsEntry
    MAX-ACCESS      not-accessible
    STATUS          current
    DESCRIPTION     
            "A sequence of iwfSCCPRegistrations attributes."
    INDEX           { ptConnGroupIndex, 
                      ptiwfSCCPRegistrationsIWFSS7Index, 
                      ptiwfSCCPRegistrationsIndex }
    ::= { ptiwfSCCPRegistrationsTable 1 }

PtiwfSCCPRegistrationsEntry ::=
    SEQUENCE {
        ptiwfSCCPRegistrationsIWFSS7Index Integer32,
        ptiwfSCCPRegistrationsParentOID OBJECT IDENTIFIER,
        ptiwfSCCPRegistrationsRowStatus RowStatus,
        ptiwfSCCPRegistrationsIndex     Integer32
    }

ptiwfSCCPRegistrationsIWFSS7Index OBJECT-TYPE
    SYNTAX          Integer32 (-2147483648..2147483647)
    MAX-ACCESS      not-accessible
    STATUS          current
    DESCRIPTION     
            "This is the index of the parent type for this object.
             This parent type is IWFSS7."
    ::= { ptiwfSCCPRegistrationsEntry 242 }

ptiwfSCCPRegistrationsParentOID OBJECT-TYPE
    SYNTAX          OBJECT IDENTIFIER
    MAX-ACCESS      read-create
    STATUS          current
    DESCRIPTION     
            "The OID of the parent object for this instance"
    ::= { ptiwfSCCPRegistrationsEntry 253 }

ptiwfSCCPRegistrationsRowStatus OBJECT-TYPE
    SYNTAX          RowStatus
    MAX-ACCESS      read-create
    STATUS          current
    DESCRIPTION     
            "The row status for the iwfSCCPRegistrations table"
    ::= { ptiwfSCCPRegistrationsEntry 254 }

ptiwfSCCPRegistrationsIndex OBJECT-TYPE
    SYNTAX          Integer32 (-2147483648..2147483647)
    MAX-ACCESS      not-accessible
    STATUS          current
    DESCRIPTION     
            "The row number for the iwfSCCPRegistrations table"
    ::= { ptiwfSCCPRegistrationsEntry 255 }

ptiwfSCCPPCSSNRegistration OBJECT IDENTIFIER
    ::= { ptiwfSCCPRegistrations 1909 }

ptiwfSCCPPCSSNRegistrationTable OBJECT-TYPE
    SYNTAX          SEQUENCE OF PtiwfSCCPPCSSNRegistrationEntry
    MAX-ACCESS      not-accessible
    STATUS          current
    DESCRIPTION     
            "No description supplied in the proxy config file."
    ::= { ptiwfSCCPPCSSNRegistration 1 }

ptiwfSCCPPCSSNRegistrationEntry OBJECT-TYPE
    SYNTAX          PtiwfSCCPPCSSNRegistrationEntry
    MAX-ACCESS      not-accessible
    STATUS          current
    DESCRIPTION     
            "A sequence of iwfSCCPPCSSNRegistration attributes."
    INDEX           { ptConnGroupIndex, 
                      ptiwfSCCPPCSSNRegistrationIWFSS7Index, 
                      ptiwfSCCPPCSSNRegistrationSCCPRegistrationsIndex, 
                      ptiwfSCCPPCSSNRegistrationIndex }
    ::= { ptiwfSCCPPCSSNRegistrationTable 1 }

PtiwfSCCPPCSSNRegistrationEntry ::=
    SEQUENCE {
        ptiwfSCCPPCSSNRegistrationPC    Integer32,
        ptiwfSCCPPCSSNRegistrationSSN   Integer32,
        ptiwfSCCPPCSSNRegistrationStatus INTEGER,
        ptiwfSCCPPCSSNRegistrationIWFSS7Index     Integer32,
        ptiwfSCCPPCSSNRegistrationSCCPRegistrationsIndex                Integer32,
        ptiwfSCCPPCSSNRegistrationParentOID   OBJECT IDENTIFIER,
        ptiwfSCCPPCSSNRegistrationRowStatus   RowStatus,
        ptiwfSCCPPCSSNRegistrationIndex Integer32
    }

ptiwfSCCPPCSSNRegistrationPC OBJECT-TYPE
    SYNTAX          Integer32 (-2147483648..2147483647)
    MAX-ACCESS      read-only
    STATUS          current
    DESCRIPTION     
            "Pointcode of an IWF SCCP service registration. \nValid values: point code format (based on PC Display Format)."
    ::= { ptiwfSCCPPCSSNRegistrationEntry 1 }

ptiwfSCCPPCSSNRegistrationSSN OBJECT-TYPE
    SYNTAX          Integer32 (2..255)
    MAX-ACCESS      read-only
    STATUS          current
    DESCRIPTION     
            "Subsystem number of an IWF SCCP service registration (2 to 255). \nSome standard SSN as per latest specifications Q.0713 (ITU) and GR-246 (ANSI) include: 5 (MAP), 6 (HLR), 7 (VLR), 8 (MSC)."
    ::= { ptiwfSCCPPCSSNRegistrationEntry 2 }

ptiwfSCCPPCSSNRegistrationStatus OBJECT-TYPE
    SYNTAX          INTEGER { notRegistered(0), partiallyRegistered(1), 
                        registered(2) }
    MAX-ACCESS      read-only
    STATUS          current
    DESCRIPTION     
            "Status of the PC-SSN Registration (NOT REGISTERED, PARTIALLY REGISTERED, REGISTERED). \nWhen all the SCCP connections have successfully registered the PC-SSN, the Status is set to REGISTERED."
    ::= { ptiwfSCCPPCSSNRegistrationEntry 3 }

ptiwfSCCPPCSSNRegistrationIWFSS7Index OBJECT-TYPE
    SYNTAX          Integer32 (-2147483648..2147483647)
    MAX-ACCESS      not-accessible
    STATUS          current
    DESCRIPTION     
            "This is the index of the parent type for this object.
             This parent type is IWFSS7."
    ::= { ptiwfSCCPPCSSNRegistrationEntry 242 }

ptiwfSCCPPCSSNRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptiwfSCCPPCSSNRegistrationEntry 243 }

ptiwfSCCPPCSSNRegistrationParentOID OBJECT-TYPE
    SYNTAX          OBJECT IDENTIFIER
    MAX-ACCESS      read-create
    STATUS          current
    DESCRIPTION     
            "The OID of the parent object for this instance"
    ::= { ptiwfSCCPPCSSNRegistrationEntry 253 }

ptiwfSCCPPCSSNRegistrationRowStatus OBJECT-TYPE
    SYNTAX          RowStatus
    MAX-ACCESS      read-create
    STATUS          current
    DESCRIPTION     
            "The row status for the iwfSCCPPCSSNRegistration table"
    ::= { ptiwfSCCPPCSSNRegistrationEntry 254 }

ptiwfSCCPPCSSNRegistrationIndex OBJECT-TYPE
    SYNTAX          Integer32 (-2147483648..2147483647)
    MAX-ACCESS      not-accessible
    STATUS          current
    DESCRIPTION     
            "The row number for the iwfSCCPPCSSNRegistration table"
    ::= { ptiwfSCCPPCSSNRegistrationEntry 255 }

ptiwfSCCPAppIDRegistration OBJECT IDENTIFIER
    ::= { ptiwfSCCPRegistrations 1910 }

ptiwfSCCPAppIDRegistrationTable OBJECT-TYPE
    SYNTAX          SEQUENCE OF PtiwfSCCPAppIDRegistrationEntry
    MAX-ACCESS      not-accessible
    STATUS          current
    DESCRIPTION     
            "No description supplied in the proxy config file."
    ::= { ptiwfSCCPAppIDRegistration 1 }

ptiwfSCCPAppIDRegistrationEntry OBJECT-TYPE
    SYNTAX          PtiwfSCCPAppIDRegistrationEntry
    MAX-ACCESS      not-accessible
    STATUS          current
    DESCRIPTION     
            "A sequence of iwfSCCPAppIDRegistration attributes."
    INDEX           { ptConnGroupIndex, 
                      ptiwfSCCPAppIDRegistrationIWFSS7Index, 
                      ptiwfSCCPAppIDRegistrationSCCPRegistrationsIndex, 
                      ptiwfSCCPAppIDRegistrationIndex }
    ::= { ptiwfSCCPAppIDRegistrationTable 1 }

PtiwfSCCPAppIDRegistrationEntry ::=
    SEQUENCE {
        ptiwfSCCPAppIDRegistrationApplicationID       DisplayString,
        ptiwfSCCPAppIDRegistrationStatus INTEGER,
        ptiwfSCCPAppIDRegistrationIWFSS7Index     Integer32,
        ptiwfSCCPAppIDRegistrationSCCPRegistrationsIndex                Integer32,
        ptiwfSCCPAppIDRegistrationParentOID   OBJECT IDENTIFIER,
        ptiwfSCCPAppIDRegistrationRowStatus   RowStatus,
        ptiwfSCCPAppIDRegistrationIndex Integer32
    }

ptiwfSCCPAppIDRegistrationApplicationID OBJECT-TYPE
    SYNTAX          DisplayString (SIZE(0..255))
    MAX-ACCESS      read-only
    STATUS          current
    DESCRIPTION     
            "Application ID of an IWF SCCP service registration. \nAssociated with the GWST Redirection feature. \nValid values: alphanumeric characters, dashes, and underscores (maximum size of 16)."
    ::= { ptiwfSCCPAppIDRegistrationEntry 1 }

ptiwfSCCPAppIDRegistrationStatus OBJECT-TYPE
    SYNTAX          INTEGER { notRegistered(0), partiallyRegistered(1), 
                        registered(2) }
    MAX-ACCESS      read-only
    STATUS          current
    DESCRIPTION     
            "Status of the Application ID Registration (NOT REGISTERED, PARTIALLY REGISTERED, REGISTERED). \nWhen all the SCCP connections have successfully registered the Application ID, the Status is set to REGISTERED."
    ::= { ptiwfSCCPAppIDRegistrationEntry 2 }

ptiwfSCCPAppIDRegistrationIWFSS7Index OBJECT-TYPE
    SYNTAX          Integer32 (-2147483648..2147483647)
    MAX-ACCESS      not-accessible
    STATUS          current
    DESCRIPTION     
            "This is the index of the parent type for this object.
             This parent type is IWFSS7."
    ::= { ptiwfSCCPAppIDRegistrationEntry 242 }

ptiwfSCCPAppIDRegistrationSCCPRegistrationsIndex OBJECT-TYPE
    SYNTAX          Integer32 (-2147483648..2147483647)
    MAX-ACCESS      not-accessible
    STATUS          current
    DESCRIPTION     
            "This is the index of the parent type for this object.
             This parent type is SCCPRegistrations."
    ::= { ptiwfSCCPAppIDRegistrationEntry 243 }

ptiwfSCCPAppIDRegistrationParentOID OBJECT-TYPE
    SYNTAX          OBJECT IDENTIFIER
    MAX-ACCESS      read-create
    STATUS          current
    DESCRIPTION     
            "The OID of the parent object for this instance"
    ::= { ptiwfSCCPAppIDRegistrationEntry 253 }

ptiwfSCCPAppIDRegistrationRowStatus OBJECT-TYPE
    SYNTAX          RowStatus
    MAX-ACCESS      read-create
    STATUS          current
    DESCRIPTION     
            "The row status for the iwfSCCPAppIDRegistration table"
    ::= { ptiwfSCCPAppIDRegistrationEntry 254 }

ptiwfSCCPAppIDRegistrationIndex OBJECT-TYPE
    SYNTAX          Integer32 (-2147483648..2147483647)
    MAX-ACCESS      not-accessible
    STATUS          current
    DESCRIPTION     
            "The row number for the iwfSCCPAppIDRegistration table"
    ::= { ptiwfSCCPAppIDRegistrationEntry 255 }

ptiwfIWFNodeMappings OBJECT IDENTIFIER
    ::= { ptConnGroup 1911 }

ptiwfIWFNodeMappingsTable OBJECT-TYPE
    SYNTAX          SEQUENCE OF PtiwfIWFNodeMappingsEntry
    MAX-ACCESS      not-accessible
    STATUS          current
    DESCRIPTION     
            "No description supplied in the proxy config file."
    ::= { ptiwfIWFNodeMappings 1 }

ptiwfIWFNodeMappingsEntry OBJECT-TYPE
    SYNTAX          PtiwfIWFNodeMappingsEntry
    MAX-ACCESS      not-accessible
    STATUS          current
    DESCRIPTION     
            "A sequence of iwfIWFNodeMappings attributes."
    INDEX           { ptConnGroupIndex, ptiwfIWFNodeMappingsIndex }
    ::= { ptiwfIWFNodeMappingsTable 1 }

PtiwfIWFNodeMappingsEntry ::=
    SEQUENCE {
        ptiwfIWFNodeMappingsParentOID   OBJECT IDENTIFIER,
        ptiwfIWFNodeMappingsRowStatus   RowStatus,
        ptiwfIWFNodeMappingsIndex       Integer32
    }

ptiwfIWFNodeMappingsParentOID OBJECT-TYPE
    SYNTAX          OBJECT IDENTIFIER
    MAX-ACCESS      read-create
    STATUS          current
    DESCRIPTION     
            "The OID of the parent object for this instance"
    ::= { ptiwfIWFNodeMappingsEntry 253 }

ptiwfIWFNodeMappingsRowStatus OBJECT-TYPE
    SYNTAX          RowStatus
    MAX-ACCESS      read-create
    STATUS          current
    DESCRIPTION     
            "The row status for the iwfIWFNodeMappings table"
    ::= { ptiwfIWFNodeMappingsEntry 254 }

ptiwfIWFNodeMappingsIndex OBJECT-TYPE
    SYNTAX          Integer32 (-2147483648..2147483647)
    MAX-ACCESS      not-accessible
    STATUS          current
    DESCRIPTION     
            "The row number for the iwfIWFNodeMappings table"
    ::= { ptiwfIWFNodeMappingsEntry 255 }

ptiwfIWFNodeMapping OBJECT IDENTIFIER
    ::= { ptiwfIWFNodeMappings 1912 }

ptiwfIWFNodeMappingTable OBJECT-TYPE
    SYNTAX          SEQUENCE OF PtiwfIWFNodeMappingEntry
    MAX-ACCESS      not-accessible
    STATUS          current
    DESCRIPTION     
            "No description supplied in the proxy config file."
    ::= { ptiwfIWFNodeMapping 1 }

ptiwfIWFNodeMappingEntry OBJECT-TYPE
    SYNTAX          PtiwfIWFNodeMappingEntry
    MAX-ACCESS      not-accessible
    STATUS          current
    DESCRIPTION     
            "A sequence of iwfIWFNodeMapping attributes."
    INDEX           { ptConnGroupIndex, 
                      ptiwfIWFNodeMappingIWFNodeMappingsIndex, 
                      ptiwfIWFNodeMappingIndex }
    ::= { ptiwfIWFNodeMappingTable 1 }

PtiwfIWFNodeMappingEntry ::=
    SEQUENCE {
        ptiwfIWFNodeMappingName         DisplayString,
        ptiwfIWFNodeMappingDiameterID   DisplayString,
        ptiwfIWFNodeMappingDiameterRealm DisplayString,
        ptiwfIWFNodeMappingSS7Number    DisplayString,
        ptiwfIWFNodeMappingSCCPGTI      INTEGER,
        ptiwfIWFNodeMappingSCCPRTI      INTEGER,
        ptiwfIWFNodeMappingSCCPPAPC     Integer32,
        ptiwfIWFNodeMappingSCCPSSN      INTEGER,
        ptiwfIWFNodeMappingSCCPTT       Integer32,
        ptiwfIWFNodeMappingSCCPNOA      Integer32,
        ptiwfIWFNodeMappingSCCPNP       Integer32,
        ptiwfIWFNodeMappingMessageTrace INTEGER,
        ptiwfIWFNodeMappingDescription  DisplayString,
        ptiwfIWFNodeMappingRecordID     Integer32,
        ptiwfIWFNodeMappingIWFNodeMappingsIndex       Integer32,
        ptiwfIWFNodeMappingParentOID    OBJECT IDENTIFIER,
        ptiwfIWFNodeMappingRowStatus    RowStatus,
        ptiwfIWFNodeMappingIndex        Integer32
    }

ptiwfIWFNodeMappingName OBJECT-TYPE
    SYNTAX          DisplayString (SIZE(0..255))
    MAX-ACCESS      read-only
    STATUS          current
    DESCRIPTION     
            "IWF Node Mapping record unique name. \nValid values: alphanumeric characters, dashes, and underscores (maximum size of 16)."
    ::= { ptiwfIWFNodeMappingEntry 1 }

ptiwfIWFNodeMappingDiameterID OBJECT-TYPE
    SYNTAX          DisplayString (SIZE(0..255))
    MAX-ACCESS      read-create
    STATUS          current
    DESCRIPTION     
            "Diameter Identifier representing the Diameter Node. \nMust be unique across all Node Mappings. \nValid values: FQDN format (as per the DSC ADN Diameter ID validation)."
    ::= { ptiwfIWFNodeMappingEntry 2 }

ptiwfIWFNodeMappingDiameterRealm OBJECT-TYPE
    SYNTAX          DisplayString (SIZE(0..255))
    MAX-ACCESS      read-create
    STATUS          current
    DESCRIPTION     
            "Diameter Realm of the Diameter Node. \nValid values: FQDN format (as per the DSC Realm Definition validation)."
    ::= { ptiwfIWFNodeMappingEntry 3 }

ptiwfIWFNodeMappingSS7Number OBJECT-TYPE
    SYNTAX          DisplayString (SIZE(0..255))
    MAX-ACCESS      read-create
    STATUS          current
    DESCRIPTION     
            "Digit representation of the SS7 Node. \nTypically the E.164 number of the node. \nMust be unique across all Node Mappings. \nValid values: hexadecimal digit string (maximum size of 32)."
    ::= { ptiwfIWFNodeMappingEntry 4 }

ptiwfIWFNodeMappingSCCPGTI OBJECT-TYPE
    SYNTAX          INTEGER { gti0000(0), gti0001(1), gti0010(2), 
                        gti0011(3), gti0100(4) }
    MAX-ACCESS      read-create
    STATUS          current
    DESCRIPTION     
            "SCCP Party Address Global Title Indicator (GTI 0000, GTI 0001, GTI 0010, GTI 0011, GTI 0100). \nCannot be set if the IWF SS7 SCCP PA Encoding attribute is not set. \nNote that GTI 0011 and GTI 0100 are only valid in ITU. \nDefault: GTI 0001 (ANSI), GTI 0100 (ITU)."
    ::= { ptiwfIWFNodeMappingEntry 5 }

ptiwfIWFNodeMappingSCCPRTI OBJECT-TYPE
    SYNTAX          INTEGER { routeOnPcssn(1), routeOnGt(2) }
    MAX-ACCESS      read-create
    STATUS          current
    DESCRIPTION     
            "SCCP Party Address Routing Indicator (ROUTE ON PCSSN, ROUTE ON GT). \nIf set to ROUTE ON PCSSN, the SCCP SSN must be defined. \nDefault value: ROUTE OF GT."
    ::= { ptiwfIWFNodeMappingEntry 6 }

ptiwfIWFNodeMappingSCCPPAPC OBJECT-TYPE
    SYNTAX          Integer32 (-2147483648..2147483647)
    MAX-ACCESS      read-create
    STATUS          current
    DESCRIPTION     
            "SCCP Party Address Point Code. \nSet to -1 (UNSET) to exclude the PC from the SCCP PA. \nCannot be set if the IWF SS7 PC format attributes are not set. \nValid values: point code format. \nDefault value: UNSET."
    ::= { ptiwfIWFNodeMappingEntry 7 }

ptiwfIWFNodeMappingSCCPSSN OBJECT-TYPE
    SYNTAX          INTEGER { unset(-1) }
    MAX-ACCESS      read-create
    STATUS          current
    DESCRIPTION     
            "SCCP Party Address Subsystem Number (-1 (UNSET), 0 to 255). \nSet to -1 (UNSET) to exclude the SSN from the SCCP PA. \nDefault value: UNSET."
    ::= { ptiwfIWFNodeMappingEntry 8 }

ptiwfIWFNodeMappingSCCPTT OBJECT-TYPE
    SYNTAX          Integer32 (0..255)
    MAX-ACCESS      read-create
    STATUS          current
    DESCRIPTION     
            "SCCP Party Address Translation Type (0 to 255). \nIncluded in the SCCP PA based on the GTI attribute (ANSI 0001/0010, ITU 0010/0011/0100). \nDefault value: 0."
    ::= { ptiwfIWFNodeMappingEntry 9 }

ptiwfIWFNodeMappingSCCPNOA OBJECT-TYPE
    SYNTAX          Integer32 (0..137)
    MAX-ACCESS      read-create
    STATUS          current
    DESCRIPTION     
            "SCCP Party Address Nature of Address (0 to 127). \nIncluded in the SCCP PA based on the GTI attribute (ITU 0001/0100). \nDefault value: 0."
    ::= { ptiwfIWFNodeMappingEntry 10 }

ptiwfIWFNodeMappingSCCPNP OBJECT-TYPE
    SYNTAX          Integer32 (0..15)
    MAX-ACCESS      read-create
    STATUS          current
    DESCRIPTION     
            "SCCP Party Address Numbering Plan (0 to 15). \nIncluded in the SCCP PA based on the GTI attribute (ANSI 0001, ITU 0011/0100). \nDefault value: 1."
    ::= { ptiwfIWFNodeMappingEntry 11 }

ptiwfIWFNodeMappingMessageTrace OBJECT-TYPE
    SYNTAX          INTEGER { disabled(0), enabled(1) }
    MAX-ACCESS      read-create
    STATUS          current
    DESCRIPTION     
            "Message tracing support for this Node Mapping (DISABLED/ENABLED). \nAll messages associated to this Node Mapping will be traced (originating and destination). \nDefault value: DISABLED."
    ::= { ptiwfIWFNodeMappingEntry 12 }

ptiwfIWFNodeMappingDescription OBJECT-TYPE
    SYNTAX          DisplayString (SIZE(0..255))
    MAX-ACCESS      read-create
    STATUS          current
    DESCRIPTION     
            "Node Mapping Description. Leave empty if not required. Valid values: free format string (maximum size of 64)."
    ::= { ptiwfIWFNodeMappingEntry 13 }

ptiwfIWFNodeMappingRecordID OBJECT-TYPE
    SYNTAX          Integer32 (-2147483648..2147483647)
    MAX-ACCESS      read-only
    STATUS          current
    DESCRIPTION     
            "Hidden attribute for the unique record ID as used by the proxy. \nMust not be zero."
    ::= { ptiwfIWFNodeMappingEntry 14 }

ptiwfIWFNodeMappingIWFNodeMappingsIndex OBJECT-TYPE
    SYNTAX          Integer32 (-2147483648..2147483647)
    MAX-ACCESS      not-accessible
    STATUS          current
    DESCRIPTION     
            "This is the index of the parent type for this object.
             This parent type is IWFNodeMappings."
    ::= { ptiwfIWFNodeMappingEntry 242 }

ptiwfIWFNodeMappingParentOID OBJECT-TYPE
    SYNTAX          OBJECT IDENTIFIER
    MAX-ACCESS      read-create
    STATUS          current
    DESCRIPTION     
            "The OID of the parent object for this instance"
    ::= { ptiwfIWFNodeMappingEntry 253 }

ptiwfIWFNodeMappingRowStatus OBJECT-TYPE
    SYNTAX          RowStatus
    MAX-ACCESS      read-create
    STATUS          current
    DESCRIPTION     
            "The row status for the iwfIWFNodeMapping table"
    ::= { ptiwfIWFNodeMappingEntry 254 }

ptiwfIWFNodeMappingIndex OBJECT-TYPE
    SYNTAX          Integer32 (-2147483648..2147483647)
    MAX-ACCESS      not-accessible
    STATUS          current
    DESCRIPTION     
            "The row number for the iwfIWFNodeMapping table"
    ::= { ptiwfIWFNodeMappingEntry 255 }

ptiwfIWFRealmMappings OBJECT IDENTIFIER
    ::= { ptConnGroup 1913 }

ptiwfIWFRealmMappingsTable OBJECT-TYPE
    SYNTAX          SEQUENCE OF PtiwfIWFRealmMappingsEntry
    MAX-ACCESS      not-accessible
    STATUS          current
    DESCRIPTION     
            "No description supplied in the proxy config file."
    ::= { ptiwfIWFRealmMappings 1 }

ptiwfIWFRealmMappingsEntry OBJECT-TYPE
    SYNTAX          PtiwfIWFRealmMappingsEntry
    MAX-ACCESS      not-accessible
    STATUS          current
    DESCRIPTION     
            "A sequence of iwfIWFRealmMappings attributes."
    INDEX           { ptConnGroupIndex, ptiwfIWFRealmMappingsIndex }
    ::= { ptiwfIWFRealmMappingsTable 1 }

PtiwfIWFRealmMappingsEntry ::=
    SEQUENCE {
        ptiwfIWFRealmMappingsParentOID  OBJECT IDENTIFIER,
        ptiwfIWFRealmMappingsRowStatus  RowStatus,
        ptiwfIWFRealmMappingsIndex      Integer32
    }

ptiwfIWFRealmMappingsParentOID OBJECT-TYPE
    SYNTAX          OBJECT IDENTIFIER
    MAX-ACCESS      read-create
    STATUS          current
    DESCRIPTION     
            "The OID of the parent object for this instance"
    ::= { ptiwfIWFRealmMappingsEntry 253 }

ptiwfIWFRealmMappingsRowStatus OBJECT-TYPE
    SYNTAX          RowStatus
    MAX-ACCESS      read-create
    STATUS          current
    DESCRIPTION     
            "The row status for the iwfIWFRealmMappings table"
    ::= { ptiwfIWFRealmMappingsEntry 254 }

ptiwfIWFRealmMappingsIndex OBJECT-TYPE
    SYNTAX          Integer32 (-2147483648..2147483647)
    MAX-ACCESS      not-accessible
    STATUS          current
    DESCRIPTION     
            "The row number for the iwfIWFRealmMappings table"
    ::= { ptiwfIWFRealmMappingsEntry 255 }

ptiwfIWFRealmMapping OBJECT IDENTIFIER
    ::= { ptiwfIWFRealmMappings 1914 }

ptiwfIWFRealmMappingTable OBJECT-TYPE
    SYNTAX          SEQUENCE OF PtiwfIWFRealmMappingEntry
    MAX-ACCESS      not-accessible
    STATUS          current
    DESCRIPTION     
            "No description supplied in the proxy config file."
    ::= { ptiwfIWFRealmMapping 1 }

ptiwfIWFRealmMappingEntry OBJECT-TYPE
    SYNTAX          PtiwfIWFRealmMappingEntry
    MAX-ACCESS      not-accessible
    STATUS          current
    DESCRIPTION     
            "A sequence of iwfIWFRealmMapping attributes."
    INDEX           { ptConnGroupIndex, 
                      ptiwfIWFRealmMappingIWFRealmMappingsIndex, 
                      ptiwfIWFRealmMappingIndex }
    ::= { ptiwfIWFRealmMappingTable 1 }

PtiwfIWFRealmMappingEntry ::=
    SEQUENCE {
        ptiwfIWFRealmMappingDiameterRealm DisplayString,
        ptiwfIWFRealmMappingApplicationID Integer32,
        ptiwfIWFRealmMappingNodeMappingName   DisplayString,
        ptiwfIWFRealmMappingDescription DisplayString,
        ptiwfIWFRealmMappingRecordID    Integer32,
        ptiwfIWFRealmMappingIWFRealmMappingsIndex         Integer32,
        ptiwfIWFRealmMappingParentOID   OBJECT IDENTIFIER,
        ptiwfIWFRealmMappingRowStatus   RowStatus,
        ptiwfIWFRealmMappingIndex       Integer32
    }

ptiwfIWFRealmMappingDiameterRealm OBJECT-TYPE
    SYNTAX          DisplayString (SIZE(0..255))
    MAX-ACCESS      read-only
    STATUS          current
    DESCRIPTION     
            "String representing a Diameter Realm. \nThe Realm Mapping is required only if a Diameter request is received without a Destination-Host AVP. The combination of the Destination-Realm AVP and Application ID in the Diameter header needs to result to the required Node Mapping record. \nValid values: FQDN format (as per the DSC ADN Diameter ID validation)."
    ::= { ptiwfIWFRealmMappingEntry 1 }

ptiwfIWFRealmMappingApplicationID OBJECT-TYPE
    SYNTAX          Integer32 (-2147483648..2147483647)
    MAX-ACCESS      read-only
    STATUS          current
    DESCRIPTION     
            "Integer representing an Application ID as found in the Diameter message header. \nThe Realm Mapping is required only if a Diameter request is received without a Destination-Host AVP. The combination of the Destination-Realm AVP and Application ID in the Diameter header needs to result to the required Node Mapping record. \nValid values: integer."
    ::= { ptiwfIWFRealmMappingEntry 2 }

ptiwfIWFRealmMappingNodeMappingName OBJECT-TYPE
    SYNTAX          DisplayString (SIZE(0..255))
    MAX-ACCESS      read-only
    STATUS          current
    DESCRIPTION     
            "Associated IWF Node Mapping record name for this realm and Application ID. \nValid values: existing Node Mapping Name."
    ::= { ptiwfIWFRealmMappingEntry 3 }

ptiwfIWFRealmMappingDescription OBJECT-TYPE
    SYNTAX          DisplayString (SIZE(0..255))
    MAX-ACCESS      read-create
    STATUS          current
    DESCRIPTION     
            "Realm Mapping description. Leave empty if not required. \nValid values: free format string (maximum size of 64)."
    ::= { ptiwfIWFRealmMappingEntry 4 }

ptiwfIWFRealmMappingRecordID OBJECT-TYPE
    SYNTAX          Integer32 (-2147483648..2147483647)
    MAX-ACCESS      read-only
    STATUS          current
    DESCRIPTION     
            "Hidden attribute for the unique record ID as used by the proxy. \nMust not be zero."
    ::= { ptiwfIWFRealmMappingEntry 14 }

ptiwfIWFRealmMappingIWFRealmMappingsIndex OBJECT-TYPE
    SYNTAX          Integer32 (-2147483648..2147483647)
    MAX-ACCESS      not-accessible
    STATUS          current
    DESCRIPTION     
            "This is the index of the parent type for this object.
             This parent type is IWFRealmMappings."
    ::= { ptiwfIWFRealmMappingEntry 242 }

ptiwfIWFRealmMappingParentOID OBJECT-TYPE
    SYNTAX          OBJECT IDENTIFIER
    MAX-ACCESS      read-create
    STATUS          current
    DESCRIPTION     
            "The OID of the parent object for this instance"
    ::= { ptiwfIWFRealmMappingEntry 253 }

ptiwfIWFRealmMappingRowStatus OBJECT-TYPE
    SYNTAX          RowStatus
    MAX-ACCESS      read-create
    STATUS          current
    DESCRIPTION     
            "The row status for the iwfIWFRealmMapping table"
    ::= { ptiwfIWFRealmMappingEntry 254 }

ptiwfIWFRealmMappingIndex OBJECT-TYPE
    SYNTAX          Integer32 (-2147483648..2147483647)
    MAX-ACCESS      not-accessible
    STATUS          current
    DESCRIPTION     
            "The row number for the iwfIWFRealmMapping table"
    ::= { ptiwfIWFRealmMappingEntry 255 }

ptFLXSS7DBAppsConfiguration OBJECT IDENTIFIER
    ::= { ptConnGroup 2001 }

ptFLXSS7DBAppsConfigurationTable OBJECT-TYPE
    SYNTAX          SEQUENCE OF PtFLXSS7DBAppsConfigurationEntry
    MAX-ACCESS      not-accessible
    STATUS          current
    DESCRIPTION     
            "No description supplied in the proxy config file."
    ::= { ptFLXSS7DBAppsConfiguration 1 }

ptFLXSS7DBAppsConfigurationEntry OBJECT-TYPE
    SYNTAX          PtFLXSS7DBAppsConfigurationEntry
    MAX-ACCESS      not-accessible
    STATUS          current
    DESCRIPTION     
            "A sequence of FLXSS7DBAppsConfiguration attributes."
    INDEX           { ptConnGroupIndex, ptFLXSS7DBAppsConfigurationIndex }
    ::= { ptFLXSS7DBAppsConfigurationTable 1 }

PtFLXSS7DBAppsConfigurationEntry ::=
    SEQUENCE {
        ptFLXSS7DBAppsConfigurationTrapInfo   DisplayString,
        ptFLXSS7DBAppsConfigurationParentOID    OBJECT IDENTIFIER,
        ptFLXSS7DBAppsConfigurationRowStatus    RowStatus,
        ptFLXSS7DBAppsConfigurationIndex Integer32
    }

ptFLXSS7DBAppsConfigurationTrapInfo OBJECT-TYPE
    SYNTAX          DisplayString (SIZE(0..255))
    MAX-ACCESS      read-only
    STATUS          current
    DESCRIPTION     
            "Information for use in traps."
    ::= { ptFLXSS7DBAppsConfigurationEntry 1 }

ptFLXSS7DBAppsConfigurationParentOID OBJECT-TYPE
    SYNTAX          OBJECT IDENTIFIER
    MAX-ACCESS      read-create
    STATUS          current
    DESCRIPTION     
            "The OID of the parent object for this instance"
    ::= { ptFLXSS7DBAppsConfigurationEntry 253 }

ptFLXSS7DBAppsConfigurationRowStatus OBJECT-TYPE
    SYNTAX          RowStatus
    MAX-ACCESS      read-create
    STATUS          current
    DESCRIPTION     
            "The row status for the FLXSS7DBAppsConfiguration table"
    ::= { ptFLXSS7DBAppsConfigurationEntry 254 }

ptFLXSS7DBAppsConfigurationIndex OBJECT-TYPE
    SYNTAX          Integer32 (-2147483648..2147483647)
    MAX-ACCESS      not-accessible
    STATUS          current
    DESCRIPTION     
            "The row number for the FLXSS7DBAppsConfiguration table"
    ::= { ptFLXSS7DBAppsConfigurationEntry 255 }

ptFLXLogConfiguration OBJECT IDENTIFIER
    ::= { ptFLXSS7DBAppsConfiguration 2011 }

ptFLXLogConfigurationTable OBJECT-TYPE
    SYNTAX          SEQUENCE OF PtFLXLogConfigurationEntry
    MAX-ACCESS      not-accessible
    STATUS          current
    DESCRIPTION     
            "No description supplied in the proxy config file."
    ::= { ptFLXLogConfiguration 1 }

ptFLXLogConfigurationEntry OBJECT-TYPE
    SYNTAX          PtFLXLogConfigurationEntry
    MAX-ACCESS      not-accessible
    STATUS          current
    DESCRIPTION     
            "A sequence of FLXLogConfiguration attributes."
    INDEX           { ptConnGroupIndex, 
                      ptFLXLogConfigurationSS7DBAppsConfigurationIndex, 
                      ptFLXLogConfigurationIndex }
    ::= { ptFLXLogConfigurationTable 1 }

PtFLXLogConfigurationEntry ::=
    SEQUENCE {
        ptFLXLogConfigurationApplication DisplayString,
        ptFLXLogConfigurationDBMgr      INTEGER,
        ptFLXLogConfigurationServiceHandlers    INTEGER,
        ptFLXLogConfigurationServices   INTEGER,
        ptFLXLogConfigurationProtocols  INTEGER,
        ptFLXLogConfigurationFlexApp    INTEGER,
        ptFLXLogConfigurationFlexInfo   INTEGER,
        ptFLXLogConfigurationFlexAll    INTEGER,
        ptFLXLogConfigurationAllError   INTEGER,
        ptFLXLogConfigurationLoadMonitor INTEGER,
        ptFLXLogConfigurationSMInterface INTEGER,
        ptFLXLogConfigurationRegAudit   INTEGER,
        ptFLXLogConfigurationInitialize INTEGER,
        ptFLXLogConfigurationChecksumError  INTEGER,
        ptFLXLogConfigurationSS7DBAppsConfigurationIndex                Integer32,
        ptFLXLogConfigurationParentOID  OBJECT IDENTIFIER,
        ptFLXLogConfigurationRowStatus  RowStatus,
        ptFLXLogConfigurationIndex      Integer32
    }

ptFLXLogConfigurationApplication OBJECT-TYPE
    SYNTAX          DisplayString (SIZE(0..255))
    MAX-ACCESS      read-only
    STATUS          current
    DESCRIPTION     
            "No description supplied in the proxy config file."
    ::= { ptFLXLogConfigurationEntry 1 }

ptFLXLogConfigurationDBMgr OBJECT-TYPE
    SYNTAX          INTEGER { notLogged(0), logged(1) }
    MAX-ACCESS      read-create
    STATUS          current
    DESCRIPTION     
            "No description supplied in the proxy config file."
    ::= { ptFLXLogConfigurationEntry 2 }

ptFLXLogConfigurationServiceHandlers OBJECT-TYPE
    SYNTAX          INTEGER { notLogged(0), logged(1) }
    MAX-ACCESS      read-create
    STATUS          current
    DESCRIPTION     
            "No description supplied in the proxy config file."
    ::= { ptFLXLogConfigurationEntry 3 }

ptFLXLogConfigurationServices OBJECT-TYPE
    SYNTAX          INTEGER { notLogged(0), logged(1) }
    MAX-ACCESS      read-create
    STATUS          current
    DESCRIPTION     
            "No description supplied in the proxy config file."
    ::= { ptFLXLogConfigurationEntry 4 }

ptFLXLogConfigurationProtocols OBJECT-TYPE
    SYNTAX          INTEGER { notLogged(0), logged(1) }
    MAX-ACCESS      read-create
    STATUS          current
    DESCRIPTION     
            "No description supplied in the proxy config file."
    ::= { ptFLXLogConfigurationEntry 5 }

ptFLXLogConfigurationFlexApp OBJECT-TYPE
    SYNTAX          INTEGER { notLogged(0), logged(1) }
    MAX-ACCESS      read-create
    STATUS          current
    DESCRIPTION     
            "No description supplied in the proxy config file."
    ::= { ptFLXLogConfigurationEntry 6 }

ptFLXLogConfigurationFlexInfo OBJECT-TYPE
    SYNTAX          INTEGER { notLogged(0), logged(1) }
    MAX-ACCESS      read-create
    STATUS          current
    DESCRIPTION     
            "No description supplied in the proxy config file."
    ::= { ptFLXLogConfigurationEntry 7 }

ptFLXLogConfigurationFlexAll OBJECT-TYPE
    SYNTAX          INTEGER { notLogged(0), logged(1) }
    MAX-ACCESS      read-create
    STATUS          current
    DESCRIPTION     
            "No description supplied in the proxy config file."
    ::= { ptFLXLogConfigurationEntry 8 }

ptFLXLogConfigurationAllError OBJECT-TYPE
    SYNTAX          INTEGER { notLogged(0), logged(1) }
    MAX-ACCESS      read-create
    STATUS          current
    DESCRIPTION     
            "No description supplied in the proxy config file."
    ::= { ptFLXLogConfigurationEntry 9 }

ptFLXLogConfigurationLoadMonitor OBJECT-TYPE
    SYNTAX          INTEGER { notLogged(0), logged(1) }
    MAX-ACCESS      read-create
    STATUS          current
    DESCRIPTION     
            "No description supplied in the proxy config file."
    ::= { ptFLXLogConfigurationEntry 10 }

ptFLXLogConfigurationSMInterface OBJECT-TYPE
    SYNTAX          INTEGER { notLogged(0), logged(1) }
    MAX-ACCESS      read-create
    STATUS          current
    DESCRIPTION     
            "No description supplied in the proxy config file."
    ::= { ptFLXLogConfigurationEntry 11 }

ptFLXLogConfigurationRegAudit OBJECT-TYPE
    SYNTAX          INTEGER { notLogged(0), logged(1) }
    MAX-ACCESS      read-create
    STATUS          current
    DESCRIPTION     
            "No description supplied in the proxy config file."
    ::= { ptFLXLogConfigurationEntry 12 }

ptFLXLogConfigurationInitialize OBJECT-TYPE
    SYNTAX          INTEGER { notLogged(0), logged(1) }
    MAX-ACCESS      read-create
    STATUS          current
    DESCRIPTION     
            "No description supplied in the proxy config file."
    ::= { ptFLXLogConfigurationEntry 13 }

ptFLXLogConfigurationChecksumError OBJECT-TYPE
    SYNTAX          INTEGER { notLogged(0), logged(1) }
    MAX-ACCESS      read-create
    STATUS          current
    DESCRIPTION     
            "No description supplied in the proxy config file."
    ::= { ptFLXLogConfigurationEntry 14 }

ptFLXLogConfigurationSS7DBAppsConfigurationIndex OBJECT-TYPE
    SYNTAX          Integer32 (-2147483648..2147483647)
    MAX-ACCESS      not-accessible
    STATUS          current
    DESCRIPTION     
            "This is the index of the parent type for this object.
             This parent type is SS7DBAppsConfiguration."
    ::= { ptFLXLogConfigurationEntry 242 }

ptFLXLogConfigurationParentOID OBJECT-TYPE
    SYNTAX          OBJECT IDENTIFIER
    MAX-ACCESS      read-create
    STATUS          current
    DESCRIPTION     
            "The OID of the parent object for this instance"
    ::= { ptFLXLogConfigurationEntry 253 }

ptFLXLogConfigurationRowStatus OBJECT-TYPE
    SYNTAX          RowStatus
    MAX-ACCESS      read-create
    STATUS          current
    DESCRIPTION     
            "The row status for the FLXLogConfiguration table"
    ::= { ptFLXLogConfigurationEntry 254 }

ptFLXLogConfigurationIndex OBJECT-TYPE
    SYNTAX          Integer32 (-2147483648..2147483647)
    MAX-ACCESS      not-accessible
    STATUS          current
    DESCRIPTION     
            "The row number for the FLXLogConfiguration table"
    ::= { ptFLXLogConfigurationEntry 255 }

ptLBLoadBalancer OBJECT IDENTIFIER
    ::= { ptConnGroup 5001 }

ptLBLoadBalancerTable OBJECT-TYPE
    SYNTAX          SEQUENCE OF PtLBLoadBalancerEntry
    MAX-ACCESS      not-accessible
    STATUS          current
    DESCRIPTION     
            "No description supplied in the proxy config file."
    ::= { ptLBLoadBalancer 1 }

ptLBLoadBalancerEntry OBJECT-TYPE
    SYNTAX          PtLBLoadBalancerEntry
    MAX-ACCESS      not-accessible
    STATUS          current
    DESCRIPTION     
            "A sequence of LBLoadBalancer attributes."
    INDEX           { ptConnGroupIndex, ptLBLoadBalancerIndex }
    ::= { ptLBLoadBalancerTable 1 }

PtLBLoadBalancerEntry ::=
    SEQUENCE {
        ptLBLoadBalancerID              Integer32,
        ptLBLoadBalancerName            DisplayString,
        ptLBLoadBalancerVersion         DisplayString,
        ptLBLoadBalancerErrors          INTEGER,
        ptLBLoadBalancerSetupManagement INTEGER,
        ptLBLoadBalancerDistributionManagement      INTEGER,
        ptLBLoadBalancerParentOID       OBJECT IDENTIFIER,
        ptLBLoadBalancerRowStatus       RowStatus,
        ptLBLoadBalancerIndex           Integer32
    }

ptLBLoadBalancerID OBJECT-TYPE
    SYNTAX          Integer32 (-2147483648..2147483647)
    MAX-ACCESS      read-only
    STATUS          current
    DESCRIPTION     
            "Load Balancer Identifier (1 or 2). \nIf more than one Load Balancer is defined, the value is overwritten by the associated command line argument on startup."
    ::= { ptLBLoadBalancerEntry 1 }

ptLBLoadBalancerName OBJECT-TYPE
    SYNTAX          DisplayString (SIZE(0..255))
    MAX-ACCESS      read-create
    STATUS          current
    DESCRIPTION     
            "Name used to logically identify the Load Balancer Instance. \nIf more than one Load Balancer Instance is defined, it is recommended that the name be updated to a short and unique value to facilitate logs, alarms, and statistics correlation. \nValid values: alphanumeric characters, dashes, and underscores (maximum size of 64). \nDefault value: LB_X, where X is the Load Balancer ID."
    ::= { ptLBLoadBalancerEntry 2 }

ptLBLoadBalancerVersion OBJECT-TYPE
    SYNTAX          DisplayString (SIZE(0..255))
    MAX-ACCESS      read-only
    STATUS          current
    DESCRIPTION     
            "Current Load Balancer application version. \nThis is a hardcoded value as per the Load Balancer application."
    ::= { ptLBLoadBalancerEntry 3 }

ptLBLoadBalancerErrors OBJECT-TYPE
    SYNTAX          INTEGER { notLogged(0), logged(1) }
    MAX-ACCESS      read-create
    STATUS          current
    DESCRIPTION     
            "Enable or disable the logging of Load Balancer error messages to the debuglog (NOT LOGGED/LOGGED). \nThe logging of Load Balancer errors should be set to LOGGED for all production systems. \nDefault value: LOGGED."
    ::= { ptLBLoadBalancerEntry 6 }

ptLBLoadBalancerSetupManagement OBJECT-TYPE
    SYNTAX          INTEGER { notLogged(0), logged(1) }
    MAX-ACCESS      read-create
    STATUS          current
    DESCRIPTION     
            "Enable or disable the logging of startup and setup information to the debuglog (NOT LOGGED/LOGGED). \nThese logs are not related to traffic processing and have no impact on the performance of a running system. \nThe logging of Load Balancer startup and setup information should be set to LOGGED for most production systems. \nDefault value: LOGGED."
    ::= { ptLBLoadBalancerEntry 7 }

ptLBLoadBalancerDistributionManagement OBJECT-TYPE
    SYNTAX          INTEGER { notLogged(0), logged(1) }
    MAX-ACCESS      read-create
    STATUS          current
    DESCRIPTION     
            "Enable or disable the logging of inter-Load Balancer process communication to the debuglog (NOT LOGGED/LOGGED). \nThe resultant log messages are intended for Sonus Networks engineering staff and are not intended for customer use. \nThe logging of LB inter-process information should be set to NOT_LOGGED on all production systems so that the CPU is not unduly taxed. Default value: NOT LOGGED."
    ::= { ptLBLoadBalancerEntry 8 }

ptLBLoadBalancerParentOID OBJECT-TYPE
    SYNTAX          OBJECT IDENTIFIER
    MAX-ACCESS      read-create
    STATUS          current
    DESCRIPTION     
            "The OID of the parent object for this instance"
    ::= { ptLBLoadBalancerEntry 253 }

ptLBLoadBalancerRowStatus OBJECT-TYPE
    SYNTAX          RowStatus
    MAX-ACCESS      read-create
    STATUS          current
    DESCRIPTION     
            "The row status for the LBLoadBalancer table"
    ::= { ptLBLoadBalancerEntry 254 }

ptLBLoadBalancerIndex OBJECT-TYPE
    SYNTAX          Integer32 (-2147483648..2147483647)
    MAX-ACCESS      not-accessible
    STATUS          current
    DESCRIPTION     
            "The row number for the LBLoadBalancer table"
    ::= { ptLBLoadBalancerEntry 255 }

ptLBTargets OBJECT IDENTIFIER
    ::= { ptLBLoadBalancer 5002 }

ptLBTargetsTable OBJECT-TYPE
    SYNTAX          SEQUENCE OF PtLBTargetsEntry
    MAX-ACCESS      not-accessible
    STATUS          current
    DESCRIPTION     
            "No description supplied in the proxy config file."
    ::= { ptLBTargets 1 }

ptLBTargetsEntry OBJECT-TYPE
    SYNTAX          PtLBTargetsEntry
    MAX-ACCESS      not-accessible
    STATUS          current
    DESCRIPTION     
            "A sequence of LBTargets attributes."
    INDEX           { ptConnGroupIndex, ptLBTargetsLoadBalancerIndex, 
                      ptLBTargetsIndex }
    ::= { ptLBTargetsTable 1 }

PtLBTargetsEntry ::=
    SEQUENCE {
        ptLBTargetsLoadBalancerIndex    Integer32,
        ptLBTargetsParentOID            OBJECT IDENTIFIER,
        ptLBTargetsRowStatus            RowStatus,
        ptLBTargetsIndex                Integer32
    }

ptLBTargetsLoadBalancerIndex OBJECT-TYPE
    SYNTAX          Integer32 (-2147483648..2147483647)
    MAX-ACCESS      not-accessible
    STATUS          current
    DESCRIPTION     
            "This is the index of the parent type for this object.
             This parent type is LoadBalancer."
    ::= { ptLBTargetsEntry 242 }

ptLBTargetsParentOID OBJECT-TYPE
    SYNTAX          OBJECT IDENTIFIER
    MAX-ACCESS      read-create
    STATUS          current
    DESCRIPTION     
            "The OID of the parent object for this instance"
    ::= { ptLBTargetsEntry 253 }

ptLBTargetsRowStatus OBJECT-TYPE
    SYNTAX          RowStatus
    MAX-ACCESS      read-create
    STATUS          current
    DESCRIPTION     
            "The row status for the LBTargets table"
    ::= { ptLBTargetsEntry 254 }

ptLBTargetsIndex OBJECT-TYPE
    SYNTAX          Integer32 (-2147483648..2147483647)
    MAX-ACCESS      not-accessible
    STATUS          current
    DESCRIPTION     
            "The row number for the LBTargets table"
    ::= { ptLBTargetsEntry 255 }

ptLBTarget OBJECT IDENTIFIER
    ::= { ptLBTargets 5003 }

ptLBTargetTable OBJECT-TYPE
    SYNTAX          SEQUENCE OF PtLBTargetEntry
    MAX-ACCESS      not-accessible
    STATUS          current
    DESCRIPTION     
            "No description supplied in the proxy config file."
    ::= { ptLBTarget 1 }

ptLBTargetEntry OBJECT-TYPE
    SYNTAX          PtLBTargetEntry
    MAX-ACCESS      not-accessible
    STATUS          current
    DESCRIPTION     
            "A sequence of LBTarget attributes."
    INDEX           { ptConnGroupIndex, ptLBTargetLoadBalancerIndex, 
                      ptLBTargetTargetsIndex, ptLBTargetIndex }
    ::= { ptLBTargetTable 1 }

PtLBTargetEntry ::=
    SEQUENCE {
        ptLBTargetName                  DisplayString,
        ptLBTargetLoadBalancing         INTEGER,
        ptLBTargetInternalID            Integer32,
        ptLBTargetStatus                DisplayString,
        ptLBTargetLoadBalancerIndex     Integer32,
        ptLBTargetTargetsIndex          Integer32,
        ptLBTargetActions               INTEGER,
        ptLBTargetParentOID             OBJECT IDENTIFIER,
        ptLBTargetRowStatus             RowStatus,
        ptLBTargetIndex                 Integer32
    }

ptLBTargetName OBJECT-TYPE
    SYNTAX          DisplayString (SIZE(0..255))
    MAX-ACCESS      read-only
    STATUS          current
    DESCRIPTION     
            "Load Balancer Target Name. \n Valid values: alphanumeric characters, dashes, and underscores (maximum size of 32)."
    ::= { ptLBTargetEntry 1 }

ptLBTargetLoadBalancing OBJECT-TYPE
    SYNTAX          INTEGER { staticMapping(0), roundRobin(1) }
    MAX-ACCESS      read-create
    STATUS          current
    DESCRIPTION     
            "Select the load balancing algorithm that applies to this target. \nValid values: ROUND ROBIN: Assigns each new connection sequentially around the target slots but assigns more connections to slots with greater capacity. \nCapacity is indicated by the user-assigned weight factor. \nSTATIC MAPPING: The user configures the mappings between connections and the target slots. \nDefault value: STATIC MAPPING."
    ::= { ptLBTargetEntry 2 }

ptLBTargetInternalID OBJECT-TYPE
    SYNTAX          Integer32 (-2147483648..2147483647)
    MAX-ACCESS      read-only
    STATUS          current
    DESCRIPTION     
            "Target unique internal ID. \nReserved for internal use."
    ::= { ptLBTargetEntry 3 }

ptLBTargetStatus OBJECT-TYPE
    SYNTAX          DisplayString (SIZE(0..255))
    MAX-ACCESS      read-only
    STATUS          current
    DESCRIPTION     
            "Configuration status. \nIndicates the status of the most recent configuration modification \nor that configuration is in progress. \nBUSY indicates that new configuration is temporarily blocked."
    ::= { ptLBTargetEntry 4 }

ptLBTargetLoadBalancerIndex OBJECT-TYPE
    SYNTAX          Integer32 (-2147483648..2147483647)
    MAX-ACCESS      not-accessible
    STATUS          current
    DESCRIPTION     
            "This is the index of the parent type for this object.
             This parent type is LoadBalancer."
    ::= { ptLBTargetEntry 242 }

ptLBTargetTargetsIndex OBJECT-TYPE
    SYNTAX          Integer32 (-2147483648..2147483647)
    MAX-ACCESS      not-accessible
    STATUS          current
    DESCRIPTION     
            "This is the index of the parent type for this object.
             This parent type is Targets."
    ::= { ptLBTargetEntry 243 }

ptLBTargetActions OBJECT-TYPE
    SYNTAX          INTEGER { forceRebalancing(1), ignoreRebalancing(2) }
    MAX-ACCESS      read-create
    STATUS          current
    DESCRIPTION     
            "The OID of all possible actions for this instance"
    ::= { ptLBTargetEntry 252 }

ptLBTargetParentOID OBJECT-TYPE
    SYNTAX          OBJECT IDENTIFIER
    MAX-ACCESS      read-create
    STATUS          current
    DESCRIPTION     
            "The OID of the parent object for this instance"
    ::= { ptLBTargetEntry 253 }

ptLBTargetRowStatus OBJECT-TYPE
    SYNTAX          RowStatus
    MAX-ACCESS      read-create
    STATUS          current
    DESCRIPTION     
            "The row status for the LBTarget table"
    ::= { ptLBTargetEntry 254 }

ptLBTargetIndex OBJECT-TYPE
    SYNTAX          Integer32 (-2147483648..2147483647)
    MAX-ACCESS      not-accessible
    STATUS          current
    DESCRIPTION     
            "The row number for the LBTarget table"
    ::= { ptLBTargetEntry 255 }

ptLBTargetSlot OBJECT IDENTIFIER
    ::= { ptLBTarget 5004 }

ptLBTargetSlotTable OBJECT-TYPE
    SYNTAX          SEQUENCE OF PtLBTargetSlotEntry
    MAX-ACCESS      not-accessible
    STATUS          current
    DESCRIPTION     
            "No description supplied in the proxy config file."
    ::= { ptLBTargetSlot 1 }

ptLBTargetSlotEntry OBJECT-TYPE
    SYNTAX          PtLBTargetSlotEntry
    MAX-ACCESS      not-accessible
    STATUS          current
    DESCRIPTION     
            "A sequence of LBTargetSlot attributes."
    INDEX           { ptConnGroupIndex, ptLBTargetSlotLoadBalancerIndex, 
                      ptLBTargetSlotTargetsIndex, 
                      ptLBTargetSlotTargetIndex, ptLBTargetSlotIndex }
    ::= { ptLBTargetSlotTable 1 }

PtLBTargetSlotEntry ::=
    SEQUENCE {
        ptLBTargetSlotSlot              Integer32,
        ptLBTargetSlotWeight            Integer32,
        ptLBTargetSlotStatus            DisplayString,
        ptLBTargetSlotLoadBalancerIndex Integer32,
        ptLBTargetSlotTargetsIndex      Integer32,
        ptLBTargetSlotTargetIndex       Integer32,
        ptLBTargetSlotParentOID         OBJECT IDENTIFIER,
        ptLBTargetSlotRowStatus         RowStatus,
        ptLBTargetSlotIndex             Integer32
    }

ptLBTargetSlotSlot OBJECT-TYPE
    SYNTAX          Integer32 (-2147483648..2147483647)
    MAX-ACCESS      read-only
    STATUS          current
    DESCRIPTION     
            "The DSC Slot associated with load balancer connections using the target. \nValid values: Available routing slot number."
    ::= { ptLBTargetSlotEntry 1 }

ptLBTargetSlotWeight OBJECT-TYPE
    SYNTAX          Integer32
    MAX-ACCESS      read-create
    STATUS          current
    DESCRIPTION     
            "Weight of the DSC Slot (1 to 100). \nOnly applicable to the ROUND ROBIN load balancing algorithm. \nDefault value: 100."
    ::= { ptLBTargetSlotEntry 2 }

ptLBTargetSlotStatus OBJECT-TYPE
    SYNTAX          DisplayString (SIZE(0..255))
    MAX-ACCESS      read-only
    STATUS          current
    DESCRIPTION     
            "Configuration status. \nIndicates the status of the most recent configuration modification \nor that configuration is in progress. \nBUSY indicates that new configuration is temporarily blocked."
    ::= { ptLBTargetSlotEntry 3 }

ptLBTargetSlotLoadBalancerIndex OBJECT-TYPE
    SYNTAX          Integer32 (-2147483648..2147483647)
    MAX-ACCESS      not-accessible
    STATUS          current
    DESCRIPTION     
            "This is the index of the parent type for this object.
             This parent type is LoadBalancer."
    ::= { ptLBTargetSlotEntry 242 }

ptLBTargetSlotTargetsIndex OBJECT-TYPE
    SYNTAX          Integer32 (-2147483648..2147483647)
    MAX-ACCESS      not-accessible
    STATUS          current
    DESCRIPTION     
            "This is the index of the parent type for this object.
             This parent type is Targets."
    ::= { ptLBTargetSlotEntry 243 }

ptLBTargetSlotTargetIndex OBJECT-TYPE
    SYNTAX          Integer32 (-2147483648..2147483647)
    MAX-ACCESS      not-accessible
    STATUS          current
    DESCRIPTION     
            "This is the index of the parent type for this object.
             This parent type is Target."
    ::= { ptLBTargetSlotEntry 244 }

ptLBTargetSlotParentOID OBJECT-TYPE
    SYNTAX          OBJECT IDENTIFIER
    MAX-ACCESS      read-create
    STATUS          current
    DESCRIPTION     
            "The OID of the parent object for this instance"
    ::= { ptLBTargetSlotEntry 253 }

ptLBTargetSlotRowStatus OBJECT-TYPE
    SYNTAX          RowStatus
    MAX-ACCESS      read-create
    STATUS          current
    DESCRIPTION     
            "The row status for the LBTargetSlot table"
    ::= { ptLBTargetSlotEntry 254 }

ptLBTargetSlotIndex OBJECT-TYPE
    SYNTAX          Integer32 (-2147483648..2147483647)
    MAX-ACCESS      not-accessible
    STATUS          current
    DESCRIPTION     
            "The row number for the LBTargetSlot table"
    ::= { ptLBTargetSlotEntry 255 }

ptLBConnections OBJECT IDENTIFIER
    ::= { ptLBLoadBalancer 5005 }

ptLBConnectionsTable OBJECT-TYPE
    SYNTAX          SEQUENCE OF PtLBConnectionsEntry
    MAX-ACCESS      not-accessible
    STATUS          current
    DESCRIPTION     
            "No description supplied in the proxy config file."
    ::= { ptLBConnections 1 }

ptLBConnectionsEntry OBJECT-TYPE
    SYNTAX          PtLBConnectionsEntry
    MAX-ACCESS      not-accessible
    STATUS          current
    DESCRIPTION     
            "A sequence of LBConnections attributes."
    INDEX           { ptConnGroupIndex, ptLBConnectionsLoadBalancerIndex, 
                      ptLBConnectionsIndex }
    ::= { ptLBConnectionsTable 1 }

PtLBConnectionsEntry ::=
    SEQUENCE {
        ptLBConnectionsLoadBalancerIndex Integer32,
        ptLBConnectionsParentOID        OBJECT IDENTIFIER,
        ptLBConnectionsRowStatus        RowStatus,
        ptLBConnectionsIndex            Integer32
    }

ptLBConnectionsLoadBalancerIndex OBJECT-TYPE
    SYNTAX          Integer32 (-2147483648..2147483647)
    MAX-ACCESS      not-accessible
    STATUS          current
    DESCRIPTION     
            "This is the index of the parent type for this object.
             This parent type is LoadBalancer."
    ::= { ptLBConnectionsEntry 242 }

ptLBConnectionsParentOID OBJECT-TYPE
    SYNTAX          OBJECT IDENTIFIER
    MAX-ACCESS      read-create
    STATUS          current
    DESCRIPTION     
            "The OID of the parent object for this instance"
    ::= { ptLBConnectionsEntry 253 }

ptLBConnectionsRowStatus OBJECT-TYPE
    SYNTAX          RowStatus
    MAX-ACCESS      read-create
    STATUS          current
    DESCRIPTION     
            "The row status for the LBConnections table"
    ::= { ptLBConnectionsEntry 254 }

ptLBConnectionsIndex OBJECT-TYPE
    SYNTAX          Integer32 (-2147483648..2147483647)
    MAX-ACCESS      not-accessible
    STATUS          current
    DESCRIPTION     
            "The row number for the LBConnections table"
    ::= { ptLBConnectionsEntry 255 }

ptLBConnection OBJECT IDENTIFIER
    ::= { ptLBConnections 5006 }

ptLBConnectionTable OBJECT-TYPE
    SYNTAX          SEQUENCE OF PtLBConnectionEntry
    MAX-ACCESS      not-accessible
    STATUS          current
    DESCRIPTION     
            "No description supplied in the proxy config file."
    ::= { ptLBConnection 1 }

ptLBConnectionEntry OBJECT-TYPE
    SYNTAX          PtLBConnectionEntry
    MAX-ACCESS      not-accessible
    STATUS          current
    DESCRIPTION     
            "A sequence of LBConnection attributes."
    INDEX           { ptConnGroupIndex, ptLBConnectionLoadBalancerIndex, 
                      ptLBConnectionConnectionsIndex, 
                      ptLBConnectionIndex }
    ::= { ptLBConnectionTable 1 }

PtLBConnectionEntry ::=
    SEQUENCE {
        ptLBConnectionName              DisplayString,
        ptLBConnectionTargetName        DisplayString,
        ptLBConnectionTransportType     INTEGER,
        ptLBConnectionLocalHost         DisplayString,
        ptLBConnectionRemoteHost        DisplayString,
        ptLBConnectionTargetSlot        INTEGER,
        ptLBConnectionConnectionPortsCount  INTEGER,
        ptLBConnectionInternalID        Integer32,
        ptLBConnectionStatus            DisplayString,
        ptLBConnectionLoadBalancerIndex Integer32,
        ptLBConnectionConnectionsIndex  Integer32,
        ptLBConnectionParentOID         OBJECT IDENTIFIER,
        ptLBConnectionRowStatus         RowStatus,
        ptLBConnectionIndex             Integer32
    }

ptLBConnectionName OBJECT-TYPE
    SYNTAX          DisplayString (SIZE(0..255))
    MAX-ACCESS      read-only
    STATUS          current
    DESCRIPTION     
            "Name used to uniquely identify the connection. \nLeading and trailing whitespaces are trimmed. \nValid values: alphanumeric characters, dashes, and underscores (maximum size of 64)."
    ::= { ptLBConnectionEntry 1 }

ptLBConnectionTargetName OBJECT-TYPE
    SYNTAX          DisplayString (SIZE(0..255))
    MAX-ACCESS      read-create
    STATUS          current
    DESCRIPTION     
            "The load balancer target hosting this connection. \nValid values: Existing load balancer target."
    ::= { ptLBConnectionEntry 2 }

ptLBConnectionTransportType OBJECT-TYPE
    SYNTAX          INTEGER { sctp(0), tcp(1), ipsec(2) }
    MAX-ACCESS      read-create
    STATUS          current
    DESCRIPTION     
            "Transport Type (SCTP, TCP, IPSec) \nSet to the transport type between the remote host and the local host. \nThe following applies to IPSec only: \no A Connection Ports object is automatically added to the connection. \no The user cannot add or remove Connection Ports. \no The user can delete the connection without deleting the automatically-added Connection Ports object. \nDefault value: SCTP."
    ::= { ptLBConnectionEntry 3 }

ptLBConnectionLocalHost OBJECT-TYPE
    SYNTAX          DisplayString (SIZE(0..255))
    MAX-ACCESS      read-create
    STATUS          current
    DESCRIPTION     
            "Local host for the connection. \nValid values: Hostname or IPv4 address."
    ::= { ptLBConnectionEntry 4 }

ptLBConnectionRemoteHost OBJECT-TYPE
    SYNTAX          DisplayString (SIZE(0..255))
    MAX-ACCESS      read-create
    STATUS          current
    DESCRIPTION     
            "Remote host for the connection. \nValid values: Hostname or IPv4 address."
    ::= { ptLBConnectionEntry 6 }

ptLBConnectionTargetSlot OBJECT-TYPE
    SYNTAX          INTEGER { unset(-1) }
    MAX-ACCESS      read-create
    STATUS          current
    DESCRIPTION     
            "Target Slot for the connection. \nThe DSC routing slot currently serving this connection. \nCan only be set when the target load balancing algorithm is set to STATIC MAPPING. \nValid values: A DSC slot defined in the target slots or the string UNSET."
    ::= { ptLBConnectionEntry 8 }

ptLBConnectionConnectionPortsCount OBJECT-TYPE
    SYNTAX          INTEGER { undefined(0) }
    MAX-ACCESS      read-only
    STATUS          current
    DESCRIPTION     
            "Connection Ports Count. \nThe number of Connection Ports configured in this connection. \nWhen no Connection Ports objects are configured on this connection, the value is set to UNDEFINED."
    ::= { ptLBConnectionEntry 9 }

ptLBConnectionInternalID OBJECT-TYPE
    SYNTAX          Integer32 (-2147483648..2147483647)
    MAX-ACCESS      read-only
    STATUS          current
    DESCRIPTION     
            "Connection unique internal ID. \nReserved for internal use."
    ::= { ptLBConnectionEntry 10 }

ptLBConnectionStatus OBJECT-TYPE
    SYNTAX          DisplayString (SIZE(0..255))
    MAX-ACCESS      read-only
    STATUS          current
    DESCRIPTION     
            "Configuration status. \nIndicates the status of the most recent configuration modification \nor that configuration is in progress. \nBUSY indicates that new configuration is temporarily blocked."
    ::= { ptLBConnectionEntry 11 }

ptLBConnectionLoadBalancerIndex OBJECT-TYPE
    SYNTAX          Integer32 (-2147483648..2147483647)
    MAX-ACCESS      not-accessible
    STATUS          current
    DESCRIPTION     
            "This is the index of the parent type for this object.
             This parent type is LoadBalancer."
    ::= { ptLBConnectionEntry 242 }

ptLBConnectionConnectionsIndex OBJECT-TYPE
    SYNTAX          Integer32 (-2147483648..2147483647)
    MAX-ACCESS      not-accessible
    STATUS          current
    DESCRIPTION     
            "This is the index of the parent type for this object.
             This parent type is Connections."
    ::= { ptLBConnectionEntry 243 }

ptLBConnectionParentOID OBJECT-TYPE
    SYNTAX          OBJECT IDENTIFIER
    MAX-ACCESS      read-create
    STATUS          current
    DESCRIPTION     
            "The OID of the parent object for this instance"
    ::= { ptLBConnectionEntry 253 }

ptLBConnectionRowStatus OBJECT-TYPE
    SYNTAX          RowStatus
    MAX-ACCESS      read-create
    STATUS          current
    DESCRIPTION     
            "The row status for the LBConnection table"
    ::= { ptLBConnectionEntry 254 }

ptLBConnectionIndex OBJECT-TYPE
    SYNTAX          Integer32 (-2147483648..2147483647)
    MAX-ACCESS      not-accessible
    STATUS          current
    DESCRIPTION     
            "The row number for the LBConnection table"
    ::= { ptLBConnectionEntry 255 }

ptLBConnectionPorts OBJECT IDENTIFIER
    ::= { ptLBConnection 5007 }

ptLBConnectionPortsTable OBJECT-TYPE
    SYNTAX          SEQUENCE OF PtLBConnectionPortsEntry
    MAX-ACCESS      not-accessible
    STATUS          current
    DESCRIPTION     
            "No description supplied in the proxy config file."
    ::= { ptLBConnectionPorts 1 }

ptLBConnectionPortsEntry OBJECT-TYPE
    SYNTAX          PtLBConnectionPortsEntry
    MAX-ACCESS      not-accessible
    STATUS          current
    DESCRIPTION     
            "A sequence of LBConnectionPorts attributes."
    INDEX           { ptConnGroupIndex, 
                      ptLBConnectionPortsLoadBalancerIndex, 
                      ptLBConnectionPortsConnectionsIndex, 
                      ptLBConnectionPortsConnectionIndex, 
                      ptLBConnectionPortsIndex }
    ::= { ptLBConnectionPortsTable 1 }

PtLBConnectionPortsEntry ::=
    SEQUENCE {
        ptLBConnectionPortsLocalPort    DisplayString,
        ptLBConnectionPortsRemotePort   DisplayString,
        ptLBConnectionPortsInternalID   Integer32,
        ptLBConnectionPortsLoadBalancerIndex    Integer32,
        ptLBConnectionPortsConnectionsIndex   Integer32,
        ptLBConnectionPortsConnectionIndex  Integer32,
        ptLBConnectionPortsParentOID    OBJECT IDENTIFIER,
        ptLBConnectionPortsRowStatus    RowStatus,
        ptLBConnectionPortsIndex        Integer32
    }

ptLBConnectionPortsLocalPort OBJECT-TYPE
    SYNTAX          DisplayString (SIZE(0..255))
    MAX-ACCESS      read-only
    STATUS          current
    DESCRIPTION     
            "Local port for the connection (ANY, 1 to 65535)."
    ::= { ptLBConnectionPortsEntry 1 }

ptLBConnectionPortsRemotePort OBJECT-TYPE
    SYNTAX          DisplayString (SIZE(0..255))
    MAX-ACCESS      read-only
    STATUS          current
    DESCRIPTION     
            "Remote port for the connection (ANY, 1 to 65535)."
    ::= { ptLBConnectionPortsEntry 2 }

ptLBConnectionPortsInternalID OBJECT-TYPE
    SYNTAX          Integer32 (-2147483648..2147483647)
    MAX-ACCESS      read-only
    STATUS          current
    DESCRIPTION     
            "Target unique internal ID. \nReserved for internal use."
    ::= { ptLBConnectionPortsEntry 3 }

ptLBConnectionPortsLoadBalancerIndex OBJECT-TYPE
    SYNTAX          Integer32 (-2147483648..2147483647)
    MAX-ACCESS      not-accessible
    STATUS          current
    DESCRIPTION     
            "This is the index of the parent type for this object.
             This parent type is LoadBalancer."
    ::= { ptLBConnectionPortsEntry 242 }

ptLBConnectionPortsConnectionsIndex OBJECT-TYPE
    SYNTAX          Integer32 (-2147483648..2147483647)
    MAX-ACCESS      not-accessible
    STATUS          current
    DESCRIPTION     
            "This is the index of the parent type for this object.
             This parent type is Connections."
    ::= { ptLBConnectionPortsEntry 243 }

ptLBConnectionPortsConnectionIndex OBJECT-TYPE
    SYNTAX          Integer32 (-2147483648..2147483647)
    MAX-ACCESS      not-accessible
    STATUS          current
    DESCRIPTION     
            "This is the index of the parent type for this object.
             This parent type is Connection."
    ::= { ptLBConnectionPortsEntry 244 }

ptLBConnectionPortsParentOID OBJECT-TYPE
    SYNTAX          OBJECT IDENTIFIER
    MAX-ACCESS      read-create
    STATUS          current
    DESCRIPTION     
            "The OID of the parent object for this instance"
    ::= { ptLBConnectionPortsEntry 253 }

ptLBConnectionPortsRowStatus OBJECT-TYPE
    SYNTAX          RowStatus
    MAX-ACCESS      read-create
    STATUS          current
    DESCRIPTION     
            "The row status for the LBConnectionPorts table"
    ::= { ptLBConnectionPortsEntry 254 }

ptLBConnectionPortsIndex OBJECT-TYPE
    SYNTAX          Integer32 (-2147483648..2147483647)
    MAX-ACCESS      not-accessible
    STATUS          current
    DESCRIPTION     
            "The row number for the LBConnectionPorts table"
    ::= { ptLBConnectionPortsEntry 255 }

ptTrapSequenceNumber OBJECT-TYPE
    SYNTAX          Integer32
    MAX-ACCESS      read-only
    STATUS          current
    DESCRIPTION     
            "The trap sequence number.   The trap sequence number
             should be maintained across system resets."
    ::= { ptiSegway 1011 }

ptTrapDateAndTime OBJECT-TYPE
    SYNTAX          DisplayString
    MAX-ACCESS      read-only
    STATUS          current
    DESCRIPTION     
            "The date and time at which the trap was emitted."
    ::= { ptiSegway 1012 }

ptTrapType OBJECT-TYPE
    SYNTAX          INTEGER { communicationAlarm(2), environmentAlarm(3), 
                        equipmentAlarm(4), processingAlarm(10), 
                        qualityOfServiceAlarm(11), undefined(9999) }
    MAX-ACCESS      read-only
    STATUS          current
    DESCRIPTION     
            "The type of the trap, follows Ref. X.733:
             
             Communication Alarm
                 An alarm of this type is principally associated with 
                 the procedures and/or processes required to convey
                 information from one point to another.
             Quality of Service Alarm
                 An alarm of this type is principally associated with
                 a degradation in the quality of a service.
             Processing Error Alarm
                 An alarm of this type is principally associated with
                 a software or processing fault.
             Equipment Alarm
                 An alarm of this type is principally associated with
                 an equipment fault.
             Environmental Alarm
                 An alarm of this type is principally associated with
                 a condition relating to an enclosure in which the
                 equipment resides.
             "
    ::= { ptiSegway 1013 }

ptEntityInstance OBJECT-TYPE
    SYNTAX          OBJECT IDENTIFIER
    MAX-ACCESS      read-only
    STATUS          current
    DESCRIPTION     
            "The instance of the entity which emitted the trap.
             entityInstance is zero for traps which are issued by scalar
             objects (i.e., traps that are not associated with tables)."
    ::= { ptiSegway 1014 }

ptTrapSeverity OBJECT-TYPE
    SYNTAX          INTEGER { critical(1), major(2), minor(3), 
                        warning(4), cleared(5), indeterminate(6) }
    MAX-ACCESS      read-only
    STATUS          current
    DESCRIPTION     
            "Severity is used in the reporting of traps.  When a trap is
             issued it will have an associated severity."
    ::= { ptiSegway 1015 }

ptTrapClearType OBJECT-TYPE
    SYNTAX          INTEGER { fmic(1), oic(2), undefined(3) }
    MAX-ACCESS      read-only
    STATUS          current
    DESCRIPTION     
            "The Clear type of the trap, which is either FMIC or OIC,
             where FMIX means that the trap will be cleared by another
             clear trap, and C means that the trap needs to be cleared 
             by the operator."
    ::= { ptiSegway 1016 }

ptTrapProbableCause OBJECT-TYPE
    SYNTAX          Integer32 (0..57)
    MAX-ACCESS      read-only
    STATUS          current
    DESCRIPTION     
            "The probable cause of the trap, follows Ref. X.733.
             
             After we identify the GSN alarms, we will categorize
             them according to the five types above, find their
             probable causes, and map the causes, as close as we
             can, to the X.733 list.
             "
    ::= { ptiSegway 1017 }

ptTrapSlotNumber OBJECT-TYPE
    SYNTAX          Integer32
    MAX-ACCESS      read-only
    STATUS          current
    DESCRIPTION     
            "The slot number. This is used to indicate the slot from where
             The trap was issued."
    ::= { ptiSegway 1018 }

ptTrapDirectoryName OBJECT-TYPE
    SYNTAX          DisplayString (SIZE(0..255))
    MAX-ACCESS      read-only
    STATUS          current
    DESCRIPTION     
            "The directory.  This is used to indicate the directory referenced
             by the trap."
    ::= { ptiSegway 1019 }

ptTrapCpuCore OBJECT-TYPE
    SYNTAX          DisplayString (SIZE(0..255))
    MAX-ACCESS      read-only
    STATUS          current
    DESCRIPTION     
            "The CPU Core. This is used to indicate the CPU core for which the 
             trap was issued."
    ::= { ptiSegway 1020 }

ptTrapCpuUsage OBJECT-TYPE
    SYNTAX          DisplayString (SIZE(0..255))
    MAX-ACCESS      read-only
    STATUS          current
    DESCRIPTION     
            "The CPU Usage. This is used to indicate the CPU usage date reported in 
             the trap."
    ::= { ptiSegway 1021 }

ptTrapItemOID OBJECT-TYPE
    SYNTAX          DisplayString (SIZE(0..255))
    MAX-ACCESS      read-only
    STATUS          current
    DESCRIPTION     
            "The Item OID. This is used to indicate the trap associated object OID."
    ::= { ptiSegway 1026 }

ptGWSTConfigurationGR310ConnectionDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A connection loss was detected on at least one routing CPU and the active GR-310 server."
    ::= { ptiSegway 0 1001 }

ptGWSTConfigurationGR310ConnectionUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All routing CPUs are connected to the active GR-310 server"
    ::= { ptiSegway 0 1002 }

ptGWSTConfigurationGR310MesageLoss NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Message loss was detected from at least one routing CPU to the active GR-310 server."
    ::= { ptiSegway 0 1003 }

ptGWSTConfigurationGR310MessageLossClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "No further message loss has been reported to the active GR-310 server in the last 5 minutes"
    ::= { ptiSegway 0 1004 }

ptGWSTConfigurationGR310ExcessiveMesssaging NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Autonomous GR-310 messages discared by GWST destined to the active GR-310 server."
    ::= { ptiSegway 0 1005 }

ptGWSTConfigurationGR310ExcessiveMessagingClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "No further autonomous messages have been discarded destined the active GR-310 server in the last 5 minutes"
    ::= { ptiSegway 0 1006 }

ptDBConnectionDBConnectionDown NOTIFICATION-TYPE
    OBJECTS         { ptTrapType, ptTrapSequenceNumber, ptTrapSeverity, 
                      ptTrapProbableCause, ptTrapClearType, 
                      ptTrapDateAndTime, ptTrapItemOID, 
                      ptdscdbDBConnectionSlot, 
                      ptdscdbDBConnectionConnectivityStatus }
    STATUS          current
    DESCRIPTION     
            "The DB Agent is not connected to its local database."
    ::= { ptiSegway 0 1191 }

ptDBConnectionDBConnectionUp NOTIFICATION-TYPE
    OBJECTS         { ptTrapType, ptTrapSequenceNumber, ptTrapSeverity, 
                      ptTrapProbableCause, ptTrapClearType, 
                      ptTrapDateAndTime, ptTrapItemOID, 
                      ptdscdbDBConnectionSlot, 
                      ptdscdbDBConnectionConnectivityStatus }
    STATUS          current
    DESCRIPTION     
            "The DB Agent is now connected to its local database."
    ::= { ptiSegway 0 1192 }

ptINAPGWConfigurationINAPGWSS7Down NOTIFICATION-TYPE
    OBJECTS         { ptTrapType, ptTrapSequenceNumber, ptTrapSeverity, 
                      ptTrapProbableCause, ptTrapClearType, 
                      ptTrapDateAndTime, ptTrapItemOID, 
                      ptinapgwINAPGWConfigurationTrafficStatus }
    STATUS          current
    DESCRIPTION     
            "The INAPGW traffic is deactivated or all SCCP NAs are not connected."
    ::= { ptiSegway 0 1301 }

ptINAPGWConfigurationINAPGWSS7Up NOTIFICATION-TYPE
    OBJECTS         { ptTrapType, ptTrapSequenceNumber, ptTrapSeverity, 
                      ptTrapProbableCause, ptTrapClearType, 
                      ptTrapDateAndTime, ptTrapItemOID, 
                      ptinapgwINAPGWConfigurationTrafficStatus }
    STATUS          current
    DESCRIPTION     
            "At least one INAPGW SCCP NA is connected."
    ::= { ptiSegway 0 1302 }

ptSCCPNAINAPGWSCCPNADown NOTIFICATION-TYPE
    OBJECTS         { ptTrapType, ptTrapSequenceNumber, ptTrapSeverity, 
                      ptTrapProbableCause, ptTrapClearType, 
                      ptTrapDateAndTime, ptTrapItemOID, ptinapgwSCCPNANA, 
                      ptinapgwSCCPNAStatus }
    STATUS          current
    DESCRIPTION     
            "The SCCP NA is deactivated or all SCCP NA connections are not connected."
    ::= { ptiSegway 0 1303 }

ptSCCPNAINAPGWSCCPNAUp NOTIFICATION-TYPE
    OBJECTS         { ptTrapType, ptTrapSequenceNumber, ptTrapSeverity, 
                      ptTrapProbableCause, ptTrapClearType, 
                      ptTrapDateAndTime, ptTrapItemOID, ptinapgwSCCPNANA, 
                      ptinapgwSCCPNAStatus }
    STATUS          current
    DESCRIPTION     
            "Atleast one INAPGW SCCP NA connection is connected."
    ::= { ptiSegway 0 1304 }

ptSCCPNAConnectionINAPGWSCCPNAConnectionDown NOTIFICATION-TYPE
    OBJECTS         { ptTrapType, ptTrapSequenceNumber, ptTrapSeverity, 
                      ptTrapProbableCause, ptTrapClearType, 
                      ptTrapDateAndTime, ptTrapItemOID, 
                      ptinapgwSCCPNAConnectionSlot, 
                      ptinapgwSCCPNAConnectionStatus }
    STATUS          current
    DESCRIPTION     
            "The INAPGW NA traffic is deactivated or the SCCP NA connection is not connected."
    ::= { ptiSegway 0 1305 }

ptSCCPNAConnectionINAPGWSCCPNAConnectionUp NOTIFICATION-TYPE
    OBJECTS         { ptTrapType, ptTrapSequenceNumber, ptTrapSeverity, 
                      ptTrapProbableCause, ptTrapClearType, 
                      ptTrapDateAndTime, ptTrapItemOID, 
                      ptinapgwSCCPNAConnectionSlot, 
                      ptinapgwSCCPNAConnectionStatus }
    STATUS          current
    DESCRIPTION     
            "The SCCP NA connection is connected."
    ::= { ptiSegway 0 1306 }

ptSCCPPCSSNRegistrationINAPGWSCCPPCSSNFailure NOTIFICATION-TYPE
    OBJECTS         { ptTrapType, ptTrapSequenceNumber, ptTrapSeverity, 
                      ptTrapProbableCause, ptTrapClearType, 
                      ptTrapDateAndTime, ptTrapItemOID, 
                      ptinapgwSCCPPCSSNRegistrationNA, 
                      ptinapgwSCCPPCSSNRegistrationPC, 
                      ptinapgwSCCPPCSSNRegistrationSSN, 
                      ptinapgwSCCPPCSSNRegistrationStatus }
    STATUS          current
    DESCRIPTION     
            "The SCCP PC-SSN registration was not successful on all the defined SCCP connections."
    ::= { ptiSegway 0 1307 }

ptSCCPPCSSNRegistrationINAPGWSCCPPCSSNSuccess NOTIFICATION-TYPE
    OBJECTS         { ptTrapType, ptTrapSequenceNumber, ptTrapSeverity, 
                      ptTrapProbableCause, ptTrapClearType, 
                      ptTrapDateAndTime, ptTrapItemOID, 
                      ptinapgwSCCPPCSSNRegistrationNA, 
                      ptinapgwSCCPPCSSNRegistrationPC, 
                      ptinapgwSCCPPCSSNRegistrationSSN, 
                      ptinapgwSCCPPCSSNRegistrationStatus }
    STATUS          current
    DESCRIPTION     
            "The SCCP PC-SSN registration was successful on all the defined SCCP connections."
    ::= { ptiSegway 0 1308 }

ptSCCPAppIDRegistrationINAPGWSCCPAppIDFailure NOTIFICATION-TYPE
    OBJECTS         { ptTrapType, ptTrapSequenceNumber, ptTrapSeverity, 
                      ptTrapProbableCause, ptTrapClearType, 
                      ptTrapDateAndTime, ptTrapItemOID, 
                      ptinapgwSCCPAppIDRegistrationNA, 
                      ptinapgwSCCPAppIDRegistrationApplicationID, 
                      ptinapgwSCCPAppIDRegistrationStatus }
    STATUS          current
    DESCRIPTION     
            "The SCCP AppID registration was not successful on all the defined SCCP connections."
    ::= { ptiSegway 0 1309 }

ptSCCPAppIDRegistrationINAPGWSCCPAppIDSuccess NOTIFICATION-TYPE
    OBJECTS         { ptTrapType, ptTrapSequenceNumber, ptTrapSeverity, 
                      ptTrapProbableCause, ptTrapClearType, 
                      ptTrapDateAndTime, ptTrapItemOID, 
                      ptinapgwSCCPAppIDRegistrationNA, 
                      ptinapgwSCCPAppIDRegistrationApplicationID, 
                      ptinapgwSCCPAppIDRegistrationStatus }
    STATUS          current
    DESCRIPTION     
            "The SCCP AppID registration was successful on all the defined SCCP connections."
    ::= { ptiSegway 0 1310 }

ptINAPGWConfigurationINAPGWDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 1311 }

ptINAPGWConfigurationINAPGWDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 1312 }

ptSNAMIConfigurationGR310TL1ConnDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "On session request, the TL1 connection cannot be established by GR310 server. 
             The event will be cleared if no other occurrences is raised in the next 
             5 minutes."
    ::= { ptiSegway 0 1501 }

ptSNAMIConfigurationGR310TL1ConnUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The GR310 server TL1 connection is now up or interval has expired."
    ::= { ptiSegway 0 1502 }

ptSNAMIConfigurationGR310MessageLoss NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The GR310 server has rejected a message due to UPL header or message decode
             error, unsupported message, or response message cannot be returned due to loss 
             of client.
             The event will be cleared if no other occurrences is raised in the next 
             5 minutes."
    ::= { ptiSegway 0 1503 }

ptSNAMIConfigurationGR310MessageLossClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The GR310 server message loss interval has expired."
    ::= { ptiSegway 0 1504 }

ptSNAMIConfigurationSNAMIUnavailable NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The SNAMI is user activated but unavailable."
    ::= { ptiSegway 0 1505 }

ptSNAMIConfigurationSNAMIAvailable NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The SNAMI is available."
    ::= { ptiSegway 0 1506 }

ptGR310ServerConfigurationGR310ServerDown NOTIFICATION-TYPE
    OBJECTS         { ptTrapType, ptTrapSequenceNumber, ptTrapSeverity, 
                      ptTrapProbableCause, ptTrapClearType, 
                      ptTrapDateAndTime, ptTrapItemOID, 
                      ptsnamiGR310ServerConfigurationSlot }
    STATUS          current
    DESCRIPTION     
            "The GR310 server is down."
    ::= { ptiSegway 0 1507 }

ptGR310ServerConfigurationGR310ServerUp NOTIFICATION-TYPE
    OBJECTS         { ptTrapType, ptTrapSequenceNumber, ptTrapSeverity, 
                      ptTrapProbableCause, ptTrapClearType, 
                      ptTrapDateAndTime, ptTrapItemOID, 
                      ptsnamiGR310ServerConfigurationSlot }
    STATUS          current
    DESCRIPTION     
            "The GR310 server is up."
    ::= { ptiSegway 0 1508 }

ptNPGWConfigurationNPGWSCCPDown NOTIFICATION-TYPE
    OBJECTS         { ptTrapType, ptTrapSequenceNumber, ptTrapSeverity, 
                      ptTrapProbableCause, ptTrapClearType, 
                      ptTrapDateAndTime, ptTrapItemOID, 
                      ptnpgwNPGWConfigurationSCCPTrafficStatus }
    STATUS          current
    DESCRIPTION     
            "The NPGW traffic is deactivated or all SCCP NAs are not connected."
    ::= { ptiSegway 0 1601 }

ptNPGWConfigurationNPGWSCCPUp NOTIFICATION-TYPE
    OBJECTS         { ptTrapType, ptTrapSequenceNumber, ptTrapSeverity, 
                      ptTrapProbableCause, ptTrapClearType, 
                      ptTrapDateAndTime, ptTrapItemOID, 
                      ptnpgwNPGWConfigurationSCCPTrafficStatus }
    STATUS          current
    DESCRIPTION     
            "At least one NPGW SCCP NA is connected."
    ::= { ptiSegway 0 1602 }

ptSCCPNANPGWSCCPNADown NOTIFICATION-TYPE
    OBJECTS         { ptTrapType, ptTrapSequenceNumber, ptTrapSeverity, 
                      ptTrapProbableCause, ptTrapClearType, 
                      ptTrapDateAndTime, ptTrapItemOID, ptnpgwSCCPNANA, 
                      ptnpgwSCCPNAStatus }
    STATUS          current
    DESCRIPTION     
            "The SCCP NA is deactivated or all SCCP NA connections are not connected."
    ::= { ptiSegway 0 1603 }

ptSCCPNANPGWSCCPNAUp NOTIFICATION-TYPE
    OBJECTS         { ptTrapType, ptTrapSequenceNumber, ptTrapSeverity, 
                      ptTrapProbableCause, ptTrapClearType, 
                      ptTrapDateAndTime, ptTrapItemOID, ptnpgwSCCPNANA, 
                      ptnpgwSCCPNAStatus }
    STATUS          current
    DESCRIPTION     
            "Atleast one NPGW SCCP NA connection is connected."
    ::= { ptiSegway 0 1604 }

ptSCCPNAConnectionNPGWSCCPNAConnectionDown NOTIFICATION-TYPE
    OBJECTS         { ptTrapType, ptTrapSequenceNumber, ptTrapSeverity, 
                      ptTrapProbableCause, ptTrapClearType, 
                      ptTrapDateAndTime, ptTrapItemOID, 
                      ptnpgwSCCPNAConnectionSlot, 
                      ptnpgwSCCPNAConnectionStatus }
    STATUS          current
    DESCRIPTION     
            "The NPGW NA traffic is deactivated or the SCCP NA connection is not connected."
    ::= { ptiSegway 0 1605 }

ptSCCPNAConnectionNPGWSCCPNAConnectionUp NOTIFICATION-TYPE
    OBJECTS         { ptTrapType, ptTrapSequenceNumber, ptTrapSeverity, 
                      ptTrapProbableCause, ptTrapClearType, 
                      ptTrapDateAndTime, ptTrapItemOID, 
                      ptnpgwSCCPNAConnectionSlot, 
                      ptnpgwSCCPNAConnectionStatus }
    STATUS          current
    DESCRIPTION     
            "The SCCP NA connection is connected."
    ::= { ptiSegway 0 1606 }

ptSCCPPCSSNRegistrationNPGWSCCPPCSSNFailure NOTIFICATION-TYPE
    OBJECTS         { ptTrapType, ptTrapSequenceNumber, ptTrapSeverity, 
                      ptTrapProbableCause, ptTrapClearType, 
                      ptTrapDateAndTime, ptTrapItemOID, 
                      ptnpgwSCCPPCSSNRegistrationNA, 
                      ptnpgwSCCPPCSSNRegistrationPC, 
                      ptnpgwSCCPPCSSNRegistrationSSN, 
                      ptnpgwSCCPPCSSNRegistrationStatus }
    STATUS          current
    DESCRIPTION     
            "The SCCP PC-SSN registration was not successful on all the defined SCCP connections."
    ::= { ptiSegway 0 1607 }

ptSCCPPCSSNRegistrationNPGWSCCPPCSSNSuccess NOTIFICATION-TYPE
    OBJECTS         { ptTrapType, ptTrapSequenceNumber, ptTrapSeverity, 
                      ptTrapProbableCause, ptTrapClearType, 
                      ptTrapDateAndTime, ptTrapItemOID, 
                      ptnpgwSCCPPCSSNRegistrationNA, 
                      ptnpgwSCCPPCSSNRegistrationPC, 
                      ptnpgwSCCPPCSSNRegistrationSSN, 
                      ptnpgwSCCPPCSSNRegistrationStatus }
    STATUS          current
    DESCRIPTION     
            "The SCCP PC-SSN registration was successful on all the defined SCCP connections."
    ::= { ptiSegway 0 1608 }

ptSCCPAppIDRegistrationNPGWSCCPAppIDFailure NOTIFICATION-TYPE
    OBJECTS         { ptTrapType, ptTrapSequenceNumber, ptTrapSeverity, 
                      ptTrapProbableCause, ptTrapClearType, 
                      ptTrapDateAndTime, ptTrapItemOID, 
                      ptnpgwSCCPAppIDRegistrationNA, 
                      ptnpgwSCCPAppIDRegistrationApplicationID, 
                      ptnpgwSCCPAppIDRegistrationStatus }
    STATUS          current
    DESCRIPTION     
            "The SCCP AppID registration was not successful on all the defined SCCP connections."
    ::= { ptiSegway 0 1609 }

ptSCCPAppIDRegistrationNPGWSCCPAppIDSuccess NOTIFICATION-TYPE
    OBJECTS         { ptTrapType, ptTrapSequenceNumber, ptTrapSeverity, 
                      ptTrapProbableCause, ptTrapClearType, 
                      ptTrapDateAndTime, ptTrapItemOID, 
                      ptnpgwSCCPAppIDRegistrationNA, 
                      ptnpgwSCCPAppIDRegistrationApplicationID, 
                      ptnpgwSCCPAppIDRegistrationStatus }
    STATUS          current
    DESCRIPTION     
            "The SCCP AppID registration was successful on all the defined SCCP connections."
    ::= { ptiSegway 0 1610 }

ptMTP3NANPGWMTP3NADown NOTIFICATION-TYPE
    OBJECTS         { ptTrapType, ptTrapSequenceNumber, ptTrapSeverity, 
                      ptTrapProbableCause, ptTrapClearType, 
                      ptTrapDateAndTime, ptTrapItemOID, ptnpgwMTP3NANA, 
                      ptnpgwMTP3NAStatus }
    STATUS          current
    DESCRIPTION     
            "The MTP3 NA is deactivated or all MTP3 NA connections are not connected."
    ::= { ptiSegway 0 1611 }

ptMTP3NANPGWMTP3NAUp NOTIFICATION-TYPE
    OBJECTS         { ptTrapType, ptTrapSequenceNumber, ptTrapSeverity, 
                      ptTrapProbableCause, ptTrapClearType, 
                      ptTrapDateAndTime, ptTrapItemOID, ptnpgwMTP3NANA, 
                      ptnpgwMTP3NAStatus }
    STATUS          current
    DESCRIPTION     
            "Atleast one NPGW MTP3 NA connection is connected."
    ::= { ptiSegway 0 1612 }

ptMTP3NAConnectionNPGWMTP3NAConnectionDown NOTIFICATION-TYPE
    OBJECTS         { ptTrapType, ptTrapSequenceNumber, ptTrapSeverity, 
                      ptTrapProbableCause, ptTrapClearType, 
                      ptTrapDateAndTime, ptTrapItemOID, 
                      ptnpgwMTP3NAConnectionSlot, 
                      ptnpgwMTP3NAConnectionStatus }
    STATUS          current
    DESCRIPTION     
            "The NPGW NA traffic is deactivated or the MTP3 NA connection is not connected."
    ::= { ptiSegway 0 1613 }

ptMTP3NAConnectionNPGWMTP3NAConnectionUp NOTIFICATION-TYPE
    OBJECTS         { ptTrapType, ptTrapSequenceNumber, ptTrapSeverity, 
                      ptTrapProbableCause, ptTrapClearType, 
                      ptTrapDateAndTime, ptTrapItemOID, 
                      ptnpgwMTP3NAConnectionSlot, 
                      ptnpgwMTP3NAConnectionStatus }
    STATUS          current
    DESCRIPTION     
            "The MTP3 NA connection is connected."
    ::= { ptiSegway 0 1614 }

ptMTP3RegistrationNPGWMTP3AppIDFailure NOTIFICATION-TYPE
    OBJECTS         { ptTrapType, ptTrapSequenceNumber, ptTrapSeverity, 
                      ptTrapProbableCause, ptTrapClearType, 
                      ptTrapDateAndTime, ptTrapItemOID, 
                      ptnpgwMTP3RegistrationNA, 
                      ptnpgwMTP3RegistrationApplicationID, 
                      ptnpgwMTP3RegistrationStatus }
    STATUS          current
    DESCRIPTION     
            "The MTP3 AppID registration was not successful on all the defined MTP3 connections."
    ::= { ptiSegway 0 1615 }

ptMTP3RegistrationNPGWMTP3AppIDSuccess NOTIFICATION-TYPE
    OBJECTS         { ptTrapType, ptTrapSequenceNumber, ptTrapSeverity, 
                      ptTrapProbableCause, ptTrapClearType, 
                      ptTrapDateAndTime, ptTrapItemOID, 
                      ptnpgwMTP3RegistrationNA, 
                      ptnpgwMTP3RegistrationApplicationID, 
                      ptnpgwMTP3RegistrationStatus }
    STATUS          current
    DESCRIPTION     
            "The MTP3 AppID registration was successful on all the defined MTP3 connections."
    ::= { ptiSegway 0 1616 }

ptNPGWConfigurationNPGWMTP3Down NOTIFICATION-TYPE
    OBJECTS         { ptTrapType, ptTrapSequenceNumber, ptTrapSeverity, 
                      ptTrapProbableCause, ptTrapClearType, 
                      ptTrapDateAndTime, ptTrapItemOID, 
                      ptnpgwNPGWConfigurationMTP3TrafficStatus }
    STATUS          current
    DESCRIPTION     
            "The NPGW traffic is deactivated or all MTP3 NAs are not connected."
    ::= { ptiSegway 0 1617 }

ptNPGWConfigurationNPGWMTP3Up NOTIFICATION-TYPE
    OBJECTS         { ptTrapType, ptTrapSequenceNumber, ptTrapSeverity, 
                      ptTrapProbableCause, ptTrapClearType, 
                      ptTrapDateAndTime, ptTrapItemOID, 
                      ptnpgwNPGWConfigurationMTP3TrafficStatus }
    STATUS          current
    DESCRIPTION     
            "At least one NPGW MTP3 NA is connected."
    ::= { ptiSegway 0 1618 }

ptPSXHostNPGWPSXHostDown NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostStatus }
    STATUS          current
    DESCRIPTION     
            "The NPGW PSX Host is not connected."
    ::= { ptiSegway 0 1619 }

ptPSXHostNPGWPSXHostUp NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostStatus }
    STATUS          current
    DESCRIPTION     
            "The NPGW PSX Host is connected."
    ::= { ptiSegway 0 1620 }

ptPSXHostConnectionNPGWPSXHostConnDown NOTIFICATION-TYPE
    OBJECTS         { ptTrapType, ptTrapSequenceNumber, ptTrapSeverity, 
                      ptTrapProbableCause, ptTrapClearType, 
                      ptTrapDateAndTime, ptTrapItemOID, 
                      ptnpgwPSXHostConnectionSlot, 
                      ptnpgwPSXHostConnectionStatus }
    STATUS          current
    DESCRIPTION     
            "The NPGW PSX Host Connection is deactivated or not connected."
    ::= { ptiSegway 0 1621 }

ptPSXHostConnectionNPGWPSXHostConnUp NOTIFICATION-TYPE
    OBJECTS         { ptTrapType, ptTrapSequenceNumber, ptTrapSeverity, 
                      ptTrapProbableCause, ptTrapClearType, 
                      ptTrapDateAndTime, ptTrapItemOID, 
                      ptnpgwPSXHostConnectionSlot, 
                      ptnpgwPSXHostConnectionStatus }
    STATUS          current
    DESCRIPTION     
            "The NPGW PSX Host Connection is connected."
    ::= { ptiSegway 0 1622 }

ptPSXNPGWPSXDown NOTIFICATION-TYPE
    OBJECTS         { ptTrapType, ptTrapSequenceNumber, ptTrapSeverity, 
                      ptTrapProbableCause, ptTrapClearType, 
                      ptTrapDateAndTime, ptTrapItemOID, ptnpgwPSXName, 
                      ptnpgwPSXStatus }
    STATUS          current
    DESCRIPTION     
            "The NPGW PSX is not connected."
    ::= { ptiSegway 0 1623 }

ptPSXNPGWPSXUp NOTIFICATION-TYPE
    OBJECTS         { ptTrapType, ptTrapSequenceNumber, ptTrapSeverity, 
                      ptTrapProbableCause, ptTrapClearType, 
                      ptTrapDateAndTime, ptTrapItemOID, ptnpgwPSXName, 
                      ptnpgwPSXStatus }
    STATUS          current
    DESCRIPTION     
            "The NPGW PSX is connected."
    ::= { ptiSegway 0 1624 }

ptPSXsNPGWPSXQueueFull NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The NPGW PSX queue is full."
    ::= { ptiSegway 0 1625 }

ptPSXsNPGWPSXQueueReady NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The NPGW PSX queue is no longer full for past 5 seconds."
    ::= { ptiSegway 0 1626 }

ptPSXHostNPGWPSXHostCongested NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostCongestion }
    STATUS          current
    DESCRIPTION     
            "The NPGW PSX Host is congested on at least one connection."
    ::= { ptiSegway 0 1627 }

ptPSXHostNPGWPSXHostCongestedClear NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostCongestion }
    STATUS          current
    DESCRIPTION     
            "The NPGW PSX Host is no longer congested."
    ::= { ptiSegway 0 1628 }

ptPSXNPGWPSXInactive NOTIFICATION-TYPE
    OBJECTS         { ptTrapType, ptTrapSequenceNumber, ptTrapSeverity, 
                      ptTrapProbableCause, ptTrapClearType, 
                      ptTrapDateAndTime, ptTrapItemOID, ptnpgwPSXName, 
                      ptnpgwPSXUserActivated }
    STATUS          current
    DESCRIPTION     
            "The NPGW PSX is deactivated."
    ::= { ptiSegway 0 1631 }

ptPSXNPGWPSXActive NOTIFICATION-TYPE
    OBJECTS         { ptTrapType, ptTrapSequenceNumber, ptTrapSeverity, 
                      ptTrapProbableCause, ptTrapClearType, 
                      ptTrapDateAndTime, ptTrapItemOID, ptnpgwPSXName, 
                      ptnpgwPSXUserActivated }
    STATUS          current
    DESCRIPTION     
            "The NPGW PSX is active."
    ::= { ptiSegway 0 1632 }

ptPSXHostNPGWPSXHostInactive NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostUserActivated }
    STATUS          current
    DESCRIPTION     
            "The NPGW PSX Host is deactivated."
    ::= { ptiSegway 0 1633 }

ptPSXHostNPGWPSXHostActive NOTIFICATION-TYPE
    OBJECTS         { ptTrapType, ptTrapSequenceNumber, ptTrapSeverity, 
                      ptTrapProbableCause, ptTrapClearType, 
                      ptTrapDateAndTime, ptTrapItemOID, 
                      ptnpgwPSXHostHost, ptnpgwPSXHostPort, 
                      ptnpgwPSXHostUserActivated }
    STATUS          current
    DESCRIPTION     
            "The NPGW PSX Host is active."
    ::= { ptiSegway 0 1634 }

ptNPGWConfigurationNPGWDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 1635 }

ptNPGWConfigurationNPGWDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 1636 }

ptADNConnectionADNConnectionDown NOTIFICATION-TYPE
    OBJECTS         { ptTrapType, ptTrapSequenceNumber, ptTrapSeverity, 
                      ptTrapProbableCause, ptTrapClearType, 
                      ptTrapDateAndTime, ptTrapItemOID, 
                      ptDSCADNConnectionSlot }
    STATUS          current
    DESCRIPTION     
            "The ADN Connection is down. Depending on the configuration, an outgoing connection has not been 
             established or the ADN has not attempted or established connectivity."
    ::= { ptiSegway 0 1801 }

ptADNConnectionADNConnectionCleared NOTIFICATION-TYPE
    OBJECTS         { ptTrapType, ptTrapSequenceNumber, ptTrapSeverity, 
                      ptTrapProbableCause, ptTrapClearType, 
                      ptTrapDateAndTime, ptTrapItemOID, 
                      ptDSCADNConnectionSlot }
    STATUS          current
    DESCRIPTION     
            "The ADN Connection is either deactivated, or connectivity is established on it."
    ::= { ptiSegway 0 1802 }

ptDSCNodesDSCLicenseUnavailable NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The license server may not be running or may not have valid license keys. 
             The DSC feature cannot be started."
    ::= { ptiSegway 0 1803 }

ptDSCNodesDSCLicenseAvailable NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "License keys have been received and validated."
    ::= { ptiSegway 0 1804 }

ptAdjacentDiameterNodeADNDown NOTIFICATION-TYPE
    OBJECTS         { ptTrapType, ptTrapSequenceNumber, ptTrapSeverity, 
                      ptTrapProbableCause, ptTrapClearType, 
                      ptTrapDateAndTime, ptTrapItemOID, 
                      ptDSCAdjacentDiameterNodeAdjacentDiameterID }
    STATUS          current
    DESCRIPTION     
            "The ADN is down. Depending on the configuration, an outgoing connection has not been 
             established or the ADN has not attempted or established connectivity."
    ::= { ptiSegway 0 1805 }

ptAdjacentDiameterNodeADNCleared NOTIFICATION-TYPE
    OBJECTS         { ptTrapType, ptTrapSequenceNumber, ptTrapSeverity, 
                      ptTrapProbableCause, ptTrapClearType, 
                      ptTrapDateAndTime, ptTrapItemOID, 
                      ptDSCAdjacentDiameterNodeAdjacentDiameterID }
    STATUS          current
    DESCRIPTION     
            "The ADN is now either deactivated, or connectivity is established on at least one connection."
    ::= { ptiSegway 0 1806 }

ptTransportServerServerUnavailable NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC cannot setup the server for the given host and port.  
             The host might not resolve to a configured address for that slot."
    ::= { ptiSegway 0 1807 }

ptTransportServerServerAvailable NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC has setup the server on the given host and port."
    ::= { ptiSegway 0 1808 }

ptDSCRoutingTablesDSCRoutingLoop NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC detects routing lookup runs too deep."
    ::= { ptiSegway 0 1809 }

ptDSCRoutingTablesDSCRoutingLoopClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC clears routing looping alarm after table record modification.
             The alarm should only be cleared when the customer modify the 
             followings to remove the loop routing lookup. These include
             1. Modificiation to nextTable/modTable attributes of the
             AVPRoutingRecord/ApplicationID/CommandCode/IncomingADN routing
             records. 2. Delete an AVPRoutingRecord/ApplicationID/CommandCode/
             IncomingADN/ModificationTable routing record. 3. Modification to
             the Command attribute of the ModificationTable. The alarm will be re-raised
             if the routing loop is not fixed properly"
    ::= { ptiSegway 0 1810 }

ptADNConnectionADNConnSecInvalid NOTIFICATION-TYPE
    OBJECTS         { ptTrapType, ptTrapSequenceNumber, ptTrapSeverity, 
                      ptTrapProbableCause, ptTrapClearType, 
                      ptTrapDateAndTime, ptTrapItemOID, 
                      ptDSCADNConnectionSlot }
    STATUS          current
    DESCRIPTION     
            "The ADN Connection security parameter certificate is invalid. The TLS security file is missing or corrupted."
    ::= { ptiSegway 0 1811 }

ptADNConnectionADNConnSecClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The ADN Connection is either deactivated, or connectivity is established on it with correct TLS security parameter certificate file."
    ::= { ptiSegway 0 1812 }

ptDSCNodesLoadConfigError NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A configuration file has one or more errors. Check warnings 
             in the debuglog log for more information."
    ::= { ptiSegway 0 1813 }

ptADNConnectionADNConnAssocPathLoss NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection path is down on a multi-homed user connection."
    ::= { ptiSegway 0 1814 }

ptADNConnectionADNConnAssocPathEstablished NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection path is up on a multi-homed user connection, following a path failure."
    ::= { ptiSegway 0 1815 }

ptServerPoolServerPoolNoDBPeerUP NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "No DB Peer is UP for use with Server Pool."
    ::= { ptiSegway 0 1816 }

ptServerPoolServerPoolNoDBPeerUPClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "DB Peer is no longer down for use with Server Pool."
    ::= { ptiSegway 0 1817 }

ptADNConnectionADNConnAssocMaxMsgSizeDiscard NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection Association discarded one or more messages exceeding maximum size."
    ::= { ptiSegway 0 1818 }

ptADNConnectionADNConnAssocMaxMsgSizeDiscardClear NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection Association has not received a message exceeding the maximum size in the past 30 seconds."
    ::= { ptiSegway 0 1819 }

ptADNConnectionADNConnAssocMaxMsgSizeAbort NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection Association closed because it received a message exceeding the maximum size."
    ::= { ptiSegway 0 1820 }

ptADNConnectionADNConnAssocMaxMsgSizeAbortClear NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost }
    STATUS          current
    DESCRIPTION     
            "ADN Connection Association is back up after aborting due to receiving an oversized message."
    ::= { ptiSegway 0 1821 }

ptTransportServerServerFirewallBlocked NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC server has Remote IP Validation enabled and no active or no resolved Allowed IPs.  This may be raised shortly after creation before host resolution has been received.
             Enabled Allowed IP(s) under the server and/or add host resolutions for those addresses."
    ::= { ptiSegway 0 1822 }

ptTransportServerServerFirewallCleared NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC server has at least one resolved Allowed IP address."
    ::= { ptiSegway 0 1823 }

ptADNConnectionADNConnectionFirewallBlocked NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionRemoteHost }
    STATUS          current
    DESCRIPTION     
            "No IP address resolutions can be made for the Remote Host.  With ADN Remote IP Validation ENABLED no connection can be successful.  Either change Remote Host or add a resolution for that value."
    ::= { ptiSegway 0 1824 }

ptADNConnectionADNConnectionFirewallCleared NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionRemoteHost }
    STATUS          current
    DESCRIPTION     
            "An IP address resolution can be made for the Remote Host.  Connections from that address will pass."
    ::= { ptiSegway 0 1825 }

ptTransportServerServerLocalEndPointConflict NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC server SCTP local end point has a conflict.  The host and port
             combination is in use by another server, ADNC, or different application.
             Review SCTP usage on the slot and host resolution for conflict."
    ::= { ptiSegway 0 1826 }

ptTransportServerServerLocalEndPointConflictCleared NOTIFICATION-TYPE
    OBJECTS         { ptTrapType, ptTrapSequenceNumber, ptTrapSeverity, 
                      ptTrapProbableCause, ptTrapClearType, 
                      ptTrapDateAndTime, ptTrapItemOID, 
                      ptDSCTransportServerSlot, ptDSCTransportServerPort, 
                      ptDSCTransportServerHost }
    STATUS          current
    DESCRIPTION     
            "The DSC server SCTP local end point conflict has been resolved.
             Note that deactivating the server clears the conflict."
    ::= { ptiSegway 0 1827 }

ptADNConnectionADNCLocalEndPointConflict NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection SCTP local end point has a conflict.  The local host and port
             combination is in use by another server, ADNC, or different application.
             Review SCTP usage on the slot and host resolution for conflict."
    ::= { ptiSegway 0 1828 }

ptADNConnectionADNCLocalEndPointConflictCleared NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection SCTP local end point conflict has been resolved.
             Note that deactivating the ADN Connection clears the conflict."
    ::= { ptiSegway 0 1829 }

ptTopologyOneToOnePublicMappingTopoMapRowMisconfig NOTIFICATION-TYPE
    OBJECTS         { ptTrapType, ptTrapSequenceNumber, ptTrapSeverity, 
                      ptTrapProbableCause, ptTrapClearType, 
                      ptTrapDateAndTime, ptTrapItemOID, 
                      ptDSCTopologyOneToOnePublicMappingRealm, 
                      ptDSCTopologyOneToOnePublicMappingPrivateDIDHost, 
                      ptDSCTopologyOneToOnePublicMappingPublicDIDHost }
    STATUS          current
    DESCRIPTION     
            "Topology Mapping misconfiguration: Private DID Host probably mis-configured as Public DID Host."
    ::= { ptiSegway 0 1830 }

ptTopologyOneToOnePublicMappingTopoMapRowMisconfigClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Topology Mapping misconfiguration: no misconfiguration deteceted in the last 5 minutes interval."
    ::= { ptiSegway 0 1831 }

ptModificationRecordModRecInvalid NOTIFICATION-TYPE
    OBJECTS         { ptTrapType, ptTrapSequenceNumber, ptTrapSeverity, 
                      ptTrapProbableCause, ptTrapClearType, 
                      ptTrapDateAndTime, ptTrapItemOID, 
                      ptDSCModificationRecordOrder, 
                      ptDSCModificationRecordCommand }
    STATUS          current
    DESCRIPTION     
            "A Modification Record entry is invalid. Check warnings 
             in the debuglog log for more information."
    ::= { ptiSegway 0 1833 }

ptModificationRecordModRecvalid NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Modification Record entry has been changed to be valid or has been deleted."
    ::= { ptiSegway 0 1834 }

ptIncomingADNRoutingTableDSCIncAdnDiscardConfigured NOTIFICATION-TYPE
    OBJECTS         { ptTrapType, ptTrapSequenceNumber, ptTrapSeverity, 
                      ptTrapProbableCause, ptTrapClearType, 
                      ptTrapDateAndTime, ptTrapItemOID, 
                      ptDSCIncomingADNRoutingTableTableName }
    STATUS          current
    DESCRIPTION     
            "The DSC routing table contains at least one table entry that is configured
             to discard messages.  This is highly discouraged."
    ::= { ptiSegway 0 1835 }

ptIncomingADNRoutingTableDSCIncAdnDiscardConfiguredCleared NOTIFICATION-TYPE
    OBJECTS         { ptTrapType, ptTrapSequenceNumber, ptTrapSeverity, 
                      ptTrapProbableCause, ptTrapClearType, 
                      ptTrapDateAndTime, ptTrapItemOID, 
                      ptDSCIncomingADNRoutingTableTableName }
    STATUS          current
    DESCRIPTION     
            "The DSC routing table is no longer configured to discard messages."
    ::= { ptiSegway 0 1836 }

ptCommandCodeRoutingTableDSCCmdCodeDiscardConfigured NOTIFICATION-TYPE
    OBJECTS         { ptTrapType, ptTrapSequenceNumber, ptTrapSeverity, 
                      ptTrapProbableCause, ptTrapClearType, 
                      ptTrapDateAndTime, ptTrapItemOID, 
                      ptDSCCommandCodeRoutingTableTableName }
    STATUS          current
    DESCRIPTION     
            "The DSC routing table contains at least one table entry that is configured
             to discard messages.  This is highly discouraged."
    ::= { ptiSegway 0 1837 }

ptCommandCodeRoutingTableDSCCmdCodeDiscardConfiguredCleared NOTIFICATION-TYPE
    OBJECTS         { ptTrapType, ptTrapSequenceNumber, ptTrapSeverity, 
                      ptTrapProbableCause, ptTrapClearType, 
                      ptTrapDateAndTime, ptTrapItemOID, 
                      ptDSCCommandCodeRoutingTableTableName }
    STATUS          current
    DESCRIPTION     
            "The DSC routing table is no longer configured to discard messages."
    ::= { ptiSegway 0 1838 }

ptApplicationIDRoutingTableDSCAppIdDiscardConfigured NOTIFICATION-TYPE
    OBJECTS         { ptTrapType, ptTrapSequenceNumber, ptTrapSeverity, 
                      ptTrapProbableCause, ptTrapClearType, 
                      ptTrapDateAndTime, ptTrapItemOID, 
                      ptDSCApplicationIDRoutingTableTableName }
    STATUS          current
    DESCRIPTION     
            "The DSC routing table contains at least one table entry that is configured
             to discard messages.  This is highly discouraged."
    ::= { ptiSegway 0 1839 }

ptApplicationIDRoutingTableDSCAppIdDiscardConfiguredCleared NOTIFICATION-TYPE
    OBJECTS         { ptTrapType, ptTrapSequenceNumber, ptTrapSeverity, 
                      ptTrapProbableCause, ptTrapClearType, 
                      ptTrapDateAndTime, ptTrapItemOID, 
                      ptDSCApplicationIDRoutingTableTableName }
    STATUS          current
    DESCRIPTION     
            "The DSC routing table is no longer configured to discard messages."
    ::= { ptiSegway 0 1840 }

ptAVPRoutingTableDSCAvpDiscardConfigured NOTIFICATION-TYPE
    OBJECTS         { ptTrapType, ptTrapSequenceNumber, ptTrapSeverity, 
                      ptTrapProbableCause, ptTrapClearType, 
                      ptTrapDateAndTime, ptTrapItemOID, 
                      ptDSCAVPRoutingTableTableName }
    STATUS          current
    DESCRIPTION     
            "The DSC routing table contains at least one table entry that is configured
             to discard messages.  This is highly discouraged."
    ::= { ptiSegway 0 1841 }

ptAVPRoutingTableDSCAvpDiscardConfiguredCleared NOTIFICATION-TYPE
    OBJECTS         { ptTrapType, ptTrapSequenceNumber, ptTrapSeverity, 
                      ptTrapProbableCause, ptTrapClearType, 
                      ptTrapDateAndTime, ptTrapItemOID, 
                      ptDSCAVPRoutingTableTableName }
    STATUS          current
    DESCRIPTION     
            "The DSC routing table is no longer configured to discard messages."
    ::= { ptiSegway 0 1842 }

ptCapacityParameterSetDSCCapDiscardConfigured NOTIFICATION-TYPE
    OBJECTS         { ptTrapType, ptTrapSequenceNumber, ptTrapSeverity, 
                      ptTrapProbableCause, ptTrapClearType, 
                      ptTrapDateAndTime, ptTrapItemOID, 
                      ptDSCCapacityParameterSetName }
    STATUS          current
    DESCRIPTION     
            "The DSC capacity parameter set is configured to discard messages when handling an overload.
             This is highly discouraged."
    ::= { ptiSegway 0 1843 }

ptCapacityParameterSetDSCCapDiscardConfiguredCleared NOTIFICATION-TYPE
    OBJECTS         { ptTrapType, ptTrapSequenceNumber, ptTrapSeverity, 
                      ptTrapProbableCause, ptTrapClearType, 
                      ptTrapDateAndTime, ptTrapItemOID, 
                      ptDSCCapacityParameterSetName }
    STATUS          current
    DESCRIPTION     
            "The DSC Capacity Parameter Set is no longer configured to discard messages."
    ::= { ptiSegway 0 1844 }

ptDSCNodesDSCNodeRoutingDiscard NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC discarded a message via routing table."
    ::= { ptiSegway 0 1845 }

ptDSCNodesDSCNodeRoutingDiscardCleared NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC has not discarded a message via routing table for 5 minutes."
    ::= { ptiSegway 0 1846 }

ptADNConnectionDSCAdncRoutingDiscard NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection discarded a message via routing table."
    ::= { ptiSegway 0 1847 }

ptADNConnectionDSCAdncRoutingDiscardCleared NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection has not discarded a message via routing table for 5 minutes."
    ::= { ptiSegway 0 1848 }

ptDSCNodesDSCCongestionDiscard NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC Node discarded a message due to configured congestion handling."
    ::= { ptiSegway 0 1849 }

ptDSCNodesDSCCongestionDiscardCleared NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC Node has not discarded messages due to configured congestion handling for 5 minutes"
    ::= { ptiSegway 0 1850 }

ptADNConnectionDSCAdncSevereCongestionDiscard NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection discarded an answer message due to severe congestion."
    ::= { ptiSegway 0 1851 }

ptADNConnectionDSCAdncSevereCongestionDiscardCleared NOTIFICATION-TYPE
    OBJECTS         { ptTrapType, ptTrapSequenceNumber, ptTrapSeverity, 
                      ptTrapProbableCause, ptTrapClearType, 
                      ptTrapDateAndTime, ptTrapItemOID, 
                      ptDSCADNConnectionSlot, 
                      ptDSCADNConnectionLocalHost, 
                      ptDSCADNConnectionLocalPort }
    STATUS          current
    DESCRIPTION     
            "The DSC ADN Connection has not discarded any answer message due to severe congestion for 5 minutes"
    ::= { ptiSegway 0 1852 }

ptDSCNodesMsgRetryExceeded NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A message has exceeded the maximum number of allowed
             retransmits allowd by the sending node"
    ::= { ptiSegway 0 1853 }

ptRateLimiterDSCRlCongestionDiscard NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter discarded a message due to configured congestion handling."
    ::= { ptiSegway 0 1854 }

ptRateLimiterDSCRlCongestionDiscardCleared NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter has not discarded messages due to configured congestion handling for 5 minutes"
    ::= { ptiSegway 0 1855 }

ptRateLimiterDSCRlSevereCongestionDiscard NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter discarded an answer message due to severe congestion."
    ::= { ptiSegway 0 1856 }

ptRateLimiterDSCRlSevereCongestionDiscardCleared NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter has not discarded any answer message due to severe congestion for 5 minutes"
    ::= { ptiSegway 0 1857 }

ptDSCNodesDSCLocalOverloadDiscard NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC Node discarded a message due to configured local overload handling."
    ::= { ptiSegway 0 1858 }

ptDSCNodesDSCLocalOverloadDiscardCleared NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The DSC Node has not discarded messages due to configured local overload handling for 5 minutes"
    ::= { ptiSegway 0 1859 }

ptDSCNodesTpsMissingUpdate NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The maximum number of missing TPS system update exceeds the threshold."
    ::= { ptiSegway 0 1860 }

ptDSCNodesTpsMissingUpdateClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The number of missing TPS update does not exceed the threshold."
    ::= { ptiSegway 0 1861 }

ptDSCNodesTpsServerSetupFailure NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "DSC TPS Update Server setup failed"
    ::= { ptiSegway 0 1862 }

ptDSCNodesTpsServerSetupSuccess NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "DSC TPS Server setup is successful"
    ::= { ptiSegway 0 1863 }

ptRateLimiterDSCRlLocalOverloadDiscard NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter discarded a message due to configured local overload handling."
    ::= { ptiSegway 0 1864 }

ptRateLimiterDSCRlLocalOverloadDiscardCleared NOTIFICATION-TYPE
    OBJECTS         { ptTrapType, ptTrapSequenceNumber, ptTrapSeverity, 
                      ptTrapProbableCause, ptTrapClearType, 
                      ptTrapDateAndTime, ptTrapItemOID, 
                      ptDSCRateLimiterName, 
                      ptDSCRateLimiterCapacityParameterSet }
    STATUS          current
    DESCRIPTION     
            "The DSC RateLimiter has not discarded messages due to configured local overload handling for 5 minutes"
    ::= { ptiSegway 0 1865 }

ptDSCPeerSyncTimeout NOTIFICATION-TYPE
    OBJECTS         { ptTrapType, ptTrapSequenceNumber, ptTrapSeverity, 
                      ptTrapProbableCause, ptTrapClearType, 
                      ptTrapDateAndTime, ptTrapItemOID, ptDSCDSCDSCName, 
                      ptDSCDSCDSCInstanceID }
    STATUS          current
    DESCRIPTION     
            "Peersync is taking longer than expected. Restart the peers having trouble syncing to rectify the situation."
    ::= { ptiSegway 0 1866 }

ptDSCPeerSyncTimeoutClear NOTIFICATION-TYPE
    OBJECTS         { ptTrapType, ptTrapSequenceNumber, ptTrapSeverity, 
                      ptTrapProbableCause, ptTrapClearType, 
                      ptTrapDateAndTime, ptTrapItemOID, ptDSCDSCDSCName, 
                      ptDSCDSCDSCInstanceID }
    STATUS          current
    DESCRIPTION     
            "Peersync is successful"
    ::= { ptiSegway 0 1867 }

ptDSCNodesDSCDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug setting is not set to the recommended value.
             
             Cause: A debug setting is not set to a recommended level.
             
             Possible Actions -
               The user should perform the 'Restore Debug Defaults' action to reset all
               debug attributes to their default values."
    ::= { ptiSegway 0 1868 }

ptDSCNodesDSCDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Debug levels are set to their recommended values."
    ::= { ptiSegway 0 1869 }

ptDSCNodeDSCNodeDebugLevelNotRecommended NOTIFICATION-TYPE
    OBJECTS         { ptTrapType, ptTrapSequenceNumber, ptTrapSeverity, 
                      ptTrapProbableCause, ptTrapClearType, 
                      ptTrapDateAndTime, ptTrapItemOID, 
                      ptDSCDSCNodeNodeDiameterID, ptDSCDSCNodeName }
    STATUS          current
    DESCRIPTION     
            "At least one node debug attribute is not set to the recommended value.
             
             Cause: A debug attribute is not set to a recommended level.
             
             Possible Actions -
                The user should perform the 'Restore Debug Defaults' action to reset all
                debug attributes to their default values."
    ::= { ptiSegway 0 1870 }

ptDSCNodeDSCNodeDebugLevelRecommended NOTIFICATION-TYPE
    OBJECTS         { ptTrapType, ptTrapSequenceNumber, ptTrapSeverity, 
                      ptTrapProbableCause, ptTrapClearType, 
                      ptTrapDateAndTime, ptTrapItemOID, 
                      ptDSCDSCNodeNodeDiameterID, ptDSCDSCNodeName }
    STATUS          current
    DESCRIPTION     
            "All node debug attributes are set to their recommended values."
    ::= { ptiSegway 0 1871 }

ptDSCAnswerMessageHitResultOrErrorTable NOTIFICATION-TYPE
    OBJECTS         { ptTrapType, ptTrapSequenceNumber, ptTrapSeverity, 
                      ptTrapProbableCause, ptTrapClearType, 
                      ptTrapDateAndTime, ptTrapItemOID, ptDSCDSCDSCName, 
                      ptDSCDSCDSCInstanceID }
    STATUS          current
    DESCRIPTION     
            "An answer message hit a result or dsc_error table.
             
             Cause - The DSC explicit routing is possibly misconfigured and an answer
                      message hits a result or dsc_error table. 
             
             Possible Actions - 
                Search the debug log for a warning entry indicating that an answer message hit a result or 
                dsc_error table. Note down the following information after the warning log entry:
                DSC instance, DSC Node name, Request Incoming ADN Name, Answer Incoming ADN Name, 
                Initial Routing Table Name, and Outgoing Answer Routing Table, and the message content
                in HEX. Note that the message content must be cleaned up as copied from the debug log. 
                Using the DSC Search Utility of the DSC instance reporting the alarm and log, upload
                the message and fill in the required information based on the information collected
                from the debug log. Perform a search and inspect the DSC Table Records the message
                goes through before hitting the result or error table. Change the configuration so
                that the answer message is properly routed and does not hit a result or error table.
                If the results of the Search do not output any DSC Table Records, use the Outgoing Answer
                Routing Table as the Initial Routing Table Name of the DSC Search Utility and perform a
                search again.
                If you still do not get any DSC Table Records, use the Outgoing Answer Routing Table as
                your starting point and trace the message flow through the routing tables until you find
                a record that puts the answer message through a result or dsc_error table.
                Note that some answer messages may be generated by the DSC ( errors for example ) and might
                not have an Answer Incoming ADN Name value. For this particular case, the Outgoing Answer 
                Routing Table of the Request Incoming ADN Name is routing the answer message through a 
                result or error routing table.
             "
    ::= { ptiSegway 0 1872 }

ptDSCAnswerMessageHitResultOrErrorTableClear NOTIFICATION-TYPE
    OBJECTS         { ptTrapType, ptTrapSequenceNumber, ptTrapSeverity, 
                      ptTrapProbableCause, ptTrapClearType, 
                      ptTrapDateAndTime, ptTrapItemOID, ptDSCDSCDSCName, 
                      ptDSCDSCDSCInstanceID }
    STATUS          current
    DESCRIPTION     
            "An answer message did not hit a result or dsc_error table in the last 5 minutes."
    ::= { ptiSegway 0 1873 }

ptDSCNodesDSCNodesRequestRejectedQueueFull NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This alarm indicates that at least one Diameter Request
             message has been recently rejected because of excessive
             memory used by queued Diameter Request messages. In this
             context, 'recently' means in the last 5 minutes and
             'rejected' means that an error is returned with
             Result-Code DIAMETER_UNABLE_TO_DELIVER.
             
             Cause: At least one Diameter Request message has been
             recently rejected because of excessive memory used by
             queued Diameter Request messages.
             
             Possible Actions -
             Excessive memory use for queued requests usually happens
             because a large number of requests are not answered.
             This is an unusual situation.
             
             First, check that the DSC MSA objects with Name QUEUE
             USAGE <slot> have reasonable Max Size attributes.
             The Maximum Size attribute represents the number of
             megabytes that may be queued. If this queue size is too
             low it could lead to unnecessary request rejection.
             
             Next, large amounts of queued requests usually mean that
             requests are timing out. These request timeouts should
             be generating paced logs in ptidbglog that gives some
             characteristics of the discarded messages. Investigate
             the timeouts and see if the root cause can be determined
             (are all the timeouts relating to the same
              Destination-Realm and Application-Id, for example)."
    ::= { ptiSegway 0 1874 }

ptDSCNodesDSCNodesRequestRejectedQueueFullClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This alarm clears ptDSCNodesRequestRejectedQueueFull.
             There have been no discards due to excessive memory
             usage for 5 minutes."
    ::= { ptiSegway 0 1875 }

ptIWFDiameterIWFDiameterDown NOTIFICATION-TYPE
    OBJECTS         { ptTrapType, ptTrapSequenceNumber, ptTrapSeverity, 
                      ptTrapProbableCause, ptTrapClearType, 
                      ptTrapDateAndTime, ptTrapItemOID, 
                      ptiwfIWFDiameterIWFDiameterID, 
                      ptiwfIWFDiameterDSCIWFUAPort, 
                      ptiwfIWFDiameterConnectivityStatus }
    STATUS          current
    DESCRIPTION     
            "The IWF traffic is deactivated or all Diameter Connections are not connected.
             The DSC associated Transport Server for the IWF port must be active and UP."
    ::= { ptiSegway 0 1901 }

ptIWFDiameterIWFDiameterUp NOTIFICATION-TYPE
    OBJECTS         { ptTrapType, ptTrapSequenceNumber, ptTrapSeverity, 
                      ptTrapProbableCause, ptTrapClearType, 
                      ptTrapDateAndTime, ptTrapItemOID, 
                      ptiwfIWFDiameterIWFDiameterID, 
                      ptiwfIWFDiameterDSCIWFUAPort, 
                      ptiwfIWFDiameterConnectivityStatus }
    STATUS          current
    DESCRIPTION     
            "At least one Diameter Connection is connected."
    ::= { ptiSegway 0 1902 }

ptDiameterConnectionIWFDiameterConnectionDown NOTIFICATION-TYPE
    OBJECTS         { ptTrapType, ptTrapSequenceNumber, ptTrapSeverity, 
                      ptTrapProbableCause, ptTrapClearType, 
                      ptTrapDateAndTime, ptTrapItemOID, 
                      ptiwfDiameterConnectionSlot, 
                      ptiwfDiameterConnectionConnectivityStatus }
    STATUS          current
    DESCRIPTION     
            "The IWF traffic is deactivated or the Diameter Connection is not connected.
             The DSC associated Transport Server for the IWF port must be active and UP on this slot."
    ::= { ptiSegway 0 1903 }

ptDiameterConnectionIWFDiameterConnectionUp NOTIFICATION-TYPE
    OBJECTS         { ptTrapType, ptTrapSequenceNumber, ptTrapSeverity, 
                      ptTrapProbableCause, ptTrapClearType, 
                      ptTrapDateAndTime, ptTrapItemOID, 
                      ptiwfDiameterConnectionSlot, 
                      ptiwfDiameterConnectionConnectivityStatus }
    STATUS          current
    DESCRIPTION     
            "The Diameter Connection is connected."
    ::= { ptiSegway 0 1904 }

ptIWFSS7IWFSS7ConfigurationMismatch NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7SCCPPAEncoding, 
                      ptiwfIWFSS7PCDisplayFormat, 
                      ptiwfIWFSS7PCRoutingFormat }
    STATUS          current
    DESCRIPTION     
            "The MTP3 configuration information provided by the SCCP to the IWF does not match with 
             the IWF SS7 configuration.  The associated MTP3 NA necessary configuration must match."
    ::= { ptiSegway 0 1905 }

ptIWFSS7IWFSS7ConfigurationValid NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7SCCPPAEncoding, 
                      ptiwfIWFSS7PCDisplayFormat, 
                      ptiwfIWFSS7PCRoutingFormat }
    STATUS          current
    DESCRIPTION     
            "The MTP3 configuration information provided by the SCCP to the IWF matches with the
             IWF SS7 configuration."
    ::= { ptiSegway 0 1906 }

ptIWFSS7IWFSS7Down NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7ConnectivityStatus }
    STATUS          current
    DESCRIPTION     
            "The IWF traffic is deactivated or all SCCP Connections are not connected.
             The SCCP associated NA must be active and available."
    ::= { ptiSegway 0 1907 }

ptIWFSS7IWFSS7Up NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7ConnectivityStatus }
    STATUS          current
    DESCRIPTION     
            "At least one SCCP Connection is connected."
    ::= { ptiSegway 0 1908 }

ptSCCPConnectionIWFSCCPConnectionDown NOTIFICATION-TYPE
    OBJECTS         { ptTrapType, ptTrapSequenceNumber, ptTrapSeverity, 
                      ptTrapProbableCause, ptTrapClearType, 
                      ptTrapDateAndTime, ptTrapItemOID, 
                      ptiwfSCCPConnectionSlot, 
                      ptiwfSCCPConnectionConnectivityStatus }
    STATUS          current
    DESCRIPTION     
            "The IWF traffic is deactivated or the SCCP Connection is not connected.
             The SCCP associated NA must be active and available on the given slot."
    ::= { ptiSegway 0 1909 }

ptSCCPConnectionIWFSCCPConnectionUp NOTIFICATION-TYPE
    OBJECTS         { ptTrapType, ptTrapSequenceNumber, ptTrapSeverity, 
                      ptTrapProbableCause, ptTrapClearType, 
                      ptTrapDateAndTime, ptTrapItemOID, 
                      ptiwfSCCPConnectionSlot, 
                      ptiwfSCCPConnectionConnectivityStatus }
    STATUS          current
    DESCRIPTION     
            "The SCCP Connection is connected."
    ::= { ptiSegway 0 1910 }

ptSCCPPCSSNRegistrationIWFSCCPPCSSNFailure NOTIFICATION-TYPE
    OBJECTS         { ptTrapType, ptTrapSequenceNumber, ptTrapSeverity, 
                      ptTrapProbableCause, ptTrapClearType, 
                      ptTrapDateAndTime, ptTrapItemOID, 
                      ptiwfSCCPPCSSNRegistrationPC, 
                      ptiwfSCCPPCSSNRegistrationSSN, 
                      ptiwfSCCPPCSSNRegistrationStatus }
    STATUS          current
    DESCRIPTION     
            "The SCCP PC-SSN Registration was unsuccessful on all the defined SCCP Connections."
    ::= { ptiSegway 0 1911 }

ptSCCPPCSSNRegistrationIWFSCCPPCSSNSuccess NOTIFICATION-TYPE
    OBJECTS         { ptTrapType, ptTrapSequenceNumber, ptTrapSeverity, 
                      ptTrapProbableCause, ptTrapClearType, 
                      ptTrapDateAndTime, ptTrapItemOID, 
                      ptiwfSCCPPCSSNRegistrationPC, 
                      ptiwfSCCPPCSSNRegistrationSSN, 
                      ptiwfSCCPPCSSNRegistrationStatus }
    STATUS          current
    DESCRIPTION     
            "The SCCP PC-SSN Registration was successful on all the defined SCCP Connections."
    ::= { ptiSegway 0 1912 }

ptSCCPAppIDRegistrationIWFSCCPAppIDFailure NOTIFICATION-TYPE
    OBJECTS         { ptTrapType, ptTrapSequenceNumber, ptTrapSeverity, 
                      ptTrapProbableCause, ptTrapClearType, 
                      ptTrapDateAndTime, ptTrapItemOID, 
                      ptiwfSCCPAppIDRegistrationApplicationID, 
                      ptiwfSCCPAppIDRegistrationStatus }
    STATUS          current
    DESCRIPTION     
            "The SCCP AppID Registration was unsuccessful on all the defined SCCP Connections."
    ::= { ptiSegway 0 1913 }

ptSCCPAppIDRegistrationIWFSCCPAppIDSuccess NOTIFICATION-TYPE
    OBJECTS         { ptTrapType, ptTrapSequenceNumber, ptTrapSeverity, 
                      ptTrapProbableCause, ptTrapClearType, 
                      ptTrapDateAndTime, ptTrapItemOID, 
                      ptiwfSCCPAppIDRegistrationApplicationID, 
                      ptiwfSCCPAppIDRegistrationStatus }
    STATUS          current
    DESCRIPTION     
            "The SCCP AppID Registration was successful on all the defined SCCP Connections."
    ::= { ptiSegway 0 1914 }

ptIWFDiameterIWFDiameterAnswerNoMatch NOTIFICATION-TYPE
    OBJECTS         { ptTrapType, ptTrapSequenceNumber, ptTrapSeverity, 
                      ptTrapProbableCause, ptTrapClearType, 
                      ptTrapDateAndTime, ptTrapItemOID, 
                      ptiwfIWFDiameterIWFDiameterID, 
                      ptiwfIWFDiameterDSCIWFUAPort, 
                      ptiwfIWFDiameterConnectivityStatus }
    STATUS          current
    DESCRIPTION     
            "The IWF received a Diameter answer with no match in the last 5 minutes."
    ::= { ptiSegway 0 1915 }

ptIWFDiameterIWFDiameterAnswerMatchClear NOTIFICATION-TYPE
    OBJECTS         { ptTrapType, ptTrapSequenceNumber, ptTrapSeverity, 
                      ptTrapProbableCause, ptTrapClearType, 
                      ptTrapDateAndTime, ptTrapItemOID, 
                      ptiwfIWFDiameterIWFDiameterID, 
                      ptiwfIWFDiameterDSCIWFUAPort, 
                      ptiwfIWFDiameterConnectivityStatus }
    STATUS          current
    DESCRIPTION     
            "The IWF did not received a Diameter answer without a match in the last 5 minutes."
    ::= { ptiSegway 0 1916 }

ptIWFSS7IWFSCCPResponseNoMatch NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7ConnectivityStatus }
    STATUS          current
    DESCRIPTION     
            "The IWF received an SCCP response with no match in the last 5 minutes."
    ::= { ptiSegway 0 1917 }

ptIWFSS7IWFSCCPResponseMatchClear NOTIFICATION-TYPE
    OBJECTS         { ptTrapType, ptTrapSequenceNumber, ptTrapSeverity, 
                      ptTrapProbableCause, ptTrapClearType, 
                      ptTrapDateAndTime, ptTrapItemOID, 
                      ptiwfIWFSS7SCCPNA, ptiwfIWFSS7ConnectivityStatus }
    STATUS          current
    DESCRIPTION     
            "The IWF did not received a SCCP response without a match in the last 5 minutes."
    ::= { ptiSegway 0 1918 }

ptIWFConfigurationIWFDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 1919 }

ptIWFConfigurationIWFDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 1920 }

ptSS7DBAppsConfigurationLsmsConnDown NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "Connectivity to the LSMS has been lost."
    ::= { ptiSegway 0 2001 }

ptSS7DBAppsConfigurationLsmsConnUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Connectivy to the LSMS has been restored"
    ::= { ptiSegway 0 2002 }

ptSS7DBAppsConfigurationLicenseError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "A critical SS7 DB Applications license error has occurred"
    ::= { ptiSegway 0 2003 }

ptSS7DBAppsConfigurationLicenseClrError NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A critical SS7 DB Applications license error has been cleared"
    ::= { ptiSegway 0 2004 }

ptSS7DBAppsConfigurationSysMgrDiskFull NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "Disk is full on SS7 DB Applications CPU"
    ::= { ptiSegway 0 2005 }

ptSS7DBAppsConfigurationSysMgrDiskFullClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Disk is no longer full on SS7 DB Applications CPU"
    ::= { ptiSegway 0 2006 }

ptSS7DBAppsConfigurationSysMgrDiskUsageOver90Percent NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "Disk usage is over 90% full on SS7 DB Applications CPU"
    ::= { ptiSegway 0 2007 }

ptSS7DBAppsConfigurationSysMgrDiskUsageUnder90Percent NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Disk usage is no longer over 90% full on SS7 DB Applications CPU"
    ::= { ptiSegway 0 2008 }

ptSS7DBAppsConfigurationSysMgr5129ThrottlingOn NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "Throttling has started for 5129 msgs."
    ::= { ptiSegway 0 2009 }

ptSS7DBAppsConfigurationSysMgr5129ThrottlingOff NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Throttling has abated for 5129 messages."
    ::= { ptiSegway 0 2010 }

ptSS7DBAppsConfigurationNsmConnDown NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "Connectivity to the NSM has been lost."
    ::= { ptiSegway 0 2011 }

ptSS7DBAppsConfigurationNsmConnUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Connectivy to the NSM has been restored"
    ::= { ptiSegway 0 2012 }

ptSS7DBAppsConfigurationBulkInputFailError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "NP Database Bulk Input completed with some failed entry."
    ::= { ptiSegway 0 2013 }

ptSS7DBAppsConfigurationBulkInputFailErrorClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "NP Database Bulk Input failed entry alarm cleared."
    ::= { ptiSegway 0 2014 }

ptSS7DBAppsConfigurationBulkInputCongRaised NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "NP Database Bulk Input congestion detected on FLXMGR to DSS path"
    ::= { ptiSegway 0 2015 }

ptSS7DBAppsConfigurationBulkInputCongClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "NP Database Bulk Input congestion alarm cleared."
    ::= { ptiSegway 0 2016 }

ptSS7DBAppsConfigurationDuplicateDbRecordsFound NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SDA DB Audit detected duplicate records."
    ::= { ptiSegway 0 2017 }

ptSS7DBAppsConfigurationDuplicateDbRecordsCleared NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "SDA DB duplicate records alarm cleared."
    ::= { ptiSegway 0 2018 }

ptSS7DBAppsConfigurationLsmsPingSuccess NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "LSMS ping test passed."
    ::= { ptiSegway 0 2020 }

ptSS7DBAppsConfigurationLsmsPingFailure NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "LSMS ping test failed."
    ::= { ptiSegway 0 2021 }

ptSS7DBAppsConfigurationSigFlexScrServerStart NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications Scripting Server has started."
    ::= { ptiSegway 0 2022 }

ptSS7DBAppsConfigurationSigFlexScrServerExit NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications Scripting Server is shutting down."
    ::= { ptiSegway 0 2023 }

ptSS7DBAppsConfigurationSigFlexScrServerAbort NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications Scripting Server has aborted."
    ::= { ptiSegway 0 2024 }

ptSS7DBAppsConfigurationSigFlexFlxRtgReady NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications Routing Server now ready."
    ::= { ptiSegway 0 2025 }

ptSS7DBAppsConfigurationSigFlexFileSystemError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications file system sync error."
    ::= { ptiSegway 0 2026 }

ptSS7DBAppsConfigurationSigFlexMemoryError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications memory error."
    ::= { ptiSegway 0 2027 }

ptSS7DBAppsConfigurationSigFlexThreadSyncError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications thread synchronization error."
    ::= { ptiSegway 0 2028 }

ptSS7DBAppsConfigurationSigFlexThreadMgmtError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications thread management error."
    ::= { ptiSegway 0 2029 }

ptSS7DBAppsConfigurationSigFlexDBAuditChecksumError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications database audit checksum error."
    ::= { ptiSegway 0 2030 }

ptSS7DBAppsConfigurationSigFlexTCAPAutoLoadMonitor NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications TCAP automatic load monitoring failed."
    ::= { ptiSegway 0 2031 }

ptSS7DBAppsConfigurationSigFlexDBAuditFailure NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications database audit failed."
    ::= { ptiSegway 0 2032 }

ptSS7DBAppsConfigurationSigFlexDBTableResizeFailure NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications database table resize failed."
    ::= { ptiSegway 0 2033 }

ptSS7DBAppsConfigurationSigFlex5129CommandTimeout NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications 5129 command timeout failure."
    ::= { ptiSegway 0 2034 }

ptSS7DBAppsConfigurationSigFlexProcessExit NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications process exit."
    ::= { ptiSegway 0 2035 }

ptSS7DBAppsConfigurationSigFlexManualNetworkElementStarted NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications manual network element monitoring started."
    ::= { ptiSegway 0 2037 }

ptSS7DBAppsConfigurationSigFlexManualLoadMonitoringStarted NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications manual load monitoring started."
    ::= { ptiSegway 0 2038 }

ptSS7DBAppsConfigurationSigFlexClxPartyLoadMonitoringStarted NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications manual called/calling party load monitoring started."
    ::= { ptiSegway 0 2039 }

ptSS7DBAppsConfigurationSigFlexInvalidMsg NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications invalid message."
    ::= { ptiSegway 0 2040 }

ptSS7DBAppsConfigurationSigFlexMsgError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications message error."
    ::= { ptiSegway 0 2041 }

ptSS7DBAppsConfigurationSigFlexAppProcessingError NOTIFICATION-TYPE
    OBJECTS         { ptTrapType, ptTrapSequenceNumber, ptTrapSeverity, 
                      ptTrapProbableCause, ptTrapClearType, 
                      ptTrapDateAndTime, ptTrapItemOID, 
                      ptFLXSS7DBAppsConfigurationTrapInfo }
    STATUS          current
    DESCRIPTION     
            "SS7 DB Applications application processing error."
    ::= { ptiSegway 0 2042 }

ptSlotSlotDSCDBPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "DSC DB partition usage is above the alarm threshold defined in 
             disk_space_quota.  The slot number indicated in this
             trap indicates the origin of the alarm.
             
             Cause  - DSC DB partition usage above threshold
             Action - Identify applications running high on disk space
             Freq   - Irregular
             "
    ::= { ptiSegway 0 3150 }

ptSlotSlotDSCDBPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "DSC DB partition usage has returned to acceptable levels.
             
             Cause  - DSC DB partition usage below threshold.
             Action - None.
             Freq   - Irregular.
             "
    ::= { ptiSegway 0 3151 }

ptSlotMonitorSlotNTPServerDown NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "Some of NTP servers configured are invalid or are down.
             
             Cause  - Some NTP servers are not working properly
             Action - Identify Some NTP servers are not working properly
             Freq   - Irregular
             "
    ::= { ptiSegway 0 3152 }

ptSlotMonitorSlotNTPServerDownCleared NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "The invalid NTP servers are removed from configuration or the down NTP servers are back to work.
             
             Cause  - The invalid NTP servers are removed from configuration or the down NTP servers are back to work.
             Action - None.
             Freq   - Irregular.
             "
    ::= { ptiSegway 0 3153 }

ptSlotSlotUSBDeviceInserted NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "A USB device has been connected to the card in the specified
             slot.  Ensure that all devices are removed unless needed.
             
             Cause  - USB device attached to faceplate connector.
             Action - Ensure that all devices are removed unless needed.
             Freq   - Irregular.
             "
    ::= { ptiSegway 0 3154 }

ptSlotSlotUSBDeviceExtracted NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "All USB devices have been disconnected.
             
             Cause  - All USB devices removed from faceplate connector.
             Action - None.
             Freq   - Irregular.
             "
    ::= { ptiSegway 0 3155 }

ptSlotDatabaseClusterMalfunction NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "The database cluster is NOT functioning as expected.
             
             Cause - 1. At least two cluster nodes are 'unreachable' to each other (Incorrect
                        network configuration, Port 7000 closed, VM down or Cassandra stopped).
                     2. The running cluster status does NOT match the configuration information
                        provided by the user during cluster setup, i.e., different tokens/racks/IP addresses, 
                        different cluster sizes or different topologies (more or less than two data
                        centers, more or less than two nodes per data center).
             
             Action - If a cluster node is 'unreachable' to the other nodes:
                       - Make sure the corresponding VM is up and Cassandra is running
                       - Make sure the network is properly configured and port 7000 is open. All nodes must successfully telnet 
                         the other nodes on port 7000. If this is not the case, reconfigure the cluster with IPv4/IPv6 addresses belonging 
                         to network interface pkt0 (or matching hostnames). Use WebUI/IP Networking/Routing IP Network to add an 
                         IPv4/IPv6 address belonging to network interface pkt0
                       - Restart Cassandra
             
                      If a mismatch between the cluster status and the configuration information provided by the user is observed:
                       - Reconfigure the cluster using startmenu -> 1 - System -> 2 - Software Revisions -> 2 - DSC DB -> DSC DB Configuration.
                         This will restart Cassandra once the configuration is completed
             Freq   - Irregular.
             "
    ::= { ptiSegway 0 3156 }

ptSlotDatabaseClusterFunction NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "The database cluster is functioning as expected.
             
             Cause  - None.
             Action - None.
             Freq   - Irregular.
             "
    ::= { ptiSegway 0 3157 }

ptSlotMonitorSlotLicenseServerConnectivityLoss NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "System lost connection to the license server."
    ::= { ptiSegway 0 3160 }

ptSlotMonitorSlotLicenseServerConnectivityEstablished NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "System re-established connection to the license server."
    ::= { ptiSegway 0 3161 }

ptSlotSlotCpuCertificateAboutToExpire NOTIFICATION-TYPE
    OBJECTS         { ptTrapType, ptTrapSequenceNumber, ptTrapSeverity, 
                      ptTrapProbableCause, ptTrapClearType, 
                      ptTrapDateAndTime, ptTrapItemOID, ptSlotSlotNumber, 
                      ptSlotPrimaryIP, ptSlotSecondaryIP }
    STATUS          current
    DESCRIPTION     
            "Certificate in this slot is within one month from expiry date."
    ::= { ptiSegway 0 3162 }

ptSlotSlotCpuCertificateExpiryDateExtended NOTIFICATION-TYPE
    OBJECTS         { ptTrapType, ptTrapSequenceNumber, ptTrapSeverity, 
                      ptTrapProbableCause, ptTrapClearType, 
                      ptTrapDateAndTime, ptTrapItemOID, ptSlotSlotNumber, 
                      ptSlotPrimaryIP, ptSlotSecondaryIP }
    STATUS          current
    DESCRIPTION     
            "Expiry date of the certificate in this slot is now extended."
    ::= { ptiSegway 0 3163 }

ptSlotSlotCpuCertificateExpired NOTIFICATION-TYPE
    OBJECTS         { ptTrapType, ptTrapSequenceNumber, ptTrapSeverity, 
                      ptTrapProbableCause, ptTrapClearType, 
                      ptTrapDateAndTime, ptTrapItemOID, ptSlotSlotNumber, 
                      ptSlotPrimaryIP, ptSlotSecondaryIP }
    STATUS          current
    DESCRIPTION     
            "Certificate in this slot has expired."
    ::= { ptiSegway 0 3164 }

ptSlotSlotCpuCertificateRenewed NOTIFICATION-TYPE
    OBJECTS         { ptTrapType, ptTrapSequenceNumber, ptTrapSeverity, 
                      ptTrapProbableCause, ptTrapClearType, 
                      ptTrapDateAndTime, ptTrapItemOID, ptSlotSlotNumber, 
                      ptSlotPrimaryIP, ptSlotSecondaryIP }
    STATUS          current
    DESCRIPTION     
            "Expired certificate in this slot is now renewed."
    ::= { ptiSegway 0 3165 }

ptSlotMonitorSlotDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
                The user should perform the 'Restore Debug Defaults' action to reset all
                debug attributes to their default values."
    ::= { ptiSegway 0 3168 }

ptSlotMonitorSlotDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 3169 }

ptSlotSlotMTUSizeNotAsConfigured NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "MTU Size for one (or more) interfaces is currently not as configured.
             
             Cause: MTU size of interface does not match the configured value.
             
             Possible Actions -
                Ensure MTU size for the physical interface is greater than or equal to all
                associated VLAN interfaces. VLAN interfaces may not have an MTU size 
                larger than the physical interface to which it is tied.  Care should be taken 
                when adjusting MTU size, as raising the MTU size could cause packets to be 
                discarded in the network."
    ::= { ptiSegway 0 3170 }

ptSlotSlotMTUSizeAsConfigured NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Current MTU sizes match configuration."
    ::= { ptiSegway 0 3171 }

ptSlotSlotAIDEErrorDetected NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "AIDE has detected file modification on one or more files.
             
             Cause: A file has been modified since the last AIDE database initialization.
             
             Possible Actions -
                Investigate the audittrail log to determine which files have been modified and which 
                action(s) may have caused them to be modified.   
             
                Reinitilazing the AIDE database via the System Manager will clear the alarm."
    ::= { ptiSegway 0 3172 }

ptSlotSlotAIDEErrorNotDetected NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "No AIDE errors detected."
    ::= { ptiSegway 0 3173 }

ptSlotAvailableMemThresh50Exceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below 50% of total memory. 
             The slot number shown in this trap indicates the origin of the alarm.  
             
             Cause  - Memory usage reached a certain threshold
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 3174 }

ptSlotAvailableMemThresh50Cleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability is restored to more than 50% of total memory.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 3175 }

ptSlotAvailableMemThresh40Exceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below 40% of total memory. 
             The slot number shown in this trap indicates the origin of the alarm.  
             
             Cause  - Memory usage reached a certain threshold
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 3176 }

ptSlotAvailableMemThresh40Cleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability is restored to more than 40% of total memory.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 3177 }

ptSlotAvailableMemThresh30Exceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below 30% of total memory. 
             The slot number shown in this trap indicates the origin of the alarm.  
             
             Cause  - Memory usage reached a certain threshold
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 3178 }

ptSlotAvailableMemThresh30Cleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability is restored to more than 30% of total memory.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 3179 }

ptSlotAvailableMemThresh20Exceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below 20% of total memory. 
             The slot number shown in this trap indicates the origin of the alarm.  
             
             Cause  - Memory usage reached a certain threshold
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 3180 }

ptSlotAvailableMemThresh20Cleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability is restored to more than 20% of total memory.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 3181 }

ptSlotAvailableMemThresh10Exceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below 10% of total memory. 
             The slot number shown in this trap indicates the origin of the alarm.  
             
             Cause  - Memory usage reached a certain threshold
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 3182 }

ptSlotAvailableMemThresh10Cleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability is restored to more than 10% of total memory.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 3183 }

ptSlotMonitorMissingIOcfgFile NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "
             The system use this alarm to warn user that there is a missing IO configuration file.
             Cause  - There is a missing IO configuration file on the management CPU.
             Action - Try to get the missing file back to management CPU, maybe need a help from system administrator.
             Freq:  - Irregular.  
             "
    ::= { ptiSegway 0 3184 }

ptSlotMonitorMissingIOcfgFileClear NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "
             All the missing IO configuration files have been restored.
             Cause  - Not detected any missing IO configuration file on the management CPU.
             Action - None.
             Freq   - Irregular.
             "
    ::= { ptiSegway 0 3185 }

ptGWSTGwstProcessStartup NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             This trap indicates the GWST process is starting up.
             Sent every time GWST starts up via a manual intervention or typically
             via the watchdog."
    ::= { ptiSegway 0 4001 }

ptGWSTGwstProcessShutdown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             This trap indicates the GWST process is shutting down.
             Sent every time GWST is terminated (intentionally or not).
             System based termination include:
               - LDL Configuration error
               - Process received a terminating signal (SIGINT, SIGTERM)."
    ::= { ptiSegway 0 4002 }

ptGWSTGwstPeerUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             This trap indicates a GWST peer is reachable.
             Sent when a GWST peer communication is established via LDL."
    ::= { ptiSegway 0 4003 }

ptGWSTGwstPeerDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             This trap indicates a GWST peer is no longer reachable.
             Sent when a GWST peer communication is lost via LDL.
             Peer connectivity interruptions include:
               - GWST peer is terminated
               - IP connectivity heartbeat/keep alive fails
               - IP connectivity is lost between GWST processes."
    ::= { ptiSegway 0 4004 }

ptGWSTConfigurationGwstDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that at least one GWST debug flag has been changed to a non recommended value.
             Cause: A user has altered at least one debugging flag to a non recommended level.
             Possible Actions -
               The user should perform the 'Restore Debug Defaults' action.
               This action is displayed in the GWST Debug Configuration screen. It restores
               all log flags to the default values which in turn clears the alarm."
    ::= { ptiSegway 0 4006 }

ptGWSTConfigurationGwstDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The GWST debugging levels are set to their recommended values."
    ::= { ptiSegway 0 4007 }

ptL4ConverterL4cvtrProcessStartup NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the L4Cvtr process is starting up.  
             
             Sent every time L4Cvtr starts up via a manual intervention or typically 
             via the watchdog."
    ::= { ptiSegway 0 4101 }

ptL4ConverterL4cvtrProcessShutdown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the L4Cvtr process is shutting down.  
             
             Sent every time L4Cvtr is terminated (intentionally or not).
             System based termination include:
               - LDL Configuration error
               - Process received a terminating signal (SIGINT, SIGTERM)."
    ::= { ptiSegway 0 4102 }

ptL4ConverterL4cvtrPeerUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a L4Cvtr peer is reachable.  
             
             Sent when a L4Cvtr peer communication is established via LDL."
    ::= { ptiSegway 0 4103 }

ptL4ConverterL4cvtrPeerDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a L4Cvtr peer is no longer reachable.  
             
             Sent when a L4Cvtr peer communication is lost via LDL.
             Peer connectivity interruptions include:
               - L4Cvtr peer is terminated
               - IP connectivity heartbeat/keep alive fails
               - IP connectivity is lost between L4Cvtr processes."
    ::= { ptiSegway 0 4104 }

ptL4ConverterL4cvtrWriteFailure NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a L4Cvtr write to file failed.  
             
             Sent when a L4Cvtr configuration or database write fails.
             Write failures include:
               - Invalid file permissions
               - Out of memory in file system"
    ::= { ptiSegway 0 4105 }

ptL4ConverterL4cvtrDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 4106 }

ptL4ConverterL4cvtrDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 4107 }

ptSCCPNAManagerSccpProcessStartup NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the SCCP process is starting up.  
             Sent every time SCCP starts up via a manual intervention or typically 
             via the watchdog."
    ::= { ptiSegway 0 4201 }

ptSCCPNAManagerSccpProcessShutdown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the SCCP process is shutting down.  
             Sent every time SCCP is terminated (intentionally or not).
             System based termination include:
               - LDL Configuration error
               - Process received a terminating signal (SIGINT, SIGTERM)."
    ::= { ptiSegway 0 4202 }

ptSCCPNAManagerSccpPeerUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a SCCP peer is reachable.  
             Sent when a SCCP peer communication is established via LDL."
    ::= { ptiSegway 0 4203 }

ptSCCPNAManagerSccpPeerDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a SCCP peer is no longer reachable.  
             Sent when a SCCP peer communication is lost via LDL.
             Peer connectivity interruptions include:
               - SCCP peer is terminated
               - IP connectivity heartbeat/keep alive fails
               - IP connectivity is lost between SCCP processes."
    ::= { ptiSegway 0 4204 }

ptSCCPNAManagerSccpWriteFailure NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a SCCP write to file failed.  
             Sent when a SCCP configuration or database write fails.
             Write failures include:
               - Invalid file permissions
               - Out of memory in file system"
    ::= { ptiSegway 0 4205 }

ptSCCPNAManagerSccpResMgrUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates SCCP is connected to the resource manager."
    ::= { ptiSegway 0 4206 }

ptSCCPNAManagerSccpResMgrDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates SCCP is no longer connected to the resource manager."
    ::= { ptiSegway 0 4207 }

ptSCCPNAManagerSccpDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
                The user should perform the 'Restore Debug Defaults' action to reset all
                debug attributes to their default values."
    ::= { ptiSegway 0 4208 }

ptSCCPNAManagerSccpDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 4209 }

ptSCCPNASccpNADebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
                 The user should perform the 'Restore Debug Defaults' action to reset all
                 debug attributes to their default values."
    ::= { ptiSegway 0 4210 }

ptSCCPNASccpNADebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 4211 }

ptSCCPNASccpNADiscardMSUUnexpectedSI NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "SCCP received an MSU from MTP3 with an SI not equal to 3 (unexpected)
             in the past 5 minutes.
             
             Possible Actions - 
               The user should check the MTP3 VNode and Routeset configuration or Gateway Redirection
               where applicable.  The Destination Point Code (DPC) of such MSUs can be found in the
               debuglog"
    ::= { ptiSegway 0 4212 }

ptSCCPNASccpNADiscardMSUUnexpectedSIClear NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "SCCP has not received an MSU from MTP3 with an SI not equal to 3 which is unexpected
             in the past 5 minutes."
    ::= { ptiSegway 0 4213 }

ptSCCPNASccpNADiscardMSUMTP3 NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "An unexpected MSU was discarded by a SCCP MTP3 NA 
             in the past 5 minutes."
    ::= { ptiSegway 0 4214 }

ptSCCPNASccpNADiscardMSUMTP3Clear NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "Clear event for MSU has been discarded by a SCCP MTP3 NA."
    ::= { ptiSegway 0 4215 }

ptSCCPNASccpNADiscardMSUUser NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "An unexpected MSU has been discarded by a SCCP User Connection 
             in the past 5 minutes."
    ::= { ptiSegway 0 4216 }

ptSCCPNASccpNADiscardMSUUserClear NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "Clear event for MSU has been discarded by a SCCP User Connection."
    ::= { ptiSegway 0 4217 }

ptSCCPNASccpNADiscardMSUGTT NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "An unexpected MSU has been discarded by a SCCP GTT Connection 
             in the past 5 minutes."
    ::= { ptiSegway 0 4218 }

ptSCCPNASccpNADiscardMSUGTTClear NOTIFICATION-TYPE
    OBJECTS         { ptTrapType, ptTrapSequenceNumber, ptTrapSeverity, 
                      ptTrapProbableCause, ptTrapClearType, 
                      ptTrapDateAndTime, ptTrapItemOID, 
                      ptSCCPSCCPNAContext }
    STATUS          current
    DESCRIPTION     
            "Clear event for MSU has been discarded by a SCCP GTT Connection."
    ::= { ptiSegway 0 4219 }

ptPCEPceProcessStartup NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the PCE process is starting up.  
             
             Sent every time PCE starts up via a manual intervention or typically 
             via the watchdog."
    ::= { ptiSegway 0 4301 }

ptPCEPceProcessShutdown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the PCE process is shutting down.  
             
             Sent every time PCE is terminated (intentionally or not).
             System based termination include:
               - LDL Configuration error
               - Process received a terminating signal (SIGINT, SIGTERM)."
    ::= { ptiSegway 0 4302 }

ptPCEPcePeerUp NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a PCE peer is reachable.  
             
             Sent when a PCE peer communication is established via LDL."
    ::= { ptiSegway 0 4303 }

ptPCEPcePeerDown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a PCE peer is no longer reachable.  
             
             Sent when a PCE peer communication is lost via LDL.
             Peer connectivity interruptions include:
               - PCE peer is terminated
               - IP connectivity heartbeat/keep alive fails
               - IP connectivity is lost between PCE processes."
    ::= { ptiSegway 0 4304 }

ptPCEPceWriteFailure NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates a PCE write to file failed.  
             
             Sent when a PCE configuration or database write fails.
             Write failures include:
               - Invalid file permissions
               - Out of memory in file system"
    ::= { ptiSegway 0 4305 }

ptPCEConfigurationPceDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 4306 }

ptPCEConfigurationPceDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Debug attributes are set to their recommended values."
    ::= { ptiSegway 0 4307 }

ptGTTGttProcessStartup NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the GTT process is starting up.
             
             Freq:
             This trap will appear every time GTT starts up.
             
             References:
                ptOriginatingOID    : ptGTT
                ptTrapType          : 11 quality of service alarm
                ptTrapSeverity      : 5 cleared
                ptTrapProbableCause : 6 Communications subsystem error
                ptTrapClearType     : 2 oic
             "
    ::= { ptiSegway 0 4400 }

ptGTTGttProcessShutdown NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates the GTT process is shutting down (gracefully).
             
             Cause:
             This may not be a failure, shutdown could be intentional.  If it is a
             failure, it may be caused by a number of reasons, including:
                - invalid config files
                - process received a terminating signal (SIGINT, SIGTERM)
                - system resources are at capacity
             
             Action:
                - make sure GTT was started with a valid base directory (-b switch)
                - restart GTT (system watchdog has this responsibility)
                - contact Sonus Networks Support for system resource issues
             
             Freq:
             This trap will appear every time GTT gracefully shuts down.
             
             References:
                ptOriginatingOID    : ptGTT
                ptTrapType          : 11 quality of service alarm
                ptTrapSeverity      : 2 major
                ptTrapProbableCause : 6 Communications subsystem error
                ptTrapClearType     : 1 fmic
             "
    ::= { ptiSegway 0 4401 }

ptGTTConfigurationGttConfigurationError NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Obsolete as of 9.0.0.
             
             This trap indicates that there was an error while processing the
             configuration file: gtt.conf
             
             Cause:
             A configuration error may be caused by a number of reasons, including:
                - unable to create configuration file
                - unable to open configuration file in read or write mode
                - there was an irrecoverable error in the configuration file
             
             Action:
                - make sure the GTT base directory (-b switch) has write access
                - make sure the configuration file has the proper permissions
                - review the configuration file for possible issues (e.g. a SCCP
                  connection is configured on NA 2 but there is no NA 2 specified)
             
             Freq:
             This trap will appear when GTT is unable to recover from configuration
             problem.
             
             References:
                ptOriginatingOID    : ptGTTConfiguration
                ptTrapType          : 11 quality of service alarm
                ptTrapSeverity      : 2 major
                ptTrapProbableCause : 6 Communications subsystem error
                ptTrapClearType     : 2 oic
             "
    ::= { ptiSegway 0 4402 }

ptGTTDBSummaryInitialDatabaseLoadFailed NOTIFICATION-TYPE
    OBJECTS         { ptTrapType, ptTrapSequenceNumber, ptTrapSeverity, 
                      ptTrapProbableCause, ptTrapClearType, 
                      ptTrapDateAndTime, ptTrapItemOID, 
                      ptGTTGTTDBSummaryDatabaseType, 
                      ptGTTGTTDBSummaryGTCalledSearches, 
                      ptGTTGTTDBSummaryGTModifications, 
                      ptGTTGTTDBSummaryPCLists, 
                      ptGTTGTTDBSummaryCommandLists, 
                      ptGTTGTTDBSummaryGTCallingSearches, 
                      ptGTTGTTDBSummaryGTOPCSearches }
    STATUS          current
    DESCRIPTION     
            "This trap indicates that GTT was not successful in loading its Live/GTT
             database at startup. "
    ::= { ptiSegway 0 4405 }

ptGTTConfigurationGttConfigurationWarning NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates the there is an expected object/parameter missing 
             from the configuration file ."
    ::= { ptiSegway 0 4406 }

ptGTTDBSummaryInitialDatabaseLoadSuccess NOTIFICATION-TYPE
    OBJECTS         { ptTrapType, ptTrapSequenceNumber, ptTrapSeverity, 
                      ptTrapProbableCause, ptTrapClearType, 
                      ptTrapDateAndTime, ptTrapItemOID, 
                      ptGTTGTTDBSummaryDatabaseType, 
                      ptGTTGTTDBSummaryGTCalledSearches, 
                      ptGTTGTTDBSummaryGTModifications, 
                      ptGTTGTTDBSummaryPCLists, 
                      ptGTTGTTDBSummaryCommandLists, 
                      ptGTTGTTDBSummaryGTCallingSearches, 
                      ptGTTGTTDBSummaryGTOPCSearches }
    STATUS          current
    DESCRIPTION     
            "This trap indicates that GTT was  successful in loading its Live/GTT
             database at startup.
             
             
             Cause:
             This failure may be caused by number of reasons, including:
                - database files do not exist
                - database files are corrupt/not readable
                - upgrade from older database files failed
             
             Action:
                - make sure GTT was started with a valid base directory (-b switch)
                - if manually transferred or moved, make sure files have not been truncated
                - contact Sonus Networks Support for upgrade failures
             
             Freq:
             This trap will appear if GTT was not capable of loading its Live database.
             
             References:
                ptOriginatingOID    : DYNAMIC ptGTTDBSummary
                ptTrapType          : 11 quality of service alarm
                ptTrapSeverity      : 2 major
                ptTrapProbableCause : 6 Communications subsystem error
                ptTrapClearType     : 1 fmic
             "
    ::= { ptiSegway 0 4407 }

ptGTTConfigurationGttLicenseWarning NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that GTT process cannot connect to the license process."
    ::= { ptiSegway 0 4408 }

ptGTTConfigurationGttLicenseError NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that GTT process cannot a  license."
    ::= { ptiSegway 0 4409 }

ptGTTConfigurationGttLicenseSuccess NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap clears  trap 4409."
    ::= { ptiSegway 0 4410 }

ptPCRegistrationPcRegistrationError NOTIFICATION-TYPE
    OBJECTS         { ptTrapType, ptTrapSequenceNumber, ptTrapSeverity, 
                      ptTrapProbableCause, ptTrapClearType, 
                      ptTrapDateAndTime, ptTrapItemOID, 
                      ptGTTPCRegistrationPointCode }
    STATUS          current
    DESCRIPTION     
            "This trap indicates that the PC registration is not successful."
    ::= { ptiSegway 0 4411 }

ptPCRegistrationPcRegistrationSuccess NOTIFICATION-TYPE
    OBJECTS         { ptTrapType, ptTrapSequenceNumber, ptTrapSeverity, 
                      ptTrapProbableCause, ptTrapClearType, 
                      ptTrapDateAndTime, ptTrapItemOID, 
                      ptGTTPCRegistrationPointCode }
    STATUS          current
    DESCRIPTION     
            "This trap indicates that the PC registration is successful."
    ::= { ptiSegway 0 4412 }

ptAppIDRegistrationAppIDRegistrationError NOTIFICATION-TYPE
    OBJECTS         { ptTrapType, ptTrapSequenceNumber, ptTrapSeverity, 
                      ptTrapProbableCause, ptTrapClearType, 
                      ptTrapDateAndTime, ptTrapItemOID, 
                      ptGTTAppIDRegistrationApplicationID }
    STATUS          current
    DESCRIPTION     
            "This trap indicates that the AppID registration is not successful."
    ::= { ptiSegway 0 4413 }

ptAppIDRegistrationAppIDRegistrationSuccess NOTIFICATION-TYPE
    OBJECTS         { ptTrapType, ptTrapSequenceNumber, ptTrapSeverity, 
                      ptTrapProbableCause, ptTrapClearType, 
                      ptTrapDateAndTime, ptTrapItemOID, 
                      ptGTTAppIDRegistrationApplicationID }
    STATUS          current
    DESCRIPTION     
            "This trap indicates that the AppID registration is successful."
    ::= { ptiSegway 0 4414 }

ptGTTDBDefGttOpcLoopDetect NOTIFICATION-TYPE
    OBJECTS         { ptTrapType, ptTrapSequenceNumber, ptTrapSeverity, 
                      ptTrapProbableCause, ptTrapClearType, 
                      ptTrapDateAndTime, ptTrapItemOID, 
                      ptGTTGTTDBDefName }
    STATUS          current
    DESCRIPTION     
            "GTT OPC Loop Detection discarded messages.
             This alarm will clear automatically if no more message is discarded by OPC Loop Detection
             for 5 minutes."
    ::= { ptiSegway 0 4415 }

ptGTTDBDefGttOpcLoopClear NOTIFICATION-TYPE
    OBJECTS         { ptTrapType, ptTrapSequenceNumber, ptTrapSeverity, 
                      ptTrapProbableCause, ptTrapClearType, 
                      ptTrapDateAndTime, ptTrapItemOID, 
                      ptGTTGTTDBDefName }
    STATUS          current
    DESCRIPTION     
            "GTT OPC Loop Detection no longer discards messages for 5 minutes."
    ::= { ptiSegway 0 4416 }

ptGTTDBDefGttOpcLoopFilterDetect NOTIFICATION-TYPE
    OBJECTS         { ptTrapType, ptTrapSequenceNumber, ptTrapSeverity, 
                      ptTrapProbableCause, ptTrapClearType, 
                      ptTrapDateAndTime, ptTrapItemOID, 
                      ptGTTGTTDBDefName }
    STATUS          current
    DESCRIPTION     
            "GTT OPC Loop Detection filters PC List entries.
             This alarm will clear automatically if no more message results in PC List entry filtering by OPC Loop Detection
             for 5 minutes."
    ::= { ptiSegway 0 4417 }

ptGTTDBDefGttOpcLoopFilterClear NOTIFICATION-TYPE
    OBJECTS         { ptTrapType, ptTrapSequenceNumber, ptTrapSeverity, 
                      ptTrapProbableCause, ptTrapClearType, 
                      ptTrapDateAndTime, ptTrapItemOID, 
                      ptGTTGTTDBDefName }
    STATUS          current
    DESCRIPTION     
            "GTT OPC Loop Detection no longer filters PC List entries for 5 minutes."
    ::= { ptiSegway 0 4418 }

ptGTTConfigurationGttDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 4420 }

ptGTTConfigurationGttDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 4421 }

ptConnectionLocalHostResFail NOTIFICATION-TYPE
    OBJECTS         { ptTrapType, ptTrapSequenceNumber, ptTrapSeverity, 
                      ptTrapProbableCause, ptTrapClearType, 
                      ptTrapDateAndTime, ptTrapItemOID, 
                      ptLBConnectionName }
    STATUS          current
    DESCRIPTION     
            "No IP address resolutions can be made for the Local Host. 
             No connection can be successful. Either change Local Host or add a resolution for that value."
    ::= { ptiSegway 0 5001 }

ptConnectionLocalHostResFailCleared NOTIFICATION-TYPE
    OBJECTS         { ptTrapType, ptTrapSequenceNumber, ptTrapSeverity, 
                      ptTrapProbableCause, ptTrapClearType, 
                      ptTrapDateAndTime, ptTrapItemOID, 
                      ptLBConnectionName }
    STATUS          current
    DESCRIPTION     
            "An IP address resolution can be made for the Local Host.  Connections from that address will pass."
    ::= { ptiSegway 0 5002 }

ptConnectionRemoteHostResFail NOTIFICATION-TYPE
    OBJECTS         { ptTrapType, ptTrapSequenceNumber, ptTrapSeverity, 
                      ptTrapProbableCause, ptTrapClearType, 
                      ptTrapDateAndTime, ptTrapItemOID, 
                      ptLBConnectionName }
    STATUS          current
    DESCRIPTION     
            "No IP address resolutions can be made for the Remote Host. 
             No connection can be successful. Either change Remote Host or add a resolution for that value."
    ::= { ptiSegway 0 5003 }

ptConnectionRemoteHostResFailCleared NOTIFICATION-TYPE
    OBJECTS         { ptTrapType, ptTrapSequenceNumber, ptTrapSeverity, 
                      ptTrapProbableCause, ptTrapClearType, 
                      ptTrapDateAndTime, ptTrapItemOID, 
                      ptLBConnectionName }
    STATUS          current
    DESCRIPTION     
            "An IP address resolution can be made for the Remote Host.  Connections from that address will pass."
    ::= { ptiSegway 0 5004 }

ptTargetTargetLoadUnbalanced NOTIFICATION-TYPE
    OBJECTS         { ptTrapType, ptTrapSequenceNumber, ptTrapSeverity, 
                      ptTrapProbableCause, ptTrapClearType, 
                      ptTrapDateAndTime, ptTrapItemOID, ptLBTargetName }
    STATUS          current
    DESCRIPTION     
            "Choose whether to force or ignore re-balancing in the target.
             Manually force re-balancing or ignore re-balancing in the target."
    ::= { ptiSegway 0 5005 }

ptTargetTargetLoadBalanced NOTIFICATION-TYPE
    OBJECTS         { ptTrapType, ptTrapSequenceNumber, ptTrapSeverity, 
                      ptTrapProbableCause, ptTrapClearType, 
                      ptTrapDateAndTime, ptTrapItemOID, ptLBTargetName }
    STATUS          current
    DESCRIPTION     
            "The load is either balanced or imbalance was ignored."
    ::= { ptiSegway 0 5006 }

ptCpuLoadExceeded NOTIFICATION-TYPE
    OBJECTS         { ptTrapType, ptTrapSeverity, ptTrapSequenceNumber, 
                      ptTrapProbableCause, ptTrapClearType, 
                      ptTrapDateAndTime, ptTrapSlotNumber, laLoad }
    STATUS          current
    DESCRIPTION     
            "This trap indicates that CPU load has reached its alarm threshold"
    ::= { ptiSegway 0 5501 }

ptCpuLoadCleared NOTIFICATION-TYPE
    OBJECTS         { ptTrapType, ptTrapSeverity, ptTrapSequenceNumber, 
                      ptTrapProbableCause, ptTrapClearType, 
                      ptTrapDateAndTime, ptTrapSlotNumber, laLoad }
    STATUS          current
    DESCRIPTION     
            "This trap indicates that the CPU load has returned below its alarm threshold"
    ::= { ptiSegway 0 5502 }

ptFreeMemThresholdExceeded NOTIFICATION-TYPE
    OBJECTS         { ptTrapType, ptTrapSeverity, ptTrapSequenceNumber, 
                      ptTrapProbableCause, ptTrapClearType, 
                      ptTrapDateAndTime, ptTrapSlotNumber, memTotalFree }
    STATUS          current
    DESCRIPTION     
            "This trap indicates that the memory usage has reached its alarm threshold"
    ::= { ptiSegway 0 5503 }

ptFreeMemTresholdCleared NOTIFICATION-TYPE
    OBJECTS         { ptTrapType, ptTrapSeverity, ptTrapSequenceNumber, 
                      ptTrapProbableCause, ptTrapClearType, 
                      ptTrapDateAndTime, ptTrapSlotNumber, memTotalFree }
    STATUS          current
    DESCRIPTION     
            "This trap indicates that the memory usage has returned below its alarm threshold"
    ::= { ptiSegway 0 5504 }

ptRootDiskPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that root disk partition usage has reached its alarm threshold"
    ::= { ptiSegway 0 5507 }

ptRootDiskPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the root disk partition usage has returned below its alarm threshold"
    ::= { ptiSegway 0 5508 }

ptIrscFtpUploadFailed NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that an irsc ftp upload failed"
    ::= { ptiSegway 0 5509 }

ptTmpDiskPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that /tmp disk partition usage has reached its alarm threshold"
    ::= { ptiSegway 0 5510 }

ptTmpDiskPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the /tmp disk partition usage has returned below its alarm threshold"
    ::= { ptiSegway 0 5511 }

ptRshRequestThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the rsh request from audit_cpu to the master cpu has reached its alarm threshold"
    ::= { ptiSegway 0 5512 }

ptTmpSelmonIpmitoolDown NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that sel_mon is now operable, and the ipmitool responding properly"
    ::= { ptiSegway 0 5513 }

ptTmpSelmonIpmitoolUp NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that sel_mon is now operable, and the ipmitool responding properly"
    ::= { ptiSegway 0 5514 }

ptSigflexDiskPartitionThresholdExceeded NOTIFICATION-TYPE
    OBJECTS         { ptTrapType, ptTrapSeverity, ptTrapSequenceNumber, 
                      ptTrapProbableCause, ptTrapClearType, 
                      ptTrapDateAndTime, ptTrapSlotNumber, 
                      ptTrapDirectoryName }
    STATUS          current
    DESCRIPTION     
            "This trap indicates that the directory referenced by the ptTrapDirectoryName variable has reached its alarm threshold"
    ::= { ptiSegway 0 5515 }

ptSigflexDiskPartitionThresholdCleared NOTIFICATION-TYPE
    OBJECTS         { ptTrapType, ptTrapSeverity, ptTrapSequenceNumber, 
                      ptTrapProbableCause, ptTrapClearType, 
                      ptTrapDateAndTime, ptTrapSlotNumber, 
                      ptTrapDirectoryName }
    STATUS          current
    DESCRIPTION     
            "This trap indicates that the directory referenced by the ptTrapDirectoryName variable has returned below its alarm threshold"
    ::= { ptiSegway 0 5516 }

ptCpuUsageMinorThresholdCrossed NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that CPU Usage has crossed its minor alarm threshold on a CPU Core"
    ::= { ptiSegway 0 5517 }

ptCpuUsageMinorThresholdCleared NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that the CPU Usage has returned below its minor alarm threshold on a CPU Core"
    ::= { ptiSegway 0 5518 }

ptCpuUsageMajorThresholdCrossed NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that CPU Usage has crossed its major alarm threshold on a CPU Core"
    ::= { ptiSegway 0 5519 }

ptCpuUsageMajorThresholdCleared NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that the CPU Usage has returned below its major alarm threshold on a CPU Core"
    ::= { ptiSegway 0 5520 }

ptCpuUsageCriticalThresholdCrossed NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that CPU Usage has crossed its critical alarm threshold on a CPU Core"
    ::= { ptiSegway 0 5521 }

ptCpuUsageCriticalThresholdCleared NOTIFICATION-TYPE
    OBJECTS         { ptTrapType, ptTrapSeverity, ptTrapSequenceNumber, 
                      ptTrapProbableCause, ptTrapClearType, 
                      ptTrapDateAndTime, ptTrapSlotNumber, ptTrapCpuCore, 
                      ptTrapCpuUsage }
    STATUS          current
    DESCRIPTION     
            "This trap indicates that the CPU Usage has returned below its critical alarm threshold on a CPU Core"
    ::= { ptiSegway 0 5522 }

ptIsmRootPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM root partition usage has reached its alarm threshold"
    ::= { ptiSegway 0 5523 }

ptIsmRootPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM root partition usage has returned below its alarm threshold"
    ::= { ptiSegway 0 5524 }

ptIsmOptPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /opt partition usage has reached its alarm threshold"
    ::= { ptiSegway 0 5525 }

ptIsmOptPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /opt partition usage has returned below its alarm threshold"
    ::= { ptiSegway 0 5526 }

ptIsmVarPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /var partition usage has reached its alarm threshold"
    ::= { ptiSegway 0 5527 }

ptIsmVarPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /var partition usage has returned below its alarm threshold"
    ::= { ptiSegway 0 5528 }

ptIsmEtcPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /etc partition usage has reached its alarm threshold"
    ::= { ptiSegway 0 5529 }

ptIsmEtcPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the ISM /var partition usage has returned below its alarm threshold"
    ::= { ptiSegway 0 5530 }

ptDSCDBPartitionThresholdExceeded NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the DSCDB Partition usage has reached its alarm threshold"
    ::= { ptiSegway 0 5531 }

ptDSCDBPartitionThresholdCleared NOTIFICATION-TYPE
    OBJECTS         { ptTrapType, ptTrapSeverity, ptTrapSequenceNumber, 
                      ptTrapProbableCause, ptTrapClearType, 
                      ptTrapDateAndTime, ptTrapSlotNumber }
    STATUS          current
    DESCRIPTION     
            "This trap indicates that the DSCDB Partition usage has returned below its alarm threshold"
    ::= { ptiSegway 0 5532 }

ptIOManagerMpmtp2UpperLayerConnectionLost NOTIFICATION-TYPE
    OBJECTS         { ptTrapType, ptTrapSequenceNumber, ptTrapSeverity, 
                      ptTrapProbableCause, ptTrapClearType, 
                      ptTrapDateAndTime, ptTrapItemOID, 
                      ptIOHWIOManagerSlotNumber, ptIOHWIOManagerCardType }
    STATUS          current
    DESCRIPTION     
            "This trap indicates all L3 connections are lost.
             
             Cause  - MTP2 has lost all Level 3 connections.
             
             Action - Check Level 3 Applications
             Freq   - Infrequent
             
             References
             
                    - ptOriginatingOID:    DYNAMIC ptTDMCard
                    - ptTrapType:          2 Communications
                    - ptTrapSeverity:      4 Warning
                    - ptTrapProbableCause: 7 Configuration error
                    - ptTrapClearType:     1 fmic
             "
    ::= { ptiSegway 0 5800 }

ptIOManagerMpmtp2UpperLayerConnectionGained NOTIFICATION-TYPE
    OBJECTS         { ptTrapType, ptTrapSequenceNumber, ptTrapSeverity, 
                      ptTrapProbableCause, ptTrapClearType, 
                      ptTrapDateAndTime, ptTrapItemOID, 
                      ptIOHWIOManagerSlotNumber, ptIOHWIOManagerCardType }
    STATUS          current
    DESCRIPTION     
            "This trap indicates at least one L3 connection has been made.
             
             Cause  - MTP2 has made at least one connection to a Level 3 application.
             
             Action - None
             Freq   - Infrequent
             
             References
             
                    - ptOriginatingOID:    DYNAMIC ptTDMCard
                    - ptTrapType:          2 Communications
                    - ptTrapSeverity:      5 clear
                    - ptTrapProbableCause: 7 Configuration error
                    - ptTrapClearType:     1 fmic
             "
    ::= { ptiSegway 0 5801 }

ptLSLChannelMpmtp2SigChanLoopbackSet NOTIFICATION-TYPE
    OBJECTS         { ptTrapType, ptTrapSequenceNumber, ptTrapSeverity, 
                      ptTrapProbableCause, ptTrapClearType, 
                      ptTrapDateAndTime, ptTrapItemOID, 
                      ptIOHWLSLChannelChannelNumber, 
                      ptIOHWLSLChannelLoopbackMode }
    STATUS          current
    DESCRIPTION     
            "This trap indicates that the signaling channel loopback mode setting
             has been changed from the default DISABLED mode
             
             Cause  - A user has modified the attribute
             
             Action - Reset to DISABLED for normal operation
             Freq   - This trap will appear when the user sets the Loopback mode
                      attribute to anything other than DISABLED
             
             References
             
                    - ptOriginatingOID:    DYNAMIC ptSignalingChannel
                    - ptTrapType:          2 communication alarm
                    - ptTrapSeverity:      3 minor
                    - ptTrapProbableCause: 7 Configuration error
                    - ptTrapClearType:     1 fmic
             "
    ::= { ptiSegway 0 5802 }

ptLSLChannelMpmtp2SigChanLoopbackCleared NOTIFICATION-TYPE
    OBJECTS         { ptTrapType, ptTrapSequenceNumber, ptTrapSeverity, 
                      ptTrapProbableCause, ptTrapClearType, 
                      ptTrapDateAndTime, ptTrapItemOID, 
                      ptIOHWLSLChannelChannelNumber, 
                      ptIOHWLSLChannelLoopbackMode }
    STATUS          current
    DESCRIPTION     
            "This trap indicates that the signaling channel loopback mode setting
             has been set to the default DISABLED mode
             
             Cause  - A user has reset the attribute to the default or the system
                      has restarted with default values
             
             Action - None required
             Freq   - This trap will appear when the user sets the Loopback
                      attribute to DISABLED or the system has started with this
                      configured value for Loopback Mode.
             
             References
             
                    - ptOriginatingOID:    DYNAMIC ptSignalingChannel
                    - ptTrapType:          2 communication alarm
                    - ptTrapSeverity:      5 clear
                    - ptTrapProbableCause: 7 Configuration error
                    - ptTrapClearType:     1 fmic
             "
    ::= { ptiSegway 0 5803 }

ptLSLH110ChannelMpmtp2H110SigChanLoopbackSet NOTIFICATION-TYPE
    OBJECTS         { ptTrapType, ptTrapSequenceNumber, ptTrapSeverity, 
                      ptTrapProbableCause, ptTrapClearType, 
                      ptTrapDateAndTime, ptTrapItemOID, 
                      ptIOHWLSLH110ChannelChannelNumber, 
                      ptIOHWLSLH110ChannelLoopbackMode }
    STATUS          current
    DESCRIPTION     
            "This trap indicates that the H110 signaling channel loopback mode
             setting has been changed from the default DISABLED mode
             
             Cause  - A user has modified the attribute
             
             Action - Reset to DISABLED for normal operation
             Freq   - This trap will appear when the user sets the Loopback mode
                      attribute to anything other than DISABLED
             
             References
             
                    - ptOriginatingOID:    DYNAMIC ptH110SignalingChannel
                    - ptTrapType:          2 communication alarm
                    - ptTrapSeverity:      3 minor
                    - ptTrapProbableCause: 7 Configuration error
                    - ptTrapClearType:     1 fmic
             "
    ::= { ptiSegway 0 5804 }

ptLSLH110ChannelMpmtp2H110SigChanLoopbackCleared NOTIFICATION-TYPE
    OBJECTS         { ptTrapType, ptTrapSequenceNumber, ptTrapSeverity, 
                      ptTrapProbableCause, ptTrapClearType, 
                      ptTrapDateAndTime, ptTrapItemOID, 
                      ptIOHWLSLH110ChannelChannelNumber, 
                      ptIOHWLSLH110ChannelLoopbackMode }
    STATUS          current
    DESCRIPTION     
            "This trap indicates that the H110 signaling channel loopback mode
             setting has been set to the default DISABLED mode
             
             Cause  - A user has reset the attribute to the default or the system
                      has restarted with default values
             Action - None required
             Freq   - This trap will appear when the user sets the Loopback
                      attribute to DISABLED or when the system has started with this
                      configured value for Loopback Mode.
             
             References
             
                    - ptOriginatingOID:    DYNAMIC ptH110SignalingChannel
                    - ptTrapType:          2 communication alarm
                    - ptTrapSeverity:      5 clear
                    - ptTrapProbableCause: 7 Configuration error
                    - ptTrapClearType:     1 fmic
             "
    ::= { ptiSegway 0 5805 }

ptHSLATMChannelMpmtp2SAALChanDeactivated NOTIFICATION-TYPE
    OBJECTS         { ptTrapType, ptTrapSequenceNumber, ptTrapSeverity, 
                      ptTrapProbableCause, ptTrapClearType, 
                      ptTrapDateAndTime, ptTrapItemOID, 
                      ptIOHWHSLATMChannelChannelNumber, 
                      ptIOHWHSLATMChannelPort }
    STATUS          current
    DESCRIPTION     
            "An ATM Link has been manually deactivated.  This is done either
             directly on the link or at the link manager level.
             
             Cause  - ATM link has been deactivated.
             Action - Re-activate the link
             Freq   - By user interaction
             
             References
             
                    - ptOriginatingOID:    DYNAMIC ptATMLink
                    - ptTrapType:          11 quality of service
                    - ptTrapSeverity:      3 major
                    - ptTrapProbableCause: 7 Configuration error
                    - ptTrapClearType:     1 fmic
             "
    ::= { ptiSegway 0 5806 }

ptHSLATMChannelMpmtp2SAALChanActivated NOTIFICATION-TYPE
    OBJECTS         { ptTrapType, ptTrapSequenceNumber, ptTrapSeverity, 
                      ptTrapProbableCause, ptTrapClearType, 
                      ptTrapDateAndTime, ptTrapItemOID, 
                      ptIOHWHSLATMChannelChannelNumber, 
                      ptIOHWHSLATMChannelPort }
    STATUS          current
    DESCRIPTION     
            "An ATM Link has been manually deactivated.  This is done either
             directly on the link or at the link manager level.
             
             Cause  - ATM link has been deactivated.
             Action - Re-activate the link
             Freq   - By user interaction
             
             References
             
                    - ptOriginatingOID:    DYNAMIC ptATMLink
                    - ptTrapType:          11 quality of service
                    - ptTrapSeverity:      3 major
                    - ptTrapProbableCause: 7 Configuration error
                    - ptTrapClearType:     1 fmic
             "
    ::= { ptiSegway 0 5807 }

ptPortClockingMpmtp2ReferenceClockIsNotPrimary NOTIFICATION-TYPE
    OBJECTS         { ptTrapType, ptTrapSequenceNumber, ptTrapSeverity, 
                      ptTrapProbableCause, ptTrapClearType, 
                      ptTrapDateAndTime, ptTrapItemOID, 
                      ptIOHWPortClockingCurrentClockSource }
    STATUS          current
    DESCRIPTION     
            "This trap indicates that the reference clock source is no longer taken from the primary setting
             
             Cause  - The reference clock source has been lost for a number of reasons
                        - Remote equipment failure.
                        - Local Port failure.
                        - Loss of Sync or Framing on the port
             
             Action - Depends on the cause
             Freq   - This trap will appear when the clocking reference has been lost on the PRIMARY reference
             
             References
             
                    - ptOriginatingOID:    DYNAMIC ptTDMCard
                    - ptTrapType:          4 equipment alarm
                    - ptTrapSeverity:      3 minor
                    - ptTrapProbableCause: 6 Communications subsystem error
                    - ptTrapClearType:     1 fmic
             "
    ::= { ptiSegway 0 5808 }

ptPortClockingMpmtp2ReferenceClockIsPrimary NOTIFICATION-TYPE
    OBJECTS         { ptTrapType, ptTrapSequenceNumber, ptTrapSeverity, 
                      ptTrapProbableCause, ptTrapClearType, 
                      ptTrapDateAndTime, ptTrapItemOID, 
                      ptIOHWPortClockingCurrentClockSource }
    STATUS          current
    DESCRIPTION     
            "This trap indicates that the clock source is referenced from the PRIMARY setting
             
             Cause  - The PRIMARY setting is used as the reference clock
             
             Action - None required
             Freq   - This trap will appear when the clocking reference is derived from the PRIMARY setting
             
             References
             
                    - ptOriginatingOID:    DYNAMIC ptTDMCard
                    - ptTrapType:          4 equipment alarm
                    - ptTrapSeverity:      5 clear
                    - ptTrapProbableCause: 6 Communications subsystem error
                    - ptTrapClearType:     1 fmic
             "
    ::= { ptiSegway 0 5809 }

ptPortMpmtp2PortLoopbackSet NOTIFICATION-TYPE
    OBJECTS         { ptTrapType, ptTrapSequenceNumber, ptTrapSeverity, 
                      ptTrapProbableCause, ptTrapClearType, 
                      ptTrapDateAndTime, ptTrapItemOID, 
                      ptIOHWPortPortNumber, ptIOHWPortLoopbackMode }
    STATUS          current
    DESCRIPTION     
            "This trap indicates that the loopback mode setting has been changed
             from the default DISABLED mode
             
             Cause  - A user has modified the attribute
             
             Action - Reset to DISABLED for normal operation
             Freq   - This trap will appear when the user sets the Loopback mode
                      attribute to anything other than DISABLED
             
             References
             
                    - ptOriginatingOID:    DYNAMIC ptPort
                    - ptTrapType:          2 communication alarm
                    - ptTrapSeverity:      3 minor
                    - ptTrapProbableCause: 7 Configuration error
                    - ptTrapClearType:     1 fmic
             "
    ::= { ptiSegway 0 5810 }

ptPortMpmtp2PortLoopbackCleared NOTIFICATION-TYPE
    OBJECTS         { ptTrapType, ptTrapSequenceNumber, ptTrapSeverity, 
                      ptTrapProbableCause, ptTrapClearType, 
                      ptTrapDateAndTime, ptTrapItemOID, 
                      ptIOHWPortPortNumber, ptIOHWPortLoopbackMode }
    STATUS          current
    DESCRIPTION     
            "This trap indicates that the loopback mode setting has been set
             to the default DISABLED mode
             
             Cause  - A user has reset the attribute to the default or the
                      system has restarted with default values
             
             Action - None required
             Freq   - This trap will appear when the user sets the Loopback
                      attribute to DISABLED or when the system has started with
                      this configured value for Loopback Mode.
                     
             
             References
             
                    - ptOriginatingOID:    DYNAMIC ptPort
                    - ptTrapType:          2 communication alarm
                    - ptTrapSeverity:      5 clear
                    - ptTrapProbableCause: 7 Configuration error
                    - ptTrapClearType:     1 fmic
             "
    ::= { ptiSegway 0 5811 }

ptIOManagerMpmtp2SoftwareRestartRequired NOTIFICATION-TYPE
    OBJECTS         { ptTrapType, ptTrapSequenceNumber, ptTrapSeverity, 
                      ptTrapProbableCause, ptTrapClearType, 
                      ptTrapDateAndTime, ptTrapItemOID, 
                      ptIOHWIOManagerSlotNumber, 
                      ptIOHWIOManagerSelectConfiguration, 
                      ptIOHWIOManagerRestartRequired }
    STATUS          current
    DESCRIPTION     
            "Trap is raised when the configuration selection has changed.  A software
             restart is required on this slot number in order for the change to take effect.
             
             Cause   - Configuration change partly complete.
             Action  - Restart software on the alarmed slot.
             Freq    - User change request.
             
             References
             
                    - ptOriginatingOID:    DYNAMIC ptTDMCard
                    - ptTrapType:          2 Communications
                    - ptTrapSeverity:      5 clear
                    - ptTrapProbableCause: 7 Configuration error
                    - ptTrapClearType:     1 fmic
             "
    ::= { ptiSegway 0 5812 }

ptPortMpmtp2PortFarEndLoopbackSet NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that the far end has been instructed to
             enter loopback mode for testing.
             
             Cause  - A user has instructed loopback activation codes to be
                      sent to place the far end in test mode
             
             Action - Send Loop Down or Stop BERT to instruct the far end
                      to return to normal operation
             Freq   - This trap will appear when the user instructs the far
                      end to enter test mode, such as for BERT.
             
             References
             
                    - ptOriginatingOID:    DYNAMIC ptPort
                    - ptTrapType:          2 communication alarm
                    - ptTrapSeverity:      3 minor
                    - ptTrapProbableCause: 7 Configuration error
                    - ptTrapClearType:     1 fmic
             "
    ::= { ptiSegway 0 5813 }

ptPortMpmtp2PortFarEndLoopbackCleared NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that the far end has been instructed to
             exit loopback mode for normal operation.
             
             Cause  - A user has instructed loopback deactivation codes to be
                      sent to restore the far end to normal operation
             
             Action - None required
             Freq   - This trap will appear when the user instructs the far
                      end to exit test mode, such as for BERT.
             
             References
             
                    - ptOriginatingOID:    DYNAMIC ptPort
                    - ptTrapType:          2 communication alarm
                    - ptTrapSeverity:      5 clear
                    - ptTrapProbableCause: 7 Configuration error
                    - ptTrapClearType:     1 fmic
             "
    ::= { ptiSegway 0 5814 }

ptPortMpmtp2PortPrbsSet NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that the PRBS test is active.
             
             Cause  - A user has activated PRBS testing
             
             Action - Stop PRBS or Stop BERT to deactivate PRBS testing
             Freq   - This trap will appear when the user instructs the port
                      to perform PRBS testing, such as for BERT.
             
             References
             
                    - ptOriginatingOID:    DYNAMIC ptPort
                    - ptTrapType:          2 communication alarm
                    - ptTrapSeverity:      3 minor
                    - ptTrapProbableCause: 7 Configuration error
                    - ptTrapClearType:     1 fmic
             "
    ::= { ptiSegway 0 5815 }

ptPortMpmtp2PortPrbsCleared NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that PRBS test has been deactivated.
             
             Cause  - A user has deactivated PRBS testing.
             
             Action - None required
             Freq   - This trap will appear when the user instructs the port
                      to stop performing PRBS testing, such as for BERT.
             
             References
             
                    - ptOriginatingOID:    DYNAMIC ptPort
                    - ptTrapType:          2 communication alarm
                    - ptTrapSeverity:      5 clear
                    - ptTrapProbableCause: 7 Configuration error
                    - ptTrapClearType:     1 fmic
             "
    ::= { ptiSegway 0 5816 }

ptPortMpmtp2PortStatusMajor NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that an MTP2 major port status event has occurred.
             
             Cause  - An error has occurred on the port.
             
             Action - Verify the functionality of the link and ports both locally and at the remote end.
             Freq   - This trap will appear whenever a major port status event occurs
             
             
             References
             
             - ptOriginatingOID:    DYNAMIC ptPort
             - ptTrapType:          4 equipment alarm
             - ptTrapSeverity:      2 major
             - ptTrapProbableCause: 6 Communications subsystem error
             - ptTrapClearType:     1 fmic
             "
    ::= { ptiSegway 0 5818 }

ptPortMpmtp2PortStatusMajorClear NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that the major port status events have cleared
             
             Cause  - All phyical port or link problems contributing to the major
                      port status events have been rectified.
             
             Action - None required
             Freq   - This trap will appear when the user sets the Loopback
                      attribute to DISABLED.  or the system has started with
                      this configured value for Loopback Mode.
             
             
             References
             
             - ptOriginatingOID:    DYNAMIC ptPort
             - ptTrapType:          4 equipment alarm
             - ptTrapSeverity:      5 clear
             - ptTrapProbableCause: 6 Communications subsystem error
             - ptTrapClearType:     1 fmic
             "
    ::= { ptiSegway 0 5819 }

ptPortMpmtp2PortStatusCritical NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that an MTP2 critical port status event has occurred.
             
             Cause  - An error has occurred on the port.
             
             Action - Verify the functionality of the link and ports both locally and at the remote end.
             Freq   - This trap will appear whenever a critical port status event occurs
             
             
             References
             
             - ptOriginatingOID:    DYNAMIC ptPort
             - ptTrapType:          4 equipment alarm
             - ptTrapSeverity:      1 critical
             - ptTrapProbableCause: 6 Communications subsystem error
             - ptTrapClearType:     1 fmic
             "
    ::= { ptiSegway 0 5820 }

ptPortMpmtp2PortStatusCriticalClear NOTIFICATION-TYPE
    OBJECTS         { ptTrapType, ptTrapSequenceNumber, ptTrapSeverity, 
                      ptTrapProbableCause, ptTrapClearType, 
                      ptTrapDateAndTime, ptTrapItemOID, 
                      ptIOHWPortPortNumber }
    STATUS          current
    DESCRIPTION     
            "This trap indicates that all critical status events have cleared
             
             Cause  - All phyical port or link problems contributing to the major
                      port status events have been rectified.
             
             Action - None required
             Freq   - This trap will appear when the user sets the Loopback
                      attribute to DISABLED or the system has started with
                      this configured value for Loopback Mode.
             
             
             References
             
             - ptOriginatingOID:    DYNAMIC ptPort
             - ptTrapType:          4 equipment alarm
             - ptTrapSeverity:      5 clear
             - ptTrapProbableCause: 6 Communications subsystem error
             - ptTrapClearType:     1 fmic
             "
    ::= { ptiSegway 0 5821 }

ptIOManagerMpmtp2DebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
              Possible Actions -
                 The user should perform the 'Restore Debug Defaults' action to reset all
                 debug attributes to their default values."
    ::= { ptiSegway 0 5822 }

ptIOManagerMpmtp2DebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 5823 }

ptSlotSlotCpuUsageMinor NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage is high.  The slot number indicated in this
             trap indicates the origin of the alarm.  This condition can lead the kernel
             to indiscriminately terminate processes causing outage.  A process listing
             and top output can identify the offending process.
             
             Cause  - CPU usage above threshold
             Action - Identify applications running high on CPU
             Freq   - Irregular    
             "
    ::= { ptiSegway 0 6240 }

ptSlotSlotCpuUsageMinorAbated NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage has returned to reasonable levels.
             
             Cause  - CPU usage below threshold.
             Action - None.
             Freq   - Irregular.                 
             "
    ::= { ptiSegway 0 6241 }

ptSlotSlotCpuUsageMajor NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage is very high.  The slot number indicated in this
             trap indicates the origin of the alarm.  This condition can lead the kernel
             to indiscriminately terminate processes causing outage.  A process listing
             and top output can identify the offending process.
             
             Cause  - CPU usage above threshold
             Action - Identify applications running high on CPU
             Freq   - Irregular    
             "
    ::= { ptiSegway 0 6242 }

ptSlotSlotCpuUsageMajorAbated NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage has returned to reasonable levels.
             
             Cause  - CPU usage below threshold.
             Action - None.
             Freq   - Irregular.                 
             "
    ::= { ptiSegway 0 6243 }

ptSlotSlotCpuUsageCritical NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage is critically high.  The slot number indicated in this
             trap indicates the origin of the alarm.  This condition can lead the kernel
             to indiscriminately terminate processes causing outage.  A process listing
             and top output can identify the offending process.
             
             Cause  - CPU usage above threshold
             Action - Identify applications running high on CPU
             Freq   - Irregular    
             "
    ::= { ptiSegway 0 6244 }

ptSlotSlotCpuUsageCriticalAbated NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "CPU usage has returned to reasonable levels.
             
             Cause  - CPU usage below threshold.
             Action - None.
             Freq   - Irregular.                 
             "
    ::= { ptiSegway 0 6245 }

ptSlotSlotIsmOptPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /opt partition usage is above the alarm threshold defined in 
             disk_space_quota.  The slot number indicated in this
             trap indicates the origin of the alarm.
             
             Cause  - ISM /opt partition usage above threshold
             Action - Identify applications running high on disk space
             Freq   - Irregular
             "
    ::= { ptiSegway 0 6246 }

ptSlotSlotIsmOptPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /opt partition usage has returned to acceptable levels.
             
             Cause  - ISM /opt partition usage below threshold.
             Action - None.
             Freq   - Irregular.
             "
    ::= { ptiSegway 0 6247 }

ptSlotSlotIsmVarPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /opt partition usage is above the alarm threshold defined in 
             disk_space_quota.  The slot number indicated in this
             trap indicates the origin of the alarm.
             
             Cause  - ISM /opt partition usage above threshold
             Action - Identify applications running high on disk space
             Freq   - Irregular
             "
    ::= { ptiSegway 0 6248 }

ptSlotSlotIsmVarPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /var partition usage has returned to acceptable levels.
             
             Cause  - ISM /var partition usage below threshold.
             Action - None.
             Freq   - Irregular.
             "
    ::= { ptiSegway 0 6249 }

ptSlotSlotStatusUnavailable NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "A card has stopped responding.  The card may be physically extracted
             or there has been a software/hardware malfunction.  This alarm will
             be raised on upgrade do to normal operation.
             
             Cause  - Card non-responsive.
             Action - Check the card is inserted and operational.
             Freq   - Infrequent.
             
             References
             
                    - ptOriginatingOID:    DYNAMIC Slot
                    - ptTrapType:          4  equipment alarm
                    - ptTrapSeverity:      1  critical
                    - ptTrapProbableCause: 11 quality of service
                    - ptTrapClearType:     1  fmic
             "
    ::= { ptiSegway 0 6250 }

ptSlotSlotStatusAvailable NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "A card has recovered and is responding.
             
             Cause  - Card is responsive.
             Action - None.
             Freq   - Infrequent.
             
             References
             
                    - ptOriginatingOID:    DYNAMIC Slot
                    - ptTrapType:          4  equipment alarm
                    - ptTrapSeverity:      5  clear
                    - ptTrapProbableCause: 11 quality of service 
                    - ptTrapClearType:     1  fmic
             "
    ::= { ptiSegway 0 6251 }

ptSlotSlotIPSubnet1Down NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "Communication loss on IP subnet 1 with this card.
             
             Cause  - IP path non-responsive.
             Action - Verify application communications.
             Freq   - Infrequent.
             
             References
             
                    - ptOriginatingOID:    DYNAMIC Slot
                    - ptTrapType:          4 equipment alarm
                    - ptTrapSeverity:      2 major
                    - ptTrapProbableCause: 7 communication subsystem
                    - ptTrapClearType:     1 fmic
             "
    ::= { ptiSegway 0 6252 }

ptSlotSlotIPSubnet1Up NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "Communication with this card on IP subnet 1 is established.
             
             Cause  - IP path established.
             Action - None.
             Freq   - Infrequent.
             
             References
             
                    - ptOriginatingOID:    DYNAMIC Slot
                    - ptTrapType:          4 equipment alarm
                    - ptTrapSeverity:      5 clear
                    - ptTrapProbableCause: 6 communication subsystem
                    - ptTrapClearType:     1 fmic
             "
    ::= { ptiSegway 0 6253 }

ptSlotSlotIPSubnet2Down NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "Communication loss on IP subnet 2 with this card.
             
             Cause  - IP path non-responsive.
             Action - Verify application communications.
             Freq   - Infrequent.
             
             References
             
                    - ptOriginatingOID:    DYNAMIC Slot
                    - ptTrapType:          4 equipment alarm
                    - ptTrapSeverity:      2 major
                    - ptTrapProbableCause: 7 communication subsystem
                    - ptTrapClearType:     1 fmic
             "
    ::= { ptiSegway 0 6254 }

ptSlotSlotIPSubnet2Up NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotPrimaryIP, 
                      ptSlotSecondaryIP }
    STATUS          current
    DESCRIPTION     
            "Communication with this card on IP subnet 2 is established.
             
             Cause  - IP path established.
             Action - None.
             Freq   - Infrequent.
             
             References
             
                    - ptOriginatingOID:    DYNAMIC Slot
                    - ptTrapType:          4 equipment alarm
                    - ptTrapSeverity:      5 clear
                    - ptTrapProbableCause: 6 communication subsystem
                    - ptTrapClearType:     1 fmic
             "
    ::= { ptiSegway 0 6255 }

ptApplicationSlotApplicationStopped NOTIFICATION-TYPE
    OBJECTS         { ptTrapType, ptTrapSequenceNumber, ptTrapSeverity, 
                      ptTrapProbableCause, ptTrapClearType, 
                      ptTrapDateAndTime, ptTrapItemOID, 
                      ptApplicationSlotNumber, 
                      ptApplicationApplicationName, 
                      ptApplicationApplicationState }
    STATUS          current
    DESCRIPTION     
            "The named application has stopped running.  May be due to user
             interaction or application fault.
             
             Cause  - Application is not running.
             Action - Verify services.
             Freq   - Infrequent.
             
             References
             
                    - ptOriginatingOID:    DYNAMIC Application
                    - ptTrapType:          4  equipment alarm
                    - ptTrapSeverity:      2  major
                    - ptTrapProbableCause: 11 quality of service
                    - ptTrapClearType:     1  fmic
             "
    ::= { ptiSegway 0 6256 }

ptApplicationSlotApplicationStarted NOTIFICATION-TYPE
    OBJECTS         { ptTrapType, ptTrapSequenceNumber, ptTrapSeverity, 
                      ptTrapProbableCause, ptTrapClearType, 
                      ptTrapDateAndTime, ptTrapItemOID, 
                      ptApplicationSlotNumber, 
                      ptApplicationApplicationName, 
                      ptApplicationApplicationState }
    STATUS          current
    DESCRIPTION     
            "The named application is running.
             
             Cause  - Application in running.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6257 }

ptSlotMonitorSlotTIPCAuditReport NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "A TIPC discrepancy has been detected.  Please review
             /tmp/TIPC_Audit.txt and transmit it to SS7 Support if
             there appears to be any system instability.
             
             Cause  - TIPC audit suggest there may be internal
                      communications problems.
             Action - Verify system stability.
             Freq   - Infrequent.
             
             References
             
                    - ptOriginatingOID:    DYNAMIC Slot
                    - ptTrapType:          4  equipment alarm
                    - ptTrapSeverity:      2  major
                    - ptTrapProbableCause: 11 quality of service
                    - ptTrapClearType:     1  fmic
             "
    ::= { ptiSegway 0 6258 }

ptSlotMonitorSlotTIPCAuditClear NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "A TIPC discrepancy state has been cleared.  A subsequent
             audit has not detected anything wrong.
             
             Cause  - TIPC audit detected no problems.
             Action - None
             Freq   - Infrequent.
             
             References
             
                    - ptOriginatingOID:    DYNAMIC Slot
                    - ptTrapType:          4  equipment alarm
                    - ptTrapSeverity:      5  clear
                    - ptTrapProbableCause: 11 quality of service
                    - ptTrapClearType:     1  fmic
             "
    ::= { ptiSegway 0 6259 }

ptSlotSlotCPUMemUsageCritical NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has dropped below the Free Memory Threshold configured
             in the Web UI.  The slot number shown in this trap indicates the origin of
             the alarm.  This condition can lead the kernel to indiscriminately terminate
             processes causing outage.  A process listing and top output can identify the
             offending process.
             
             Cause  - Memory usage it too high
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     1 fmic
             "
    ::= { ptiSegway 0 6260 }

ptSlotSlotCPUMemUsageCriticalAbated NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability has returned to reasonable levels.
             
             Cause  - Applications have freed memory.
             Action - None.
             Freq   - Irregular.
             
             References
             
                    - ptOriginatingOID:    DYNAMIC Slot
                    - ptTrapType:          4 equipment alarm
                    - ptTrapSeverity:      5 clear
                    - ptTrapProbableCause: 6 communication subsystem
                    - ptTrapClearType:     0 oic
             "
    ::= { ptiSegway 0 6261 }

ptSlotSlotCPUMemUsageCriticalPersists NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPUMemoryUsage }
    STATUS          current
    DESCRIPTION     
            "Memory availability continues to be lower than the Free Memory Threshold
             configured in the Web UI.  The slot number shown in this trap indicates
             the origin of the alarm.
             
             Cause  - Memory usage it too high
             Action - Identify applications consuming memory
             Freq   - Irregular
             
             References
             
                    - ptOriginatingOID:    DYNAMIC Slot
                    - ptTrapType:          4 equipment alarm
                    - ptTrapSeverity:      1 critical
                    - ptTrapProbableCause: 6 communication subsystem
                    - ptTrapClearType:     0 oic
             "
    ::= { ptiSegway 0 6262 }

ptSlotSlotCPULoadUsageCritical NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPULoadUsage }
    STATUS          current
    DESCRIPTION     
            "CPU load average is high. The slot number indicated in this trap 
             indicates the origin of the alarm. A process listing and top 
             output can identify the offending process(es).
             
             Cause  - Load Average above threshold
             Action - Identify applications running high on CPU
             Freq   - Irregular    
             "
    ::= { ptiSegway 0 6263 }

ptSlotSlotCPULoadUsageCriticalAbated NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotCPULoadUsage }
    STATUS          current
    DESCRIPTION     
            "CPU load average has returned to reasonable levels.
             
             Cause  - Load Average below threshold.
             Action - None.
             Freq   - Irregular.                 
             "
    ::= { ptiSegway 0 6264 }

ptSlotMonitorSlotBondingARPMonitorFault NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "Bonding driver link monitoring has detected an ARP
             failure.  One or more of the Ethernet devices may have
             failed.
             
             Cause  - Link monitoring has lost communication with
                      the far end.
             Action - Verify Ethernet connections of the bonded
                      network interface.
             Freq   - Infrequent.
             
             References
             
                    - ptOriginatingOID:    DYNAMIC Slot
                    - ptTrapType:          4  equipment alarm
                    - ptTrapSeverity:      2  major
                    - ptTrapProbableCause: 11 quality of service
                    - ptTrapClearType:     1  fmic
             "
    ::= { ptiSegway 0 6266 }

ptSlotMonitorSlotBondingARPMonitorClear NOTIFICATION-TYPE
    OBJECTS         { ptTrapType, ptTrapSequenceNumber, ptTrapSeverity, 
                      ptTrapProbableCause, ptTrapClearType, 
                      ptTrapDateAndTime, ptTrapItemOID, 
                      ptSlotMonitorHostname }
    STATUS          current
    DESCRIPTION     
            "Bonding driver link monitoring has established ARP
             communication with the far end.
             
             Cause  - Link monitoring has established communication
                      with the far end.
             Action - None
             Freq   - Infrequent.
             
             References
             
                    - ptOriginatingOID:    DYNAMIC Slot
                    - ptTrapType:          4  equipment alarm
                    - ptTrapSeverity:      5  clear
                    - ptTrapProbableCause: 11 quality of service
                    - ptTrapClearType:     1  fmic
             "
    ::= { ptiSegway 0 6267 }

ptSlotSlotIsmEtcPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /etc partition usage is above the alarm threshold defined in 
             disk_space_quota.  The slot number indicated in this
             trap indicates the origin of the alarm.
             
             Cause  - ISM /etc partition usage above threshold
             Action - Identify applications running high on disk space
             Freq   - Irregular
             "
    ::= { ptiSegway 0 6268 }

ptSlotSlotIsmEtcPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "ISM /etc partition usage has returned to acceptable levels.
             
             Cause  - ISM /etc partition usage below threshold.
             Action - None.
             Freq   - Irregular.
             "
    ::= { ptiSegway 0 6269 }

ptSlotSlotBackupSpaceUsageCritical NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotBackupSpaceUsage }
    STATUS          current
    DESCRIPTION     
            "HDD space for backups is dangerously low.  The slot number indicated in this
             trap indicates the origin of the alarm.
             
             Cause  - Backups using up too much HDD space
             Action - Delete some old Backups 
             Freq   - Irregular
             "
    ::= { ptiSegway 0 6270 }

ptSlotSlotBackupSpaceUsageCriticalAbated NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotBackupSpaceUsage }
    STATUS          current
    DESCRIPTION     
            "HDD space for backups has returned to reasonable levels.
             
             Cause  - HDD space for backups has been restored. 
             Action - None.
             Freq   - Irregular.
             "
    ::= { ptiSegway 0 6271 }

ptSlotSlotRootDiskPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "CPU root partition usage is above the alarm threshold defined in 
             disk_space_quota.  The slot number indicated in this
             trap indicates the origin of the alarm.
             
             Cause  - root partition usage above threshold
             Action - Identify applications running high on disk space
             Freq   - Irregular
             "
    ::= { ptiSegway 0 6272 }

ptSlotSlotRootDiskPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "CPU root partition usage has returned to acceptable levels.
             
             Cause  - root partition usage below threshold.
             Action - None.
             Freq   - Irregular.
             "
    ::= { ptiSegway 0 6273 }

ptSlotSlotTmpDiskPartitionThresholdExceeded NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "CPU /tmp partition usage is above the alarm threshold defined in 
             disk_space_quota.  The slot number indicated in this
             trap indicates the origin of the alarm.  
             
             Cause  - /tmp partition usage above threshold
             Action - Identify applications running high on disk space
             Freq   - Irregular
             "
    ::= { ptiSegway 0 6274 }

ptSlotSlotTmpDiskPartitionThresholdCleared NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus }
    STATUS          current
    DESCRIPTION     
            "CPU /tmp partition usage has returned to acceptable levels.
             
             Cause  - /tmp partition usage below threshold.
             Action - None.
             Freq   - Irregular.
             "
    ::= { ptiSegway 0 6275 }

ptSlotSlotOmsSpaceUsageCritical NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotOMsSpaceUsage }
    STATUS          current
    DESCRIPTION     
            "HDD space for SP2K Specific OMs is dangerously low.  The slot number indicated in this
             trap indicates the origin of the alarm.
             
             Cause  - SP2K Specific OMs using up too much HDD space
             Action - Delete some old SP2K Specific OMs 
             Freq   - Irregular
             "
    ::= { ptiSegway 0 6276 }

ptSlotSlotOmsSpaceUsageCriticalAbated NOTIFICATION-TYPE
    OBJECTS         { ptTrapType, ptTrapSequenceNumber, ptTrapSeverity, 
                      ptTrapProbableCause, ptTrapClearType, 
                      ptTrapDateAndTime, ptTrapItemOID, ptSlotSlotNumber, 
                      ptSlotSlotStatus, ptSlotOMsSpaceUsage }
    STATUS          current
    DESCRIPTION     
            "HDD space for SP2K Specific OMs has returned to reasonable levels.
             
             Cause  - HDD space for SP2K Specific OMs has been restored. 
             Action - None.
             Freq   - Irregular.
             "
    ::= { ptiSegway 0 6277 }

ptSlotSlotBackupSftpUploadFailure NOTIFICATION-TYPE
    OBJECTS         { ptTrapType, ptTrapSequenceNumber, ptTrapSeverity, 
                      ptTrapProbableCause, ptTrapClearType, 
                      ptTrapDateAndTime, ptTrapItemOID, 
                      ptSlotLastFailedSFTPBackupDestIP, 
                      ptSlotLastFailedSFTPBackupDestUserID, 
                      ptSlotLastFailedSFTPBackupDestDir }
    STATUS          current
    DESCRIPTION     
            "A backup to an SFTP destination could not be completed.
             
             Cause  - Backup could not be transferred to remote SFTP destination
             Action - Check that SFTP keys have been exchanged, remote SFTP node state
             Freq   - Irregular
             "
    ::= { ptiSegway 0 6278 }

ptSlotSlotBackupSftpUploadFailureCleared NOTIFICATION-TYPE
    OBJECTS         { ptTrapType, ptTrapSequenceNumber, ptTrapSeverity, 
                      ptTrapProbableCause, ptTrapClearType, 
                      ptTrapDateAndTime, ptTrapItemOID, 
                      ptSlotLastFailedSFTPBackupDestIP, 
                      ptSlotLastFailedSFTPBackupDestUserID, 
                      ptSlotLastFailedSFTPBackupDestDir }
    STATUS          current
    DESCRIPTION     
            "A backup to SFTP destination has now been successfully completed.
             
             Cause  - Backup successfully transferred to remote SFTP destination
             Action - None.
             Freq   - Irregular
             "
    ::= { ptiSegway 0 6279 }

ptSwitchSwitchUnreachable NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "A switch card has stopped responding.  The card may be physically extracted
             or there has been a software/hardware malfunction.
             
             Other cards in the chassis cannot communicate on the fabric that this card was managing.
             
             This alarm will be raised on upgrade due to normal operation.
             
             Cause  - Switch card non-responsive.
             Action - Check the card is inserted and operational.
             Freq   - Infrequent.
             
             References
             
                    - ptOriginatingOID:    DYNAMIC Slot
                    - ptTrapType:          4  equipment alarm
                    - ptTrapSeverity:      1  critical
                    - ptTrapProbableCause: 11 quality of service
                    - ptTrapClearType:     1  fmic
             "
    ::= { ptiSegway 0 6280 }

ptSwitchSwitchReachable NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "A switch card has recovered and is responding. 
             The associated fabric is now operational.
             
             Cause  - Switch card is running.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6281 }

ptExternalPortSwitchPortDown NOTIFICATION-TYPE
    OBJECTS         { ptTrapType, ptTrapSequenceNumber, ptTrapSeverity, 
                      ptTrapProbableCause, ptTrapClearType, 
                      ptTrapDateAndTime, ptTrapItemOID, 
                      ptSWMExternalPortSlotNumber, 
                      ptSWMExternalPortPortNumber, 
                      ptSWMExternalPortState, ptSWMExternalPortPortName }
    STATUS          current
    DESCRIPTION     
            "A switch external port is down.
             
             Cause  - External port non responsive.
             Action - Check the cable connected to the port and the remote end of the cable.
             Freq   - Infrequent.
             
             References
             
                    - ptOriginatingOID:    DYNAMIC Slot
                    - ptTrapType:          4  equipment alarm
                    - ptTrapSeverity:      1  critical
                    - ptTrapProbableCause: 11 quality of service
                    - ptTrapClearType:     1  fmic
             "
    ::= { ptiSegway 0 6282 }

ptExternalPortSwitchPortUp NOTIFICATION-TYPE
    OBJECTS         { ptTrapType, ptTrapSequenceNumber, ptTrapSeverity, 
                      ptTrapProbableCause, ptTrapClearType, 
                      ptTrapDateAndTime, ptTrapItemOID, 
                      ptSWMExternalPortSlotNumber, 
                      ptSWMExternalPortPortNumber, 
                      ptSWMExternalPortState, ptSWMExternalPortPortName }
    STATUS          current
    DESCRIPTION     
            "A switch external port is up. 
             
             Cause  - External port now responsive.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6283 }

ptSwitchTopologyChange NOTIFICATION-TYPE
    OBJECTS         { ptTrapType, ptTrapSequenceNumber, ptTrapSeverity, 
                      ptTrapProbableCause, ptTrapClearType, 
                      ptTrapDateAndTime, ptTrapItemOID, 
                      ptSWMSwitchSlotNumber }
    STATUS          current
    DESCRIPTION     
            "A rapid spanning tree topology change has been issued. 
             
             Cause  - Change in the IP network.
             Action - None.
             Freq   - Infrequent.
             
             References
             
                    - ptOriginatingOID:    DYNAMIC Application
                    - ptTrapType:          4  equipment alarm
                    - ptTrapSeverity:      4  Warning
                    - ptTrapProbableCause: 11 quality of service
                    - ptTrapClearType:     0  oic
             "
    ::= { ptiSegway 0 6285 }

ptSwitchNewRoot NOTIFICATION-TYPE
    OBJECTS         { ptTrapType, ptTrapSequenceNumber, ptTrapSeverity, 
                      ptTrapProbableCause, ptTrapClearType, 
                      ptTrapDateAndTime, ptTrapItemOID, 
                      ptSWMSwitchSlotNumber }
    STATUS          current
    DESCRIPTION     
            "A rapid spanning tree selected a new root in the network. 
             
             Cause  - Change in the IP network.
             Action - None.
             Freq   - Infrequent.
             
             References
             
                    - ptOriginatingOID:    DYNAMIC Application
                    - ptTrapType:          4  equipment alarm
                    - ptTrapSeverity:      4  warning
                    - ptTrapProbableCause: 11 quality of service
                    - ptTrapClearType:     2  oic
             "
    ::= { ptiSegway 0 6286 }

ptSwitchColdStart NOTIFICATION-TYPE
    OBJECTS         { ptTrapType, ptTrapSequenceNumber, ptTrapSeverity, 
                      ptTrapProbableCause, ptTrapClearType, 
                      ptTrapDateAndTime, ptTrapItemOID, 
                      ptSWMSwitchSlotNumber }
    STATUS          current
    DESCRIPTION     
            "A switch card has recovered and issued a cold start. 
             The associated fabric is now operational.
             
             Cause  - Switch card is running.
             Action - None.
             Freq   - Infrequent.
             
             References
             
                    - ptOriginatingOID:    DYNAMIC Application
                    - ptTrapType:          4  equipment alarm
                    - ptTrapSeverity:      4  warning
                    - ptTrapProbableCause: 11 quality of service
                    - ptTrapClearType:     2  oic
             "
    ::= { ptiSegway 0 6287 }

ptSwitchWarmStart NOTIFICATION-TYPE
    OBJECTS         { ptTrapType, ptTrapSequenceNumber, ptTrapSeverity, 
                      ptTrapProbableCause, ptTrapClearType, 
                      ptTrapDateAndTime, ptTrapItemOID, 
                      ptSWMSwitchSlotNumber }
    STATUS          current
    DESCRIPTION     
            "A switch card has recovered and issued a warm start. 
             The associated fabric is now operational.
             
             Cause  - Switch card is running.
             Action - None.
             Freq   - Infrequent.
             
             References
             
                    - ptOriginatingOID:    DYNAMIC Application
                    - ptTrapType:          4  equipment alarm
                    - ptTrapSeverity:      4  warning
                    - ptTrapProbableCause: 11 quality of service
                    - ptTrapClearType:     0  oic
             "
    ::= { ptiSegway 0 6288 }

ptSwitchSwitchSyncDown NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "The sync interface to this switch is down. This interface is provided by
             a cable connected between the RMCs of the two switch cards in each chassis.
             Check that the state of the switch cards are both AVAILABLE. If so, check
             the state of the cable between the switches.
             
             This alarm will be raised on upgrade due to normal operation.
             
             Cause  - Switch Sync interface is non-responsive.
             Action - Check the card and cable are inserted and operational.
             Freq   - Infrequent.
             
             References
             
                    - ptOriginatingOID:    DYNAMIC Slot
                    - ptTrapType:          4  equipment alarm
                    - ptTrapSeverity:      2  major
                    - ptTrapProbableCause: 11 quality of service
                    - ptTrapClearType:     1  fmic
             "
    ::= { ptiSegway 0 6290 }

ptSwitchSwitchSyncUp NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "A sync interface has recovered and is operational. 
             
             Cause  - Sync interface is connected and is operational.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6291 }

ptSwitchSwitchIntegrityFailed NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "The integrity status of this switch is failed. This status is
             determined by on-board background tests performed continually.
             
             Cause  - Switch Integrity has been reported as Failed.
             Action - Check log files for messages from this card.
             Freq   - Infrequent.
             
             References
             
                    - ptOriginatingOID:    DYNAMIC Slot
                    - ptTrapType:          4  equipment alarm
                    - ptTrapSeverity:      2  major
                    - ptTrapProbableCause: 11 quality of service
                    - ptTrapClearType:     1  fmic
             "
    ::= { ptiSegway 0 6292 }

ptSwitchSwitchIntegrityPassed NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "The integrity status of this switch is passed. This status is
             determined by on-board background tests performed continually.
             
             Cause  - Switch Integrity has been reported as Passed.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6293 }

ptSwitchMonitorSwitchmonDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 6294 }

ptSwitchMonitorSwitchmonDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 6295 }

ptSlotSlotTIPCBearerLoss NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "At least one required TIPC is unavailable 
             
             Cause  - TIPC is reporting an unavailable bearer.
             
             Possible Actions - Invetigate the systems TIPC configuration."
    ::= { ptiSegway 0 6296 }

ptSlotSlotTIPCBearerLossClear NOTIFICATION-TYPE
    OBJECTS         { ptTrapType, ptTrapSequenceNumber, ptTrapSeverity, 
                      ptTrapProbableCause, ptTrapClearType, 
                      ptTrapDateAndTime, ptTrapItemOID, ptSlotSlotNumber }
    STATUS          current
    DESCRIPTION     
            "All TIPC Bearers are available"
    ::= { ptiSegway 0 6297 }

ptSwitchFabricDown NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "The fabric associated to this switch card is NOT operational.
             Communication through this fabric has failed for all slots.   
             The switch card (MCH) might be physically extracted
             or there has been a software/hardware malfunction.
             
             Other cards in the chassis cannot communicate on this fabric.
             
             This alarm will be raised on upgrade due to normal operation.
             
             Cause  - Fabric is NOT operational.
             Action - Check the card is inserted and operational.
             Freq   - Infrequent.
             
             References
             
                    - ptOriginatingOID:    DYNAMIC Slot
                    - ptTrapType:          4  equipment alarm
                    - ptTrapSeverity:      1  critical
                    - ptTrapProbableCause: 11 quality of service
                    - ptTrapClearType:     1  fmic
             "
    ::= { ptiSegway 0 6298 }

ptSwitchFabricUp NOTIFICATION-TYPE
    OBJECTS         { ptTrapType, ptTrapSequenceNumber, ptTrapSeverity, 
                      ptTrapProbableCause, ptTrapClearType, 
                      ptTrapDateAndTime, ptTrapItemOID, 
                      ptSWMSwitchSlotNumber, ptSWMSwitchSlotStatus }
    STATUS          current
    DESCRIPTION     
            "The fabric associated to this switch card is now operational.
             
             Cause  - Fabric is operational.
             Action - None.
             Freq   - Infrequent.
             
             References
             
                    - ptOriginatingOID:    DYNAMIC Application
                    - ptTrapType:          4  equipment alarm
                    - ptTrapSeverity:      5  clear
                    - ptTrapProbableCause: 11 quality of service
                    - ptTrapClearType:     1  fmic
             "
    ::= { ptiSegway 0 6299 }

ptHardwareMonitorHwMonShutdown NOTIFICATION-TYPE
    OBJECTS         { ptTrapType, ptTrapSequenceNumber, ptTrapSeverity, 
                      ptTrapProbableCause, ptTrapClearType, 
                      ptTrapDateAndTime, ptTrapItemOID, 
                      pthwmonHardwareMonitorStatus }
    STATUS          current
    DESCRIPTION     
            "Hardware Monitor stopped.
             
             Cause  - Hardware Monitor stopped
             Action - Check process listing
             Freq   - Infrequent
             
             References
                 - ptOriginatingOID:    DYNAMIC ptHwMon
                 - ptTrapType:          4 equipment alarm
                 - ptTrapSeverity:      2 major
                 - ptTrapProbableCause: 7 configuration error
                 - ptTrapClearType:     1 fmic
             "
    ::= { ptiSegway 0 6300 }

ptHardwareMonitorHwMonStartup NOTIFICATION-TYPE
    OBJECTS         { ptTrapType, ptTrapSequenceNumber, ptTrapSeverity, 
                      ptTrapProbableCause, ptTrapClearType, 
                      ptTrapDateAndTime, ptTrapItemOID, 
                      pthwmonHardwareMonitorStatus }
    STATUS          current
    DESCRIPTION     
            "Hardware Monitor started.
             
             Cause  - Hardware Monitor started
             Action - None
             Freq   - Infrequent
             
             References
                 - ptOriginatingOID:    DYNAMIC ptHwMon
                 - ptTrapType:          4 equipment alarm
                 - ptTrapSeverity:      5 clear
                 - ptTrapProbableCause: 7 configuration error
                 - ptTrapClearType:     1 fmic
             "
    ::= { ptiSegway 0 6301 }

ptHardwareMonitorHwMonInitSlow NOTIFICATION-TYPE
    OBJECTS         { ptTrapType, ptTrapSequenceNumber, ptTrapSeverity, 
                      ptTrapProbableCause, ptTrapClearType, 
                      ptTrapDateAndTime, ptTrapItemOID, 
                      pthwmonHardwareMonitorStatus }
    STATUS          current
    DESCRIPTION     
            "Hardware Monitor initialization slow.
             The initialization process is taking longer than expected.
             The portald might still be busy populating its database.
             
             Cause  - Hardware Monitor Initialization Slow
             Action - Check portald process listing
             Freq   - Infrequent
             "
    ::= { ptiSegway 0 6302 }

ptHardwareMonitorHwMonInitCompleted NOTIFICATION-TYPE
    OBJECTS         { ptTrapType, ptTrapSequenceNumber, ptTrapSeverity, 
                      ptTrapProbableCause, ptTrapClearType, 
                      ptTrapDateAndTime, ptTrapItemOID, 
                      pthwmonHardwareMonitorStatus }
    STATUS          current
    DESCRIPTION     
            "Hardware Monitor initialization completed.
             
             Cause  - Hardware Monitor initialization completed
             Action - None
             Freq   - Infrequent
             "
    ::= { ptiSegway 0 6303 }

ptHardwareMonitorHwMonDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
                The user should perform the 'Restore Debug Defaults' action to reset all
                debug attributes to their default values."
    ::= { ptiSegway 0 6304 }

ptHardwareMonitorHwMonDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 6305 }

ptSlotSlotExtracted NOTIFICATION-TYPE
    OBJECTS         { ptTrapType, ptTrapSequenceNumber, ptTrapSeverity, 
                      ptTrapProbableCause, ptTrapClearType, 
                      ptTrapDateAndTime, ptTrapItemOID, 
                      pthwmonSlotSlotNumber }
    STATUS          current
    DESCRIPTION     
            "Slot extracted/deactivated.
             
             Cause  - Slot extracted
             Action - Check hardware configuration
             Freq   - Infrequent
             
             References
                 - ptOriginatingOID:    DYNAMIC ptHwMon
                 - ptTrapType:          4 equipment alarm
                 - ptTrapSeverity:      2 major
                 - ptTrapProbableCause: 7 configuration error
                 - ptTrapClearType:     1 fmic
             "
    ::= { ptiSegway 0 6310 }

ptSlotSlotInserted NOTIFICATION-TYPE
    OBJECTS         { ptTrapType, ptTrapSequenceNumber, ptTrapSeverity, 
                      ptTrapProbableCause, ptTrapClearType, 
                      ptTrapDateAndTime, ptTrapItemOID, 
                      pthwmonSlotSlotNumber }
    STATUS          current
    DESCRIPTION     
            "Slot inserted/activated.
             
             Cause  - Slot inserted
             Action - None
             Freq   - Infrequent
             
             References
                 - ptOriginatingOID:    DYNAMIC ptHwMon
                 - ptTrapType:          4 equipment alarm
                 - ptTrapSeverity:      5 clear
                 - ptTrapProbableCause: 7 configuration error
                 - ptTrapClearType:     1 fmic
             "
    ::= { ptiSegway 0 6311 }

ptDiscreteSensorPowerFaultAssert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor power fault alarm was asserted
             
             Cause  - A discrete sensor detects a power fault condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6320 }

ptDiscreteSensorPowerFaultDeassert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor power fault alarm was deasserted
             
             Cause  - A discrete sensor no longer detects a power fault condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6321 }

ptDiscreteSensorCpuErrorAssert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor CPU error alarm was asserted
             
             Cause  - A discrete sensor detects a CPU error condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6322 }

ptDiscreteSensorCpuErrorDeassert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor CPU error alarm was deasserted
             
             Cause  - A discrete sensor no longer detects a CPU error condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6323 }

ptDiscreteSensorThermTripAssert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor therm trip alarm was asserted
             
             Cause  - A discrete sensor detects a therm trip condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6324 }

ptDiscreteSensorThermTripDeassert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor therm trip alarm was deasserted
             
             Cause  - A discrete sensor no longer detects a therm trip condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6325 }

ptDiscreteSensorPsFaultAssert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor power supply fault alarm was asserted
             
             Cause  - A discrete sensor detects a power supply fault condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6326 }

ptDiscreteSensorPsFaultDeassert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "A discrete sensor power supply fault alarm was deasserted
             
             Cause  - A discrete sensor no longer detects a power supply fault condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6327 }

ptDiscreteSensorSysComponentExtracted NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "System Component extracted/deactivated.
             
             Cause  - System component extracted
             Action - Check hardware configuration
             Freq   - Infrequent
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6328 }

ptDiscreteSensorSysComponentInserted NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "System Component inserted/activated.
             
             Cause  - System component inserted
             Action - None
             Freq   - Infrequent
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6329 }

ptDiscreteSensorSpiFaultAssert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "SPIbus test Failed
             
             Cause  - SPIbus Hardware fault detected on slot 
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6330 }

ptDiscreteSensorSpiFaultDeassert NOTIFICATION-TYPE
    OBJECTS         { ptTrapType, ptTrapSequenceNumber, ptTrapSeverity, 
                      ptTrapProbableCause, ptTrapClearType, 
                      ptTrapDateAndTime, ptTrapItemOID, 
                      pthwmonDiscreteSensorName, 
                      pthwmonDiscreteSensorSlot, 
                      pthwmonDiscreteSensorPortalID, 
                      pthwmonDiscreteSensorIPMINumber }
    STATUS          current
    DESCRIPTION     
            "SPIbus test Passed
             
             Cause  - SPIbus Hardware is operational on slot
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6331 }

ptThresholdSensorUpperCriticalAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper critical alarm was asserted
             
             Cause  - A threshold sensor detects an upper critical condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6340 }

ptThresholdSensorUpperCriticalDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper critical alarm was deasserted
             
             Cause  - A threshold sensor no longer detects an upper critical condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6341 }

ptThresholdSensorUpperMajorAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper major alarm was asserted
             
             Cause  - A threshold sensor detects an upper major condition
             Action - Verify sensor
             Freq   - Unexpected
             
             References
                 - ptOriginatingOID:    DYNAMIC ptSensor
                 - ptTrapType:          4 equipment alarm
                 - ptTrapSeverity:      2 major
                 - ptTrapProbableCause: 7 configuration error
                 - ptTrapClearType:     1 fmic
             "
    ::= { ptiSegway 0 6342 }

ptThresholdSensorUpperMajorDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper major alarm was deasserted
             
             Cause  - A threshold sensor no longer detects an upper major condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6343 }

ptThresholdSensorUpperMinorAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper minor alarm was asserted
             
             Cause  - A threshold sensor detects an upper minor condition
             Action - Verify sensor
             Freq   - Unexpected
             
             References
                 - ptOriginatingOID:    DYNAMIC ptSensor
                 - ptTrapType:          4 equipment alarm
                 - ptTrapSeverity:      3 minor
                 - ptTrapProbableCause: 7 configuration error
                 - ptTrapClearType:     1 fmic
             "
    ::= { ptiSegway 0 6344 }

ptThresholdSensorUpperMinorDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor upper minor alarm was deasserted
             
             Cause  - A threshold sensor no longer detects an upper minor condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6345 }

ptThresholdSensorLowerMinorAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower minor alarm was asserted
             
             Cause  - A threshold sensor detects a lower minor condition
             Action - Verify sensor
             Freq   - Unexpected
             
             References
                 - ptOriginatingOID:    DYNAMIC ptSensor
                 - ptTrapType:          4 equipment alarm
                 - ptTrapSeverity:      3 minor
                 - ptTrapProbableCause: 7 configuration error
                 - ptTrapClearType:     1 fmic
             "
    ::= { ptiSegway 0 6346 }

ptThresholdSensorLowerMinorDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower minor alarm was deasserted
             
             Cause  - A threshold sensor no longer detects a lower minor condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6347 }

ptThresholdSensorLowerMajorAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower major alarm was asserted
             
             Cause  - A threshold sensor detects a lower major condition
             Action - Verify sensor
             Freq   - Unexpected
             
             References
                 - ptOriginatingOID:    DYNAMIC ptSensor
                 - ptTrapType:          4 equipment alarm
                 - ptTrapSeverity:      2 major
                 - ptTrapProbableCause: 7 configuration error
                 - ptTrapClearType:     1 fmic
             "
    ::= { ptiSegway 0 6348 }

ptThresholdSensorLowerMajorDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower major alarm was deasserted
             
             Cause  - A threshold sensor no longer detects a lower major condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6349 }

ptThresholdSensorLowerCriticalAssert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower critical alarm was asserted
             
             Cause  - A threshold sensor detects a lower critical condition
             Action - Verify sensor
             Freq   - Unexpected
             
             References
                 - ptOriginatingOID:    DYNAMIC ptSensor
                 - ptTrapType:          4 equipment alarm
                 - ptTrapSeverity:      1 critical
                 - ptTrapProbableCause: 7 configuration error
                 - ptTrapClearType:     1 fmic
             "
    ::= { ptiSegway 0 6350 }

ptThresholdSensorLowerCriticalDeassert NOTIFICATION-TYPE
    OBJECTS         { ptTrapType, ptTrapSequenceNumber, ptTrapSeverity, 
                      ptTrapProbableCause, ptTrapClearType, 
                      ptTrapDateAndTime, ptTrapItemOID, 
                      pthwmonThresholdSensorName, 
                      pthwmonThresholdSensorSlot, 
                      pthwmonThresholdSensorPortalID, 
                      pthwmonThresholdSensorIPMINumber }
    STATUS          current
    DESCRIPTION     
            "A threshold sensor lower critical alarm was deasserted
             
             Cause  - A threshold sensor no longer detects a lower critical condition
             Action - None
             Freq   - Unexpected
             
             References
                 - ptOriginatingOID:    DYNAMIC ptSensor
                 - ptTrapType:          4 equipment alarm
                 - ptTrapSeverity:      5 clear
                 - ptTrapProbableCause: 7 configuration error
                 - ptTrapClearType:     1 fmic
             "
    ::= { ptiSegway 0 6351 }

ptEventAlarmAckStateUpdate NOTIFICATION-TYPE
    OBJECTS         { ptTrapType, ptTrapSequenceNumber, ptTrapSeverity, 
                      ptTrapProbableCause, ptTrapClearType, 
                      ptTrapDateAndTime, ptTrapItemOID, 
                      ptLIBEVEventEventName, ptLIBEVEventInstanceId, 
                      ptLIBEVEventAckBy }
    STATUS          current
    DESCRIPTION     
            "This trap indicates the event object has changed state."
    ::= { ptiSegway 0 6665 }

ptEventAlarmCommentUpdate NOTIFICATION-TYPE
    OBJECTS         { ptTrapType, ptTrapSequenceNumber, ptTrapSeverity, 
                      ptTrapProbableCause, ptTrapClearType, 
                      ptTrapDateAndTime, ptTrapItemOID, 
                      ptLIBEVEventEventName, ptLIBEVEventInstanceId, 
                      ptLIBEVEventComment }
    STATUS          current
    DESCRIPTION     
            "This trap indicates the event object has changed state."
    ::= { ptiSegway 0 6666 }

ptLSLinkSs7L3LinkDeactivated NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been deactivated.
             Causes ,Corrective actions and Frequency:  
               1) ptSpecificTrapCause = operatorDeactivation 
                  Cause  - Operator deactivates link.
                  Action - Operator can activate the link again.
                  Freq   - Operator dependant. 
                   
               2) ptSpecificTrapCause = timerT17Expiry
                  Cause  - Event appears between each attempt to perform an initial 
                           alignment procedure. After an unsuccessful attempt, a delay
                           T17 expires before the next attempt is initiated.
                  Action - Operator can activate the link.  
                  Freq   - T19 expiry , T19 can take a value between 800 - 1500 ms
             
               3) ptSpecificTrapCause = unknownCause
             
             References
               1) Table 1 Q.752, SL Failure
               2) Q.704 (07/96) Section 12.2 
                             
               ptOriginatingOID:    DYNAMIC ptLink
               ptTrapType:          2 communicationAlarm
               ptTrapSeverity:      3 minor
               ptTrapProbableCause: 29 Loss of signal   
               ptTrapClearType:     1 fmic
             "
    ::= { ptiSegway 0 7103 }

ptLSLinkSs7L3LinkActivated NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been activated
             either by the operator or as a result of a successful restoration 
             which was initiated upon detection of an inactive link.
             This trap could also be generated at restart without a previous
             corresponding trap 201.
             
             References
               1)  Q.752, SL Restoration
               2)  Q.704, (07/96) Section 12.2
               
               ptOriginatingOID:    DYNAMIC ptLink
               ptTrapType:          2 communicationAlarm
               ptTrapSeverity:      5 cleared
               ptTrapProbableCause: 29 Loss of signal 
               ptTrapClearType:     1 fmic              
             "
    ::= { ptiSegway 0 7104 }

ptLSLinkSs7L3LinkLocalInhibited NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been inhibited 
             by operator at the local node.
               Cause  - Operator inhibits the link.
               Action - Operator can uninhibit the link.
               Freq   - Operator dependant. 
             
             References
               1) Table 2 Q.752, Start of local inhibition
               2) Q.704 , (07/96) Section 10       
             
               ptOriginatingOID:    DYNAMIC ptLink
               ptTrapType:          11 qualityofserviceAlarm
               ptTrapSeverity:      4 warning
               ptTrapProbableCause: 43 Resource at or near capacity   
               ptTrapClearType:     1 fmic
             "
    ::= { ptiSegway 0 7105 }

ptLSLinkSs7L3LinkLocalUninhibited NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been uninhibited at the 
             local node by operator.
             
             References
               1) Table 2 Q.752, End of local inhibition
               2) Q.704 , (07/96) Section 10       
             
               ptOriginatingOID:    DYNAMIC ptLink
               ptTrapType:          11 qualityofserviceAlarm
               ptTrapSeverity:      5 cleared
               ptTrapProbableCause: 43 Resource at or near capacity
               ptTrapClearType:     1 fmic     
             "
    ::= { ptiSegway 0 7106 }

ptLSLinkSs7L3LinkRemoteInhibited NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been inhibited at a 
             remote node.
               Cause  - Operator has inhibited remote end of the link.
               Action - Link is inhibited until the operator uninhibits the 
                        remote end of the link.
               Freq   - Operator dependant. 
             
             References
               1) Table 2 Q.752, Start of remote inhibition
               2) Q.704 , (07/96) Section 10       
             
               ptOriginatingOID:    DYNAMIC ptLink
             	 		 		 		      ptTrapType:          11 qualityofserviceAlarm 
               ptTrapSeverity:      4 warning
               ptTrapProbableCause: 43 Resource at or near capacity  
               ptTrapClearType:     1 fmic         
             "
    ::= { ptiSegway 0 7107 }

ptLSLinkSs7L3LinkRemoteUninhibited NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been uninhibited 
             at the remote end of a link. This can be requested by the operator
             or by signaling routing control function . Signaling routing 
             control will initiate signaling link uninhibit if an inhibited 
             link is found to be a member of a linkset in a route to a destination
             which has become inaccessible. 
             
             References
               1) Table 2 Q.752, End of remote inhibition
               2) Q.704 , (07/96) Section 10       
             
               ptOriginatingOID:    DYNAMIC ptLink
             	 		 		 		      ptTrapType:          11 qualityofserviceAlarm
               ptTrapSeverity:      5 cleared
               ptTrapProbableCause: 43 Resource at or near capacity  
               ptTrapClearType:     1 fmic             
             "
    ::= { ptiSegway 0 7108 }

ptLSLinkSs7L3LinkInhibitDenied NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that an attempt to inhibit a signaling link 
             has failed.
             This is a stateless trap (no alarm).
             
               Causes ,Corrective actions and Frequency: 
                 1) ptSpecificTrapCause = DPC not available 
                    Cause  - This trap occurs when a request to inhibit a link will
                             result in a destination becoming inaccessible and therefore
                             the request is denied.
                    Action - Operator will have to create another link 
                             to access the destination before attempting to inhibit this 
                             one.
                    Freq   - Depends on how many destinations have single links and how
                             often management wants to inhibit them. 
             
                 2) ptSpecificTrapCause = Negative ACK from remote end
                    Cause  - This trap occurs when a request to inhibit the link at the 
                             remote end of a link results in a destination becoming 
                             inaccessible. 
                    Action - Operator will have to wait until another link is available
                             to the destination before inhibiting this one.  
                    Freq   - Depends on how many destinations have single links and how
                             often management wants to inhibit them. 
             
                 3) ptSpecificTrapCause = UnknownCause 
             
               References
                 1) Q.704 , (07/96) Section 10.2       
             
             
                ptOriginatingOID:    DYNAMIC ptLink
                ptTrapType:          10 processingAlarm 
                ptTrapSeverity:      4 warning
                ptTrapProbableCause: 56 Underlying resource unavailable 
                ptTrapClearType:     2 oic       
             "
    ::= { ptiSegway 0 7109 }

ptLSLinkSs7L3LinkUninhibitDenied NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that an attempt to uninhibit a signaling link has failed.
             This is a stateless trap (no alarm).
             
                 Cause  - A request to uninhibit a link from the local node to a 
                          destination will fail if all the routes to the destination
                          are unavailable.
                 Action - Operator will have to wait until a route to the destination
                          becomes available in order that it can send an uninhibit link 
                          message. 
                 Freq   - Operator dependant.
             
               References
                 1) Q.704 , (07/96) Section 10.2       
             
                 ptOriginatingOID:    DYNAMIC ptLink
                 ptTrapType:          10 processingAlarm
                 ptTrapSeverity:      4 warning
                 ptTrapProbableCause: 56 Underlying resource unavailable
                 ptTrapClearType:     2 oic
             "
    ::= { ptiSegway 0 7111 }

ptLSLinkSs7L3LinkRemoteBlocked NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been blocked at a remote node.
             
             Cause  - Signaling link is blocked at the remote node of the link
                      by operator intervention or due to processor outage.
             Action - The link will be unblocked when the remote node of the 
                      link becomes unblocked. 
             Freq   - Operator dependant.
             
             References
             1) Table 2 Q.752 Start of Remote Processor Outage
             2) Q.704 Section 3.3.5      
             
             ptOriginatingOID:      DYNAMIC ptLink
             ptTrapType:            2 communicationAlarm
             ptTrapSeverity:        3 minor
             ptTrapProbableCause:   42 Remote node transmission error  
             ptTrapClearType:       1 fmic
             "
    ::= { ptiSegway 0 7113 }

ptLSLinkSs7L3LinkRemoteUnblocked NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been unblocked at a remote node.
             
             Causes ,Corrective actions and Frequency  
               1) ptSpecificTrapCause = linkDeactivated 
                  Cause  -  Unknown Cause
             
               2) ptSpecificTrapCause = unknownCause
             
             References
               1) Table 2 Q.752 Stop of Remote Processor Outage
               2) Q.704 Section 3.3.5      
             
               ptOriginatingOID:    DYNAMIC ptLink
               ptTrapType:          2 communicationAlarm
               ptTrapSeverity:      5 cleared
               ptTrapProbableCause: 42 Remote node transmission error  
               ptTrapClearType:     1 fmic
             "
    ::= { ptiSegway 0 7114 }

ptLSLinkSs7L3LinkLocalBlocked NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been blocked at the local node by 
             the operator.
             
                  Cause  - Operator blocks a link.
                  Action - Operator can unblock the link. 
                  Freq   - Operator dependant.
             
             
                References
                  1) Q.704 Section 3.2      
             
                  ptOriginatingOID:    DYNAMIC ptLink
                  ptTrapType:          10 processingAlarm
                  ptTrapSeverity:      3 minor
                  ptTrapProbableCause: 56 Underlying resource unavailable
                  ptTrapClearType:     1 fmic       
             "
    ::= { ptiSegway 0 7115 }

ptLSLinkSs7L3LinkLocalUnblocked NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link has been unblocked at the local node 
             by the operator.
             
                References
                 1) Q.704 Section 3.2      
             
                 ptOriginatingOID:    DYNAMIC ptLink
                 ptTrapType:          10 processingAlarm
                 ptTrapSeverity:      5 cleared
                 ptTrapProbableCause: 56 Underlying resource unavailable
                 ptTrapClearType:     1 fmic
             "
    ::= { ptiSegway 0 7116 }

ptLSLinkSs7L2LinkCongested NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkLinkName }
    STATUS          current
    DESCRIPTION     
            "This trap indicates that a signaling link is congested.
             
             Causes and Corrective Action  
               1) ptSpecificTrapCause = managementInitiated 
                  Cause  - Protocol manager detects the condition.  
             
               2) ptSpecificTrapCause = linkCongestion 
                  Cause  - Trap occurs when the thresholds for the number of MSUs
                           in the transmission or re-transmission buffer are exceeded.  
                  Action - Wait until the MSUs are sent .
             
             References
               1) Q.704 , Section 3.8.2 
             
               ptOriginatingOID:    DYNAMIC ptLink
               ptTrapType:          10 processingAlarm
               ptTrapSeverity:      3 minor
               ptTrapProbableCause: 49 Storage capacity problem
               ptTrapClearType:     1 fmic
             "
    ::= { ptiSegway 0 7119 }

ptLSLinkSs7L2LinkUncongested NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkLinkName }
    STATUS          current
    DESCRIPTION     
            "This trap indicates that a signaling link is no longer congested.
             
             Causes and Frequency  
               1) ptSpecificTrapCause = managementInitiated 
                  Cause  - Protocol Manager detects the condition
             
               2) ptSpecificTrapCause = linkUncongested 
                  Cause  - Trap occurs when the number of MSUs in the transmission
                           or re-transmission buffer goes from a value in excess of
                           the thresholds for congestion to a value which is less 
                           than the thresholds.   
                  Freq   - Dependant on throughput of MSUs .
             
             References
               1) Q.704 , Section 3.8.2 
             
               ptOriginatingOID:    DYNAMIC ptLink
               ptTrapType:          10 processingAlarm
               ptTrapSeverity:      5 cleared
               ptTrapProbableCause: 49 Storage capacity problem
               ptTrapClearType:     1 fmic       
             "
    ::= { ptiSegway 0 7120 }

ptLSLinkSs7L2LinkUnaligned NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL2State, ptMTPLSLinkLinkName }
    STATUS          current
    DESCRIPTION     
            "This trap indicates that a signaling link has lost alignment.
             
             Cause  - After a signaling link failure is detected , signaling link
                      initial alignment will take place. The Alignment procedure 
                      passes through a number of states and when the procedure 
                      enters the state not aligned this trap is sent.
             Action - If the initial alignment procedure does not work then the 
                      operator will have to intervene in order that the link 
                      alignment succeeds.
             Freq   - This trap will continue to appear each time the initial 
                      alignment procedure enters the state not aligned. This
                      may happen a number of times as the initial alignment 
                      procedure is repeated until alignment has been completed
                      successfully. 
                   
             References
               1) Q.703 , (07/96) Section 7.3 
             
             
               ptOriginatingOID:    DYNAMIC ptLink
               ptTrapType:          2 communicationAlarm
               ptTrapSeverity:      3 minor
               ptTrapProbableCause: 6 Communications subsystem error
               ptTrapClearType:     1 fmic       
             "
    ::= { ptiSegway 0 7121 }

ptLSLinkSs7L2LinkAligned NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL2State, ptMTPLSLinkLinkName }
    STATUS          current
    DESCRIPTION     
            "This trap indicates that a signaling link has been aligned.
             
             Cause  - After a signaling link failure is detected, signaling link
                      initial alignment will take place. The Alignment procedure 
                      passes through a number of states and when the procedure 
                      enters the state aligned this trap is sent.
             Freq   - Once the alignment procedure enters the aligned state then
                      the alignment procedure will not be repeated. 
                   
             References
             1) Q.703 , (07/96) Section 7.3 
             
             ptOriginatingOID:    DYNAMIC ptLink
             ptTrapType:          2 communicationAlarm
             ptTrapSeverity:      5 cleared
             ptTrapProbableCause: 6 Communications subsystem error 
             ptTrapClearType:     1 fmic       
             "
    ::= { ptiSegway 0 7122 }

ptLSLinkSs7L3LinkFailCraftRefTimerExpiry NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that the fail link craft referral timer expired
             without having signaling link activated. The fail link craft referral timer
             is the duration allowed for a signaling link to come into service.
             After expiry of this timer, this alarm is generated as per
             the system configuration.
             This is a stateless trap (no alarm).
             
               References
                 1) GR246 Core, section 12.2.1, 12.3.1, 12.3.2
                 2) GR-82-CORE, CR6-43 [673]
                 
                 ptOriginatingOID:    DYNAMIC ptLink
                 ptTrapType:          2 communicationAlarm
                 ptTrapSeverity:      4 warning
                 ptTrapProbableCause: 29 Loss of signal 
                 ptTrapClearType:     2 oic
             "
    ::= { ptiSegway 0 7123 }

ptLSLinkSs7L3LinkUsageAlarmSet NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State }
    STATUS          current
    DESCRIPTION     
            "Obsolete as of 8.2.0.
             
             This trap indicates that the average traffic over this link exceeds 
             predefined threshold. There is potential for traffic loss if this 
             condition persists
             
               References
                 This is PTI proprietary trap.
             
                 ptOriginatingOID:    DYNAMIC ptLink
                 ptTrapType:          11 qualityofserviceAlarm
                 ptTrapSeverity:      4 warning
                 ptTrapProbableCause: 51 Threshold crossed 
                 ptTrapClearType:     2 oic              
             "
    ::= { ptiSegway 0 7124 }

ptATMLinkAtmL3LinkDeactivated NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been deactivated.
             Causes ,Corrective actions and Frequency:  
               1) ptSpecificTrapCause = operatorDeactivation 
                  Cause  - Operator deactivates link.
                  Action - Operator can activate the link again.
                  Freq   - Operator dependant. 
                   
               2) ptSpecificTrapCause = timerT17Expiry
                  Cause  - Event appears between each attempt to perform an initial 
                           alignment procedure. After an unsuccessful attempt, a delay
                           T17 expires before the next attempt is initiated.
                  Action - Operator can activate the link.  
                  Freq   - T19 expiry , T19 can take a value between 800 - 1500 ms
             
               3) ptSpecificTrapCause = unknownCause
             
             References
               1) Table 1 Q.752, SL Failure
               2) Q.704 (07/96) Section 12.2 
                             
               ptOriginatingOID:    DYNAMIC ptLink
               ptTrapType:          2 communicationAlarm
               ptTrapSeverity:      3 minor
               ptTrapProbableCause: 29 Loss of signal   
               ptTrapClearType:     1 fmic
             "
    ::= { ptiSegway 0 7133 }

ptATMLinkAtmL3LinkActivated NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been activated
             either by the operator or as a result of a successful restoration 
             which was initiated upon detection of an inactive link.
             This trap could also be generated at restart without a previous
             corresponding trap 201.
             
             References
               1)  Q.752, SL Restoration
               2)  Q.704, (07/96) Section 12.2
               
               ptOriginatingOID:    DYNAMIC ptLink
               ptTrapType:          2 communicationAlarm
               ptTrapSeverity:      5 cleared
               ptTrapProbableCause: 29 Loss of signal 
               ptTrapClearType:     1 fmic              
             "
    ::= { ptiSegway 0 7134 }

ptATMLinkAtmL3LinkLocalInhibited NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been inhibited 
             by operator at the local node.
               Cause  - Operator inhibits the link.
               Action - Operator can uninhibit the link.
               Freq   - Operator dependant. 
             
             References
               1) Table 2 Q.752, Start of local inhibition
               2) Q.704 , (07/96) Section 10       
             
               ptOriginatingOID:    DYNAMIC ptLink
               ptTrapType:          11 qualityofserviceAlarm
               ptTrapSeverity:      4 warning
               ptTrapProbableCause: 43 Resource at or near capacity   
               ptTrapClearType:     1 fmic
             "
    ::= { ptiSegway 0 7135 }

ptATMLinkAtmL3LinkLocalUninhibited NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been uninhibited at the 
             local node by operator.
             
             References
               1) Table 2 Q.752, End of local inhibition
               2) Q.704 , (07/96) Section 10       
             
               ptOriginatingOID:    DYNAMIC ptLink
               ptTrapType:          11 qualityofserviceAlarm
               ptTrapSeverity:      5 cleared
               ptTrapProbableCause: 43 Resource at or near capacity
               ptTrapClearType:     1 fmic     
             "
    ::= { ptiSegway 0 7136 }

ptATMLinkAtmL3LinkRemoteInhibited NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been inhibited at a 
             remote node.
               Cause  - Operator has inhibited remote end of the link.
               Action - Link is inhibited until the operator uninhibits the 
                        remote end of the link.
               Freq   - Operator dependant. 
             
             References
               1) Table 2 Q.752, Start of remote inhibition
               2) Q.704 , (07/96) Section 10       
             
               ptOriginatingOID:    DYNAMIC ptLink
             	 		 		 		      ptTrapType:          11 qualityofserviceAlarm 
               ptTrapSeverity:      4 warning
               ptTrapProbableCause: 43 Resource at or near capacity  
               ptTrapClearType:     1 fmic         
             "
    ::= { ptiSegway 0 7137 }

ptATMLinkAtmL3LinkRemoteUninhibited NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been uninhibited 
             at the remote end of a link. This can be requested by the operator
             or by signaling routing control function . Signaling routing 
             control will initiate signaling link uninhibit if an inhibited 
             link is found to be a member of a linkset in a route to a destination
             which has become inaccessible. 
             
             References
               1) Table 2 Q.752, End of remote inhibition
               2) Q.704 , (07/96) Section 10       
             
               ptOriginatingOID:    DYNAMIC ptLink
             	 		 		 		      ptTrapType:          11 qualityofserviceAlarm
               ptTrapSeverity:      5 cleared
               ptTrapProbableCause: 43 Resource at or near capacity  
               ptTrapClearType:     1 fmic             
             "
    ::= { ptiSegway 0 7138 }

ptATMLinkAtmL3LinkInhibitDenied NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that an attempt to inhibit a signaling link 
             has failed.
             This is a stateless trap (no alarm).
             
               Causes ,Corrective actions and Frequency: 
                 1) ptSpecificTrapCause = DPC not available 
                    Cause  - This trap occurs when a request to inhibit a link will
                             result in a destination becoming inaccessible and therefore
                             the request is denied.
                    Action - Operator will have to create another link 
                             to access the destination before attempting to inhibit this 
                             one.
                    Freq   - Depends on how many destinations have single links and how
                             often management wants to inhibit them. 
             
                 2) ptSpecificTrapCause = Negative ACK from remote end
                    Cause  - This trap occurs when a request to inhibit the link at the 
                             remote end of a link results in a destination becoming 
                             inaccessible. 
                    Action - Operator will have to wait until another link is available
                             to the destination before inhibiting this one.  
                    Freq   - Depends on how many destinations have single links and how
                             often management wants to inhibit them. 
             
                 3) ptSpecificTrapCause = UnknownCause 
             
               References
                 1) Q.704 , (07/96) Section 10.2       
             
             
                ptOriginatingOID:    DYNAMIC ptLink
                ptTrapType:          10 processingAlarm 
                ptTrapSeverity:      4 warning
                ptTrapProbableCause: 56 Underlying resource unavailable 
                ptTrapClearType:     2 oic       
             "
    ::= { ptiSegway 0 7139 }

ptATMLinkAtmL3LinkUninhibitDenied NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that an attempt to uninhibit a signaling link has failed.
             This is a stateless trap (no alarm).
             
                 Cause  - A request to uninhibit a link from the local node to a 
                          destination will fail if all the routes to the destination
                          are unavailable.
                 Action - Operator will have to wait until a route to the destination
                          becomes available in order that it can send an uninhibit link 
                          message. 
                 Freq   - Operator dependant.
             
               References
                 1) Q.704 , (07/96) Section 10.2       
             
                 ptOriginatingOID:    DYNAMIC ptLink
                 ptTrapType:          10 processingAlarm
                 ptTrapSeverity:      4 warning
                 ptTrapProbableCause: 56 Underlying resource unavailable
                 ptTrapClearType:     2 oic
             "
    ::= { ptiSegway 0 7141 }

ptATMLinkAtmL3LinkRemoteBlocked NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been blocked at a remote node.
             
             Cause  - Signaling link is blocked at the remote node of the link
                      by operator intervention or due to processor outage.
             Action - The link will be unblocked when the remote node of the 
                      link becomes unblocked. 
             Freq   - Operator dependant.
             
             References
             1) Table 2 Q.752 Start of Remote Processor Outage
             2) Q.704 Section 3.3.5      
             
             ptOriginatingOID:      DYNAMIC ptLink
             ptTrapType:            2 communicationAlarm
             ptTrapSeverity:        3 minor
             ptTrapProbableCause:   42 Remote node transmission error  
             ptTrapClearType:       1 fmic
             "
    ::= { ptiSegway 0 7143 }

ptATMLinkAtmL3LinkRemoteUnblocked NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been unblocked at a remote node.
             
             Causes ,Corrective actions and Frequency  
               1) ptSpecificTrapCause = linkDeactivated 
                  Cause  -  Unknown Cause
             
               2) ptSpecificTrapCause = unknownCause
             
             References
               1) Table 2 Q.752 Stop of Remote Processor Outage
               2) Q.704 Section 3.3.5      
             
               ptOriginatingOID:    DYNAMIC ptLink
               ptTrapType:          2 communicationAlarm
               ptTrapSeverity:      5 cleared
               ptTrapProbableCause: 42 Remote node transmission error  
               ptTrapClearType:     1 fmic
             "
    ::= { ptiSegway 0 7144 }

ptATMLinkAtmL3LinkLocalBlocked NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been blocked at the local node by 
             the operator.
             
                  Cause  - Operator blocks a link.
                  Action - Operator can unblock the link. 
                  Freq   - Operator dependant.
             
             
                References
                  1) Q.704 Section 3.2      
             
                  ptOriginatingOID:    DYNAMIC ptLink
                  ptTrapType:          10 processingAlarm
                  ptTrapSeverity:      3 minor
                  ptTrapProbableCause: 56 Underlying resource unavailable
                  ptTrapClearType:     1 fmic       
             "
    ::= { ptiSegway 0 7145 }

ptATMLinkAtmL3LinkLocalUnblocked NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link has been unblocked at the local node 
             by the operator.
             
                References
                 1) Q.704 Section 3.2      
             
                 ptOriginatingOID:    DYNAMIC ptLink
                 ptTrapType:          10 processingAlarm
                 ptTrapSeverity:      5 cleared
                 ptTrapProbableCause: 56 Underlying resource unavailable
                 ptTrapClearType:     1 fmic
             "
    ::= { ptiSegway 0 7146 }

ptATMLinkAtmL2LinkCongested NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkLinkName }
    STATUS          current
    DESCRIPTION     
            "This trap indicates that a signaling link is congested.
             
             Causes and Corrective Action  
               1) ptSpecificTrapCause = managementInitiated 
                  Cause  - Protocol manager detects the condition.  
             
               2) ptSpecificTrapCause = linkCongestion 
                  Cause  - Trap occurs when the thresholds for the number of MSUs
                           in the transmission or re-transmission buffer are exceeded.  
                  Action - Wait until the MSUs are sent .
             
             References
               1) Q.704 , Section 3.8.2 
             
               ptOriginatingOID:    DYNAMIC ptLink
               ptTrapType:          10 processingAlarm
               ptTrapSeverity:      3 minor
               ptTrapProbableCause: 49 Storage capacity problem
               ptTrapClearType:     1 fmic
             "
    ::= { ptiSegway 0 7149 }

ptATMLinkAtmL2LinkUncongested NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkLinkName }
    STATUS          current
    DESCRIPTION     
            "This trap indicates that a signaling link is no longer congested.
             
             Causes and Frequency  
               1) ptSpecificTrapCause = managementInitiated 
                  Cause  - Protocol Manager detects the condition
             
               2) ptSpecificTrapCause = linkUncongested 
                  Cause  - Trap occurs when the number of MSUs in the transmission
                           or re-transmission buffer goes from a value in excess of
                           the thresholds for congestion to a value which is less 
                           than the thresholds.   
                  Freq   - Dependant on throughput of MSUs .
             
             References
               1) Q.704 , Section 3.8.2 
             
               ptOriginatingOID:    DYNAMIC ptLink
               ptTrapType:          10 processingAlarm
               ptTrapSeverity:      5 cleared
               ptTrapProbableCause: 49 Storage capacity problem
               ptTrapClearType:     1 fmic       
             "
    ::= { ptiSegway 0 7150 }

ptRouteRouteInaccessible NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "This trap indicates that a route is no longer accessible.
             It is cleared by a routeAccessible trap.
             
             Cause  - The route may become inaccessible for a number of reasons including
                       - SS7 Node can no longer receive SS7 traffic
                       - All links to this route have been removed 
                       
             Action - Depends on the cause 
             Freq   - This trap will appear when the status of a route changes to inaccessible.  
             
             References 
                1) Q.703 , (07/96) Section 7.3 
                
                ptOriginatingOID:    DYNAMIC ptRoute 
                ptTrapType:          2 communicationAlarm 
                ptTrapSeverity:      3 minor
                ptTrapProbableCause: 6 Communications subsystem error 
                ptTrapClearType:     1 fmic
             "
    ::= { ptiSegway 0 7151 }

ptRouteRouteAccessible NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "This trap indicates that a route is now accessible.
             
             Cause  - The route may become inaccessible for a number of reasons including
                       - SS7 Node can no longer receive SS7 traffic
                       - All links to this route have been removed 
                       
             Action - Depends on the cause 
             Freq   - This trap will appear when the status of a route changes to inaccessible.  
             
             References 
               1) Q.703 , (07/96) Section 7.3 
               
               ptOriginatingOID:    DYNAMIC ptRoute
               ptTrapType:          2 communicationAlarm
               ptTrapSeverity:      5 cleared
               ptTrapProbableCause: 6 Communications subsystem error
               ptTrapClearType:     1 fmic
             "
    ::= { ptiSegway 0 7152 }

ptRoutesetRoutesetInaccessible NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "This trap indicates that a routeset is no longer accessible.
             
             Cause  - The routeset destination may become inaccessible for a number of reasons including
                       - Routeset deactivation
                       - Destination SS7 Node can no longer receive SS7 traffic 
                       - All routes in the routeset are no longer accessible 
                     
             Action - Depends on the cause 
             Freq   - This trap will appear when the status of a routeset destination changes to inaccessible
                      or the routeset is manually deactivated.  
             
             References 
                1) Q.703 
                
                ptOriginatingOID: DYNAMIC ptRouteset 
                ptTrapType: 2 communicationAlarm 
                ptTrapSeverity: 1 critical 
                ptTrapProbableCause: 6 Communications subsystem error 
                ptTrapClearType: 1 fmic                 
             "
    ::= { ptiSegway 0 7153 }

ptRoutesetRoutesetAccessible NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "This trap indicates that a routeset is now accessible.
             
             Cause  - The routeset may become accessible for a number of reasons including
                       - SS7 Node can now receive SS7 traffic
                       - Routes in the routeset have become accessible 
                       
             Action - Depends on the cause 
             Freq - This trap will appear when the status of a routeset changes to accessible.  
             
             References 
                1) Q.703 , (07/96) Section 7.3 
                
                ptOriginatingOID:    DYNAMIC ptRouteset 
                ptTrapType:          2 communicationAlarm 
                ptTrapSeverity:      5 cleared 
                ptTrapProbableCause: 6 Communications subsystem error 
                ptTrapClearType:     1 fmic
             "
    ::= { ptiSegway 0 7154 }

ptLinksetSs7LinksetInaccessible NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that an SS7 linkset is no longer accessible.
             
             Cause  - The linkset destination may become inaccessible for a number of reasons including
                       - Linkset deactivation
                       - All links in the linkset are no longer aligned
                     
             Action - Depends on the cause 
             Freq   - This trap will appear when the status of a linkset status changes from active to inactive or failed.  
             
             References 
                1) Q.703 
                
                ptOriginatingOID: DYNAMIC ptLinkset 
                ptTrapType: 2 communicationAlarm 
                ptTrapSeverity: 1 critical
                ptTrapProbableCause: 6 Communications subsystem error 
                ptTrapClearType: 1 fmic                 
             "
    ::= { ptiSegway 0 7155 }

ptLinksetSs7LinksetAccessible NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that an SS7 linkset is now accessible.
             
             Cause  - The linkset may become accessible when links in the linkset are aligned 
                       
             Action - None required
             Freq   - This trap will appear when the status of a linkset changes to active.  
             
             References 
                1) Q.703 , (07/96) Section 7.3 
                
                ptOriginatingOID:    DYNAMIC ptLinkset
                ptTrapType:          2 communicationAlarm 
                ptTrapSeverity:      5 cleared 
                ptTrapProbableCause: 6 Communications subsystem error 
                ptTrapClearType:     1 fmic
             "
    ::= { ptiSegway 0 7156 }

ptL2ConnectionL2ModuleInaccessible NOTIFICATION-TYPE
    OBJECTS         { ptTrapType, ptTrapSequenceNumber, ptTrapSeverity, 
                      ptTrapProbableCause, ptTrapClearType, 
                      ptTrapDateAndTime, ptTrapItemOID, 
                      ptMTPL2ConnectionCageID }
    STATUS          current
    DESCRIPTION     
            "This trap indicates that an MTP2 is no longer accessible.
             
             Cause  - An MTP2 may become inaccessible for a number of reasons
                      including
                       - MTP2 failure
                       - Communication failure in the IP network leading to MTP2
                     
             Action - Depends on the cause 
             Freq   - This trap will appear when the status of an MTP2 changes
                      to inaccessible.  
             
             References 
                None.  This is implementation specific.
             "
    ::= { ptiSegway 0 7157 }

ptL2ConnectionL2ModuleAccessible NOTIFICATION-TYPE
    OBJECTS         { ptTrapType, ptTrapSequenceNumber, ptTrapSeverity, 
                      ptTrapProbableCause, ptTrapClearType, 
                      ptTrapDateAndTime, ptTrapItemOID, 
                      ptMTPL2ConnectionCageID }
    STATUS          current
    DESCRIPTION     
            "This trap indicates that an MTP2 is now accessible.
             
             Cause  - An MTP2 may become inaccessible for a number of reasons
                      including
                       - MTP2 failure
                       - Communication failure in the IP network leading to MTP2
                      The cause of the clear depends on the failure cause.
                     
             Action - None.
             Freq   - This trap will appear when the status of an MTP2 changes
                      to accessible.  
             
             References 
                None.  This is implementation specific.
             "
    ::= { ptiSegway 0 7158 }

ptRouteRouteInaccessibleCRDT NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "This trap indicates that a route is no longer accessible
             because it failed the ANSI Circular Route Detection Test (CRDT).
             It is cleared by a routeInaccessibleCRDTRecovery trap.
             
             Cause  - The route failed an ANSI Circular Route Detection
                      Test (CRDT).  It will remain unavailable until
                      maintenance personnel reset the state of the
                      route using the Reset State action (presumably
                      after investigating and removing the routing
                      loop).
             
             Action - Investigate and remove the cause of circular
                      routing, then reset the route state using the
                      Reset State action.
             
             Freq   - This trap will appear when the route fails an
                      ANSI CRDT.
             
             References 
                1) GR-246-CORE Issue 10 T1.111.7 Section 2.4
                2) GR-82-CORE Issue 10
                
                ptOriginatingOID:    DYNAMIC ptRoute 
                ptTrapType:          2 communicationAlarm 
                ptTrapSeverity:      1 critical
                ptTrapProbableCause: 6 Communications subsystem error 
                ptTrapClearType:     1 fmic
             
             "
    ::= { ptiSegway 0 7159 }

ptRouteRouteInaccessibleCRDTRecovery NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "This trap clears routeInaccessibleCRDT.
             This trap is issued for a route that was previously unavailable
             because of a failed ANSI Circular Route Detection Test (CRDT) to
             indicate that traffic may be resumed on this route.
             
             
             Cause  - The route previously failed an ANSI Circular Route
                      Detection Test (CRDT).  That condition has been cleared.
             
             Action - None.
             
             Freq   - This trap occurs when a route is cleared of a CRDT
                      condition.
             
             References 
                1) GR-246-CORE Issue 10 T1.111.7 Section 2.4
                2) GR-82-CORE Issue 10
                2) GR-310-CORE Issue 3 Section 8.1
                
                ptOriginatingOID:    DYNAMIC ptRoute 
                ptTrapType:          2 communicationAlarm 
                ptTrapSeverity:      5 cleared
                ptTrapProbableCause: 6 Communications subsystem error 
                ptTrapClearType:     1 fmic
             
             "
    ::= { ptiSegway 0 7160 }

ptATMLinkAtmL2LinkUnaligned NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL2State, 
                      ptMTPATMLinkLinkName }
    STATUS          current
    DESCRIPTION     
            "This trap indicates that a signaling link has lost alignment.
             
             Cause  - After a signaling link failure is detected , signaling link
                      initial alignment will take place. The Alignment procedure 
                      passes through a number of states and when the procedure 
                      enters the state not aligned this trap is sent.
             Action - If the initial alignment procedure does not work then the 
                      operator will have to intervene in order that the link 
                      alignment succeeds.
             Freq   - This trap will continue to appear each time the initial 
                      alignment procedure enters the state not aligned. This
                      may happen a number of times as the initial alignment 
                      procedure is repeated until alignment has been completed
                      successfully. 
                   
             References
               1) Q.703 , (07/96) Section 7.3 
             
             
               ptOriginatingOID:    DYNAMIC ptLink
               ptTrapType:          2 communicationAlarm
               ptTrapSeverity:      3 minor
               ptTrapProbableCause: 6 Communications subsystem error
               ptTrapClearType:     1 fmic       
             "
    ::= { ptiSegway 0 7161 }

ptATMLinkAtmL2LinkAligned NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL2State, 
                      ptMTPATMLinkLinkName }
    STATUS          current
    DESCRIPTION     
            "This trap indicates that a signaling link has been aligned.
             
             Cause  - After a signaling link failure is detected, signaling link
                      initial alignment will take place. The Alignment procedure 
                      passes through a number of states and when the procedure 
                      enters the state aligned this trap is sent.
             Freq   - Once the alignment procedure enters the aligned state then
                      the alignment procedure will not be repeated. 
                   
             References
             1) Q.703 , (07/96) Section 7.3 
             
             ptOriginatingOID:    DYNAMIC ptLink
             ptTrapType:          2 communicationAlarm
             ptTrapSeverity:      5 cleared
             ptTrapProbableCause: 6 Communications subsystem error 
             ptTrapClearType:     1 fmic       
             "
    ::= { ptiSegway 0 7162 }

ptATMLinkAtmL3LinkFailCraftRefTimerExpiry NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that the fail link craft referral timer expired
             without having signaling link activated. The fail link craft referral timer
             is the duration allowed for a signaling link to come into service.
             After expiry of this timer, this alarm is generated as per
             the system configuration.
             This is a stateless trap (no alarm).
             
               References
                 1) GR246 Core, section 12.2.1, 12.3.1, 12.3.2
                 2) GR-82-CORE,  CR6-43 [673]
                 
                 ptOriginatingOID:    DYNAMIC ptLink
                 ptTrapType:          2 communicationAlarm
                 ptTrapSeverity:      4 warning
                 ptTrapProbableCause: 29 Loss of signal 
                 ptTrapClearType:     2 oic
             "
    ::= { ptiSegway 0 7163 }

ptATMLinkAtmL3LinkUsageAlarmSet NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "Obsolete as of 8.2.0.
             
             This trap indicates that the average traffic over this link exceeds 
             predefined threshold. There is potential for traffic loss if this 
             condition persists
             
               References
                 This is PTI proprietary trap.
             
                 ptOriginatingOID:    DYNAMIC ptLink
                 ptTrapType:          11 qualityofserviceAlarm
                 ptTrapSeverity:      4 warning
                 ptTrapProbableCause: 51 Threshold crossed 
                 ptTrapClearType:     2 oic              
             "
    ::= { ptiSegway 0 7164 }

ptRouteRouteAlarmsDisabled NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "Route alarms are disabled."
    ::= { ptiSegway 0 7165 }

ptRouteRouteAlarmsEnabled NOTIFICATION-TYPE
    OBJECTS         { ptTrapType, ptTrapSequenceNumber, ptTrapSeverity, 
                      ptTrapProbableCause, ptTrapClearType, 
                      ptTrapDateAndTime, ptTrapItemOID, ptMTPRouteAPC, 
                      ptMTPRouteCLLI, ptMTPRouteState, 
                      ptMTPRouteLinksetName }
    STATUS          current
    DESCRIPTION     
            "Route alarms are enabled."
    ::= { ptiSegway 0 7166 }

ptLinksetSs7LinksetAlarmsDisabled NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "Linkset alarms are disabled."
    ::= { ptiSegway 0 7167 }

ptLinksetSs7LinksetAlarmsEnabled NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "Linkset alarms are enabled."
    ::= { ptiSegway 0 7168 }

ptAnnexALinkAnnexaL3LinkDeactivated NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been deactivated.
             Causes ,Corrective actions and Frequency:  
               1) ptSpecificTrapCause = operatorDeactivation 
                  Cause  - Operator deactivates link.
                  Action - Operator can activate the link again.
                  Freq   - Operator dependant. 
                   
               2) ptSpecificTrapCause = timerT17Expiry
                  Cause  - Event appears between each attempt to perform an initial 
                           alignment procedure. After an unsuccessful attempt, a delay
                           T17 expires before the next attempt is initiated.
                  Action - Operator can activate the link.  
                  Freq   - T19 expiry , T19 can take a value between 800 - 1500 ms
             
               3) ptSpecificTrapCause = unknownCause
             
             References
               1) Table 1 Q.752, SL Failure
               2) Q.704 (07/96) Section 12.2 
                             
               ptOriginatingOID:    DYNAMIC ptLink
               ptTrapType:          2 communicationAlarm
               ptTrapSeverity:      3 minor
               ptTrapProbableCause: 29 Loss of signal   
               ptTrapClearType:     1 fmic
             "
    ::= { ptiSegway 0 7173 }

ptAnnexALinkAnnexaL3LinkActivated NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been activated
             either by the operator or as a result of a successful restoration 
             which was initiated upon detection of an inactive link.
             This trap could also be generated at restart without a previous
             corresponding trap 201.
             
             References
               1)  Q.752, SL Restoration
               2)  Q.704, (07/96) Section 12.2
               
               ptOriginatingOID:    DYNAMIC ptLink
               ptTrapType:          2 communicationAlarm
               ptTrapSeverity:      5 cleared
               ptTrapProbableCause: 29 Loss of signal 
               ptTrapClearType:     1 fmic              
             "
    ::= { ptiSegway 0 7174 }

ptAnnexALinkAnnexaL3LinkLocalInhibited NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been inhibited 
             by operator at the local node.
               Cause  - Operator inhibits the link.
               Action - Operator can uninhibit the link.
               Freq   - Operator dependant. 
             
             References
               1) Table 2 Q.752, Start of local inhibition
               2) Q.704 , (07/96) Section 10       
             
               ptOriginatingOID:    DYNAMIC ptLink
               ptTrapType:          11 qualityofserviceAlarm
               ptTrapSeverity:      4 warning
               ptTrapProbableCause: 43 Resource at or near capacity   
               ptTrapClearType:     1 fmic
             "
    ::= { ptiSegway 0 7175 }

ptAnnexALinkAnnexaL3LinkLocalUninhibited NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been uninhibited at the 
             local node by operator.
             
             References
               1) Table 2 Q.752, End of local inhibition
               2) Q.704 , (07/96) Section 10       
             
               ptOriginatingOID:    DYNAMIC ptLink
               ptTrapType:          11 qualityofserviceAlarm
               ptTrapSeverity:      5 cleared
               ptTrapProbableCause: 43 Resource at or near capacity
               ptTrapClearType:     1 fmic     
             "
    ::= { ptiSegway 0 7176 }

ptAnnexALinkAnnexaL3LinkRemoteInhibited NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been inhibited at a 
             remote node.
               Cause  - Operator has inhibited remote end of the link.
               Action - Link is inhibited until the operator uninhibits the 
                        remote end of the link.
               Freq   - Operator dependant. 
             
             References
               1) Table 2 Q.752, Start of remote inhibition
               2) Q.704 , (07/96) Section 10       
             
               ptOriginatingOID:    DYNAMIC ptLink
             	 		 		 		      ptTrapType:          11 qualityofserviceAlarm 
               ptTrapSeverity:      4 warning
               ptTrapProbableCause: 43 Resource at or near capacity  
               ptTrapClearType:     1 fmic         
             "
    ::= { ptiSegway 0 7177 }

ptAnnexALinkAnnexaL3LinkRemoteUninhibited NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been uninhibited 
             at the remote end of a link. This can be requested by the operator
             or by signaling routing control function . Signaling routing 
             control will initiate signaling link uninhibit if an inhibited 
             link is found to be a member of a linkset in a route to a destination
             which has become inaccessible. 
             
             References
               1) Table 2 Q.752, End of remote inhibition
               2) Q.704 , (07/96) Section 10       
             
               ptOriginatingOID:    DYNAMIC ptLink
             	 		 		 		      ptTrapType:          11 qualityofserviceAlarm
               ptTrapSeverity:      5 cleared
               ptTrapProbableCause: 43 Resource at or near capacity  
               ptTrapClearType:     1 fmic             
             "
    ::= { ptiSegway 0 7178 }

ptAnnexALinkAnnexaL3LinkInhibitDenied NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that an attempt to inhibit a signaling link 
             has failed.
             This is a stateless trap (no alarm).
             
               Causes ,Corrective actions and Frequency: 
                 1) ptSpecificTrapCause = DPC not available 
                    Cause  - This trap occurs when a request to inhibit a link will
                             result in a destination becoming inaccessible and therefore
                             the request is denied.
                    Action - Operator will have to create another link 
                             to access the destination before attempting to inhibit this 
                             one.
                    Freq   - Depends on how many destinations have single links and how
                             often management wants to inhibit them. 
             
                 2) ptSpecificTrapCause = Negative ACK from remote end
                    Cause  - This trap occurs when a request to inhibit the link at the 
                             remote end of a link results in a destination becoming 
                             inaccessible. 
                    Action - Operator will have to wait until another link is available
                             to the destination before inhibiting this one.  
                    Freq   - Depends on how many destinations have single links and how
                             often management wants to inhibit them. 
             
                 3) ptSpecificTrapCause = UnknownCause 
             
               References
                 1) Q.704 , (07/96) Section 10.2       
             
             
                ptOriginatingOID:    DYNAMIC ptLink
                ptTrapType:          10 processingAlarm 
                ptTrapSeverity:      4 warning
                ptTrapProbableCause: 56 Underlying resource unavailable 
                ptTrapClearType:     2 oic       
             "
    ::= { ptiSegway 0 7179 }

ptAnnexALinkAnnexaL3LinkUninhibitDenied NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that an attempt to uninhibit a signaling link has failed.
             This is a stateless trap (no alarm).
             
                 Cause  - A request to uninhibit a link from the local node to a 
                          destination will fail if all the routes to the destination
                          are unavailable.
                 Action - Operator will have to wait until a route to the destination
                          becomes available in order that it can send an uninhibit link 
                          message. 
                 Freq   - Operator dependant.
             
               References
                 1) Q.704 , (07/96) Section 10.2       
             
                 ptOriginatingOID:    DYNAMIC ptLink
                 ptTrapType:          10 processingAlarm
                 ptTrapSeverity:      4 warning
                 ptTrapProbableCause: 56 Underlying resource unavailable
                 ptTrapClearType:     2 oic
             "
    ::= { ptiSegway 0 7181 }

ptAnnexALinkAnnexaL3LinkRemoteBlocked NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been blocked at a remote node.
             
             Cause  - Signaling link is blocked at the remote node of the link
                      by operator intervention or due to processor outage.
             Action - The link will be unblocked when the remote node of the 
                      link becomes unblocked. 
             Freq   - Operator dependant.
             
             References
             1) Table 2 Q.752 Start of Remote Processor Outage
             2) Q.704 Section 3.3.5      
             
             ptOriginatingOID:      DYNAMIC ptLink
             ptTrapType:            2 communicationAlarm
             ptTrapSeverity:        3 minor
             ptTrapProbableCause:   42 Remote node transmission error  
             ptTrapClearType:       1 fmic
             "
    ::= { ptiSegway 0 7183 }

ptAnnexALinkAnnexaL3LinkRemoteUnblocked NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been unblocked at a remote node.
             
             Causes ,Corrective actions and Frequency  
               1) ptSpecificTrapCause = linkDeactivated 
                  Cause  -  Unknown Cause
             
               2) ptSpecificTrapCause = unknownCause
             
             References
               1) Table 2 Q.752 Stop of Remote Processor Outage
               2) Q.704 Section 3.3.5      
             
               ptOriginatingOID:    DYNAMIC ptLink
               ptTrapType:          2 communicationAlarm
               ptTrapSeverity:      5 cleared
               ptTrapProbableCause: 42 Remote node transmission error  
               ptTrapClearType:     1 fmic
             "
    ::= { ptiSegway 0 7184 }

ptAnnexALinkAnnexaL3LinkLocalBlocked NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been blocked at the local node by 
             the operator.
             
                  Cause  - Operator blocks a link.
                  Action - Operator can unblock the link. 
                  Freq   - Operator dependant.
             
             
                References
                  1) Q.704 Section 3.2      
             
                  ptOriginatingOID:    DYNAMIC ptLink
                  ptTrapType:          10 processingAlarm
                  ptTrapSeverity:      3 minor
                  ptTrapProbableCause: 56 Underlying resource unavailable
                  ptTrapClearType:     1 fmic       
             "
    ::= { ptiSegway 0 7185 }

ptAnnexALinkAnnexaL3LinkLocalUnblocked NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link has been unblocked at the local node 
             by the operator.
             
                References
                 1) Q.704 Section 3.2      
             
                 ptOriginatingOID:    DYNAMIC ptLink
                 ptTrapType:          10 processingAlarm
                 ptTrapSeverity:      5 cleared
                 ptTrapProbableCause: 56 Underlying resource unavailable
                 ptTrapClearType:     1 fmic
             "
    ::= { ptiSegway 0 7186 }

ptAnnexALinkAnnexaL2LinkCongested NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link is congested.
             
             Causes and Corrective Action  
               1) ptSpecificTrapCause = managementInitiated 
                  Cause  - Protocol manager detects the condition.  
             
               2) ptSpecificTrapCause = linkCongestion 
                  Cause  - Trap occurs when the thresholds for the number of MSUs
                           in the transmission or re-transmission buffer are exceeded.  
                  Action - Wait until the MSUs are sent .
             
             References
               1) Q.704 , Section 3.8.2 
             
               ptOriginatingOID:    DYNAMIC ptLink
               ptTrapType:          10 processingAlarm
               ptTrapSeverity:      3 minor
               ptTrapProbableCause: 49 Storage capacity problem
               ptTrapClearType:     1 fmic
             "
    ::= { ptiSegway 0 7189 }

ptAnnexALinkAnnexaL2LinkUncongested NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkLinkName }
    STATUS          current
    DESCRIPTION     
            "This trap indicates that a signaling link is no longer congested.
             
             Causes and Frequency  
               1) ptSpecificTrapCause = managementInitiated 
                  Cause  - Protocol Manager detects the condition
             
               2) ptSpecificTrapCause = linkUncongested 
                  Cause  - Trap occurs when the number of MSUs in the transmission
                           or re-transmission buffer goes from a value in excess of
                           the thresholds for congestion to a value which is less 
                           than the thresholds.   
                  Freq   - Dependant on throughput of MSUs .
             
             References
               1) Q.704 , Section 3.8.2 
             
               ptOriginatingOID:    DYNAMIC ptLink
               ptTrapType:          10 processingAlarm
               ptTrapSeverity:      5 cleared
               ptTrapProbableCause: 49 Storage capacity problem
               ptTrapClearType:     1 fmic       
             "
    ::= { ptiSegway 0 7190 }

ptAnnexALinkAnnexaL2LinkUnaligned NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL2State, 
                      ptMTPAnnexALinkLinkName }
    STATUS          current
    DESCRIPTION     
            "This trap indicates that a signaling link has lost alignment.
             
             Cause  - After a signaling link failure is detected , signaling link
                      initial alignment will take place. The Alignment procedure 
                      passes through a number of states and when the procedure 
                      enters the state not aligned this trap is sent.
             Action - If the initial alignment procedure does not work then the 
                      operator will have to intervene in order that the link 
                      alignment succeeds.
             Freq   - This trap will continue to appear each time the initial 
                      alignment procedure enters the state not aligned. This
                      may happen a number of times as the initial alignment 
                      procedure is repeated until alignment has been completed
                      successfully. 
                   
             References
               1) Q.703 , (07/96) Section 7.3 
             
             
               ptOriginatingOID:    DYNAMIC ptLink
               ptTrapType:          2 communicationAlarm
               ptTrapSeverity:      3 minor
               ptTrapProbableCause: 6 Communications subsystem error
               ptTrapClearType:     1 fmic       
             "
    ::= { ptiSegway 0 7191 }

ptAnnexALinkAnnexaL2LinkAligned NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL2State, 
                      ptMTPAnnexALinkLinkName }
    STATUS          current
    DESCRIPTION     
            "This trap indicates that a signaling link has been aligned.
             
             Cause  - After a signaling link failure is detected, signaling link
                      initial alignment will take place. The Alignment procedure 
                      passes through a number of states and when the procedure 
                      enters the state aligned this trap is sent.
             Freq   - Once the alignment procedure enters the aligned state then
                      the alignment procedure will not be repeated. 
                   
             References
             1) Q.703 , (07/96) Section 7.3 
             
             ptOriginatingOID:    DYNAMIC ptLink
             ptTrapType:          2 communicationAlarm
             ptTrapSeverity:      5 cleared
             ptTrapProbableCause: 6 Communications subsystem error 
             ptTrapClearType:     1 fmic       
             "
    ::= { ptiSegway 0 7192 }

ptAnnexALinkAnnexaL3LinkFailCraftRefTimerExpiry NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that the fail link craft referral timer expired
             without having signaling link activated. The fail link craft referral timer
             is the duration allowed for a signaling link to come into service.
             After expiry of this timer, this alarm is generated as per
             the system configuration.
             This is a stateless trap (no alarm).
             
               References
                 1) GR246 Core, section 12.2.1, 12.3.1, 12.3.2
                 2) GR-82-CORE,  CR6-43 [673]
                 
                 ptOriginatingOID:    DYNAMIC ptLink
                 ptTrapType:          2 communicationAlarm
                 ptTrapSeverity:      4 warning
                 ptTrapProbableCause: 29 Loss of signal 
                 ptTrapClearType:     1 fmic              
             "
    ::= { ptiSegway 0 7193 }

ptAnnexALinkAnnexaL3LinkOscillationFilterSet NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that Link Oscillation Filter Timer T32 has started 
             "
    ::= { ptiSegway 0 7195 }

ptAnnexALinkAnnexaL3LinkOscillationFilterClear NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that Link Oscillation Filter Timer T32 has expired 
             "
    ::= { ptiSegway 0 7196 }

ptM2UALinkM2uaL3LinkUsageAlarmSet NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "Obsolete as of 8.2.0.
             
             This trap indicates that the average traffic over this link exceeds 
             predefined threshold. There is potential for traffic loss if this 
             condition persists
             
               References
                 This is PTI proprietary trap.
             
                 ptOriginatingOID:    DYNAMIC ptLink
                 ptTrapType:          11 qualityofserviceAlarm
                 ptTrapSeverity:      4 warning
                 ptTrapProbableCause: 51 Threshold crossed 
                 ptTrapClearType:     2 oic              
             "
    ::= { ptiSegway 0 7197 }

ptAnnexALinkAnnexaL3LinkUsageAlarmSet NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "Obsolete as of 8.2.0.
             
             This trap indicates that the average traffic over this link exceeds 
             predefined threshold. There is potential for traffic loss if this 
             condition persists
             
               References
                 This is PTI proprietary trap.
             
                 ptOriginatingOID:    DYNAMIC ptLink
                 ptTrapType:          11 qualityofserviceAlarm
                 ptTrapSeverity:      4 warning
                 ptTrapProbableCause: 51 Threshold crossed 
                 ptTrapClearType:     2 oic              
             "
    ::= { ptiSegway 0 7198 }

ptCICUAAppServerFailedCloseCicServer NOTIFICATION-TYPE
    OBJECTS         { ptTrapType, ptTrapSequenceNumber, ptTrapSeverity, 
                      ptTrapProbableCause, ptTrapClearType, 
                      ptTrapDateAndTime, ptTrapItemOID, 
                      ptSGCICUAAppServerDPC, ptSGCICUAAppServerStatus }
    STATUS          current
    DESCRIPTION     
            "Failed to close CIC UA TCP Server."
    ::= { ptiSegway 0 7200 }

ptCICUAAppServerSuccessCloseCicServer NOTIFICATION-TYPE
    OBJECTS         { ptTrapType, ptTrapSequenceNumber, ptTrapSeverity, 
                      ptTrapProbableCause, ptTrapClearType, 
                      ptTrapDateAndTime, ptTrapItemOID, 
                      ptSGCICUAAppServerDPC, ptSGCICUAAppServerStatus }
    STATUS          current
    DESCRIPTION     
            "Success closed CIC UA TCP Server."
    ::= { ptiSegway 0 7201 }

ptCICUAAppServerFailedEstablishCicServer NOTIFICATION-TYPE
    OBJECTS         { ptTrapType, ptTrapSequenceNumber, ptTrapSeverity, 
                      ptTrapProbableCause, ptTrapClearType, 
                      ptTrapDateAndTime, ptTrapItemOID, 
                      ptSGCICUAAppServerDPC, ptSGCICUAAppServerStatus }
    STATUS          current
    DESCRIPTION     
            "Failed to establish CIC UA TCP Server."
    ::= { ptiSegway 0 7202 }

ptCICUAAppServerSuccessEstablishCicServer NOTIFICATION-TYPE
    OBJECTS         { ptTrapType, ptTrapSequenceNumber, ptTrapSeverity, 
                      ptTrapProbableCause, ptTrapClearType, 
                      ptTrapDateAndTime, ptTrapItemOID, 
                      ptSGCICUAAppServerDPC, ptSGCICUAAppServerStatus }
    STATUS          current
    DESCRIPTION     
            "Successfully established CIC UA TCP Server."
    ::= { ptiSegway 0 7203 }

ptCICUAASPCicUserConnLoss NOTIFICATION-TYPE
    OBJECTS         { ptTrapType, ptTrapSequenceNumber, ptTrapSeverity, 
                      ptTrapProbableCause, ptTrapClearType, 
                      ptTrapDateAndTime, ptTrapItemOID, ptSGCICUAASPHost, 
                      ptSGCICUAASPPort, ptSGCICUAASPASPID }
    STATUS          current
    DESCRIPTION     
            "A CIC UA connection loss notification is sent when the
             connection between an ASP and Dinamo is lost."
    ::= { ptiSegway 0 7218 }

ptCICUAASPCicUserConnEstablished NOTIFICATION-TYPE
    OBJECTS         { ptTrapType, ptTrapSequenceNumber, ptTrapSeverity, 
                      ptTrapProbableCause, ptTrapClearType, 
                      ptTrapDateAndTime, ptTrapItemOID, ptSGCICUAASPHost, 
                      ptSGCICUAASPPort, ptSGCICUAASPASPID }
    STATUS          current
    DESCRIPTION     
            "A CIC UA connection established notification is sent when the
             connection between an ASP and Dinamo is established."
    ::= { ptiSegway 0 7219 }

ptSUAASPSuaUserConnLoss NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "A user connection loss notification is sent when the
             connection between an ASP and Dinamo is lost."
    ::= { ptiSegway 0 7224 }

ptSUAASPSuaUserConnEstablished NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "A user connection established notification is sent when the
             connection between an ASP and Dinamo is established."
    ::= { ptiSegway 0 7225 }

ptM3UAASPM3uaUserConnLoss NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "A user connection loss notification is sent when the
             connection between an ASP and Dinamo is lost."
    ::= { ptiSegway 0 7228 }

ptM3UAASPM3uaUserConnEstablished NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "A user connection established notification is sent when the
             connection between an ASP and Dinamo is established."
    ::= { ptiSegway 0 7229 }

ptMTP3NAMtp3NANotConnected NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA not connected notification is sent when the
             connectivity between the Dinamo and MTP3 NA is lost."
    ::= { ptiSegway 0 7230 }

ptMTP3NAMtp3NAConnected NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA connected notification is sent when the
             connectivity between the Dinamo and MTP3 is established."
    ::= { ptiSegway 0 7231 }

ptSCCPNASccpNANotConnected NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "An SCCP NA not connected notification is sent when the
             connectivity between the Dinamo and SCCP NA is lost."
    ::= { ptiSegway 0 7232 }

ptSCCPNASccpNAConnected NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "An SCCP NA connected notification is sent when the
             connectivity between the Dinamo and SCCP is established."
    ::= { ptiSegway 0 7233 }

ptM3UASCTPServersM3uaLicCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical M3UA License Event has occurred"
    ::= { ptiSegway 0 7234 }

ptM3UASCTPServersM3uaLicClrCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical M3UA License Event has been cleared"
    ::= { ptiSegway 0 7235 }

ptM3UASCTPServersM3uaLicMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major M3UA License Event has occurred"
    ::= { ptiSegway 0 7236 }

ptM3UASCTPServersM3uaLicClrMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major M3UA License Event has been cleared"
    ::= { ptiSegway 0 7237 }

ptSUASCTPServersSuaLicCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical SUA License Event has occurred"
    ::= { ptiSegway 0 7238 }

ptSUASCTPServersSuaLicClrCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical SUA License Event has been cleared"
    ::= { ptiSegway 0 7239 }

ptSUASCTPServersSuaLicMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major SUA License Event has occurred"
    ::= { ptiSegway 0 7240 }

ptSUASCTPServersSuaLicClrMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major SUA License Event has been cleared"
    ::= { ptiSegway 0 7241 }

ptCICUATCPServerCicLicCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical CIC License Event has occurred"
    ::= { ptiSegway 0 7250 }

ptCICUATCPServerCicLicClrCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Critical CIC License Event has been cleared"
    ::= { ptiSegway 0 7251 }

ptCICUATCPServerCicLicMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major CIC License Event has occurred"
    ::= { ptiSegway 0 7252 }

ptCICUATCPServerCicLicClrMajor NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A Major CIC License Event has been cleared"
    ::= { ptiSegway 0 7253 }

ptM3UAASPM3uaAssocPathLoss NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "A path is down on a multi-homed user connection"
    ::= { ptiSegway 0 7270 }

ptM3UAASPM3uaUserAssocPathEstablished NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "A path is up on a multi-homed user connection"
    ::= { ptiSegway 0 7271 }

ptSUAASPSuaAssocPathLoss NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "A path is down on a multi-homed user connection"
    ::= { ptiSegway 0 7272 }

ptSUAASPSuaUserAssocPathEstablished NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "A path is up on a multi-homed user connection"
    ::= { ptiSegway 0 7273 }

ptSGConfigurationLicConnCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A critical SG license error has occurred"
    ::= { ptiSegway 0 7274 }

ptSGConfigurationLicConnClrCritical NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A critical SG license error has been cleared"
    ::= { ptiSegway 0 7275 }

ptSGConfigurationSgDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended value.
             
             Possible Actions -
               The user should perform the 'Restore Debug Defaults' action to reset all
               debug attributes to their default values."
    ::= { ptiSegway 0 7276 }

ptSGConfigurationSgDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 7277 }

ptM3UAAppServerM3UAAppServerNotActive NOTIFICATION-TYPE
    OBJECTS         { ptTrapType, ptTrapSequenceNumber, ptTrapSeverity, 
                      ptTrapProbableCause, ptTrapClearType, 
                      ptTrapDateAndTime, ptTrapItemOID, 
                      ptSGM3UAAppServerRoutingContext, 
                      ptSGM3UAAppServerDPC, ptSGM3UAAppServerSI, 
                      ptSGM3UAAppServerNetworkAppearance, 
                      ptSGM3UAAppServerApplicationID }
    STATUS          current
    DESCRIPTION     
            "This trap indicates that an App Server is not active.  
             Cause: No ASP has activated the associated routing context (RC).
               ptOriginatingOID: DYNAMIC
               ptTrapType: 2 communicationAlarm 
               ptTrapSeverity: 1 critical 
               ptTrapProbableCause: 6 Communications subsystem error 
               ptTrapClearType: 1 fmic"
    ::= { ptiSegway 0 7300 }

ptM3UAAppServerM3UAAppServerActive NOTIFICATION-TYPE
    OBJECTS         { ptTrapType, ptTrapSequenceNumber, ptTrapSeverity, 
                      ptTrapProbableCause, ptTrapClearType, 
                      ptTrapDateAndTime, ptTrapItemOID, 
                      ptSGM3UAAppServerRoutingContext, 
                      ptSGM3UAAppServerDPC, ptSGM3UAAppServerSI, 
                      ptSGM3UAAppServerNetworkAppearance, 
                      ptSGM3UAAppServerApplicationID }
    STATUS          current
    DESCRIPTION     
            "This trap indicates that an App Server is now active.  
             Cause: An ASP has activated the associated routing context (RC).
               ptOriginatingOID: DYNAMIC
               ptTrapType: 2 communicationAlarm 
               ptTrapSeverity: 5 cleared 
               ptTrapProbableCause: 6 Communications subsystem error 
               ptTrapClearType: 1 fmic"
    ::= { ptiSegway 0 7301 }

ptM3UAConfiguredASPM3UAConfiguredASPDown NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "This trap indicates that a Configured ASP is down.  
             Cause: No ASP has connected to this ID and sent an ASPUP notification.
               ptOriginatingOID: DYNAMIC
               ptTrapType: 2 communicationAlarm 
               ptTrapSeverity: 3 minor
               ptTrapProbableCause: 6 Communications subsystem error 
               ptTrapClearType: 1 fmic"
    ::= { ptiSegway 0 7302 }

ptM3UAConfiguredASPM3UAConfiguredASPUp NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "This trap indicates that a Configured ASP is now up.  
             Cause: An ASP has connected and sent an ASPUP notification.
               ptOriginatingOID: DYNAMIC
               ptTrapType: 2 communicationAlarm 
               ptTrapSeverity: 5 cleared 
               ptTrapProbableCause: 6 Communications subsystem error 
               ptTrapClearType: 1 fmic"
    ::= { ptiSegway 0 7303 }

ptM3UAMultiAssociationASPM3UAMultiAssocASPDown NOTIFICATION-TYPE
    OBJECTS         { ptTrapType, ptTrapSequenceNumber, ptTrapSeverity, 
                      ptTrapProbableCause, ptTrapClearType, 
                      ptTrapDateAndTime, ptTrapItemOID, 
                      ptSGM3UAMultiAssociationASPID, 
                      ptSGM3UAMultiAssociationASPName }
    STATUS          current
    DESCRIPTION     
            "This trap indicates that a Multipath ASP is down.
             Cause: No ASP has connected to this ID and sent an ASPUP notification.
               ptOriginatingOID: DYNAMIC
               ptTrapType: 2 communicationAlarm
               ptTrapSeverity: 3 minor
               ptTrapProbableCause: 6 Communications subsystem error
               ptTrapClearType: 1 fmic"
    ::= { ptiSegway 0 7304 }

ptM3UAMultiAssociationASPM3UAMultiAssocASPUp NOTIFICATION-TYPE
    OBJECTS         { ptTrapType, ptTrapSequenceNumber, ptTrapSeverity, 
                      ptTrapProbableCause, ptTrapClearType, 
                      ptTrapDateAndTime, ptTrapItemOID, 
                      ptSGM3UAMultiAssociationASPID, 
                      ptSGM3UAMultiAssociationASPName }
    STATUS          current
    DESCRIPTION     
            "This trap indicates that a Multipath ASP is now up.
             Cause: An ASP has connected and sent an ASPUP notification.
               ptOriginatingOID: DYNAMIC
               ptTrapType: 2 communicationAlarm
               ptTrapSeverity: 5 cleared
               ptTrapProbableCause: 6 Communications subsystem error
               ptTrapClearType: 1 fmic"
    ::= { ptiSegway 0 7305 }

ptM3UAASPAssociationM3UAASPAssocDown NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "This trap indicates that a configured association is down.
             Cause: No ASP has connected to this ID and sent an ASPUP notification.
               ptOriginatingOID: DYNAMIC
               ptTrapType: 2 communicationAlarm
               ptTrapSeverity: 3 minor
               ptTrapProbableCause: 6 Communications subsystem error
               ptTrapClearType: 1 fmic"
    ::= { ptiSegway 0 7306 }

ptM3UAASPAssociationM3UAASPAssocUp NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "This trap indicates that a configured association is now up.
             Cause: An ASP has connected and sent an ASPUP notification.
               ptOriginatingOID: DYNAMIC
               ptTrapType: 2 communicationAlarm
               ptTrapSeverity: 5 cleared
               ptTrapProbableCause: 6 Communications subsystem error
               ptTrapClearType: 1 fmic"
    ::= { ptiSegway 0 7307 }

ptSUAAppServerSUAAppServerNotActive NOTIFICATION-TYPE
    OBJECTS         { ptTrapType, ptTrapSequenceNumber, ptTrapSeverity, 
                      ptTrapProbableCause, ptTrapClearType, 
                      ptTrapDateAndTime, ptTrapItemOID, 
                      ptSGSUAAppServerRoutingContext, 
                      ptSGSUAAppServerDPC, ptSGSUAAppServerSSN, 
                      ptSGSUAAppServerNetworkAppearance, 
                      ptSGSUAAppServerApplicationID }
    STATUS          current
    DESCRIPTION     
            "This trap indicates that an App Server is not active.  
             Cause: No ASP has activated the associated routing context (RC).
               ptOriginatingOID: DYNAMIC
               ptTrapType: 2 communicationAlarm 
               ptTrapSeverity: 1 critical 
               ptTrapProbableCause: 6 Communications subsystem error 
               ptTrapClearType: 1 fmic"
    ::= { ptiSegway 0 7310 }

ptSUAAppServerSUAAppServerActive NOTIFICATION-TYPE
    OBJECTS         { ptTrapType, ptTrapSequenceNumber, ptTrapSeverity, 
                      ptTrapProbableCause, ptTrapClearType, 
                      ptTrapDateAndTime, ptTrapItemOID, 
                      ptSGSUAAppServerRoutingContext, 
                      ptSGSUAAppServerDPC, ptSGSUAAppServerSSN, 
                      ptSGSUAAppServerNetworkAppearance, 
                      ptSGSUAAppServerApplicationID }
    STATUS          current
    DESCRIPTION     
            "This trap indicates that an App Server is now active.  
             Cause: An ASP has activated the associated routing context (RC).
               ptOriginatingOID: DYNAMIC
               ptTrapType: 2 communicationAlarm 
               ptTrapSeverity: 5 cleared 
               ptTrapProbableCause: 6 Communications subsystem error 
               ptTrapClearType: 1 fmic"
    ::= { ptiSegway 0 7311 }

ptSUAConfiguredASPSUAConfiguredASPDown NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "This trap indicates that a Configured ASP is down.  
             Cause: No ASP has connected to this ID and sent an ASPUP notification.
               ptOriginatingOID: DYNAMIC
               ptTrapType: 2 communicationAlarm 
               ptTrapSeverity: 3 minor
               ptTrapProbableCause: 6 Communications subsystem error 
               ptTrapClearType: 1 fmic"
    ::= { ptiSegway 0 7312 }

ptSUAConfiguredASPSUAConfiguredASPUp NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "This trap indicates that a Configured ASP is now up.  
             Cause: An ASP has connected and sent an ASPUP notification.
               ptOriginatingOID: DYNAMIC
               ptTrapType: 2 communicationAlarm 
               ptTrapSeverity: 5 cleared 
               ptTrapProbableCause: 6 Communications subsystem error 
               ptTrapClearType: 1 fmic"
    ::= { ptiSegway 0 7313 }

ptMTP3NAM3UAASMasterNotActive NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that an AS Master is not active for an NA.
             Cause: One or more AS of type AS Master for that NA are not active.
               ptOriginatingOID: DYNAMIC
               ptTrapType: 2 communicationAlarm
               ptTrapSeverity: 1 critical
               ptTrapProbableCause: 6 Communications subsystem error
               ptTrapClearType: 1 fmic"
    ::= { ptiSegway 0 7316 }

ptMTP3NAM3UAASMasterActive NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that the AS Master is now active for an NA.
             Cause: All AS of type AS Master for that NA are now active.
               ptOriginatingOID: DYNAMIC
               ptTrapType: 2 communicationAlarm
               ptTrapSeverity: 5 cleared
               ptTrapProbableCause: 6 Communications subsystem error
               ptTrapClearType: 1 fmic"
    ::= { ptiSegway 0 7317 }

ptM3UAM3UAASMasterNAMismatch NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that an AS Master has NA data on the C20 Core but not
             on the SG. It could be caused by deletion operation failure or
             a synchronization issue. The user should compare the C20 Core with the SG NA data and
             fix it manually.
               ptOriginatingOID: DYNAMIC
               ptTrapType: 2 communicationAlarm
               ptTrapSeverity: 2 major 
               ptTrapProbableCause: 6 Communications subsystem error
               ptTrapClearType: 1 fmic"
    ::= { ptiSegway 0 7318 }

ptM3UAM3UAASMasterNAMatch NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that an AS Master has NA data matched 
             on both the C20 Core and the SG. It clears the mismatch alarm.
               ptOriginatingOID: DYNAMIC
               ptTrapType: 2 communicationAlarm
               ptTrapSeverity: 5 cleared
               ptTrapProbableCause: 6 Communications subsystem error
               ptTrapClearType: 1 fmic"
    ::= { ptiSegway 0 7319 }

ptMTP3NAMtp3NAC20SyncFail NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA Sync Failed notification is sent when Dinamo fails
             to synchronize the newly add NA value to C20 Core and mismatch occurs."
    ::= { ptiSegway 0 7320 }

ptMTP3NAMtp3NAC20SyncSucc NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA Sync Success notification is sent when Dinamo
             synchronizes the newly add NA value to C20 Core and mismatch is corrected."
    ::= { ptiSegway 0 7321 }

ptSUAASPSuaAssocHighTransmitUsageOnset NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "The amount of traffic being transmitted to an SUA ASP has reached excessive levels.
             The conditions of this clear event are controlled by the user using the SUA
             High Usage Onset setting."
    ::= { ptiSegway 0 7324 }

ptSUAASPSuaAssocHighTransmitUsageAbatement NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "The amount of traffic being transmitted to an SUA ASP has received normal levels.
             The conditions of this clear event are controlled by the user using the SUA
             High Usage Abatement setting."
    ::= { ptiSegway 0 7325 }

ptSUAASPSuaAssocHighReceiveUsageOnset NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "The amount of traffic being transmitted to an SUA ASP on an association has received normal levels.
             The conditions of this clear event are controlled by the user using the SUA
             High Usage Onset setting."
    ::= { ptiSegway 0 7326 }

ptSUAASPSuaAssocHighReceiveUsageAbatement NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "The amount of traffic being received from an SUA ASP has received normal levels.
             The conditions of this clear event are controlled by the user using the SUA
             High Usage Abatement setting."
    ::= { ptiSegway 0 7327 }

ptM3UAASPM3uaAssocHighTransmitUsageOnset NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "The amount of traffic being transmitted to an M3UA ASP has reached excessive levels.
             The conditions of this clear event are controlled by the user using the M3UA
             High Usage Onset setting."
    ::= { ptiSegway 0 7328 }

ptM3UAASPM3uaAssocHighTransmitUsageAbatement NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "The amount of traffic being transmitted to an M3UA ASP has received normal levels.
             The conditions of this clear event are controlled by the user using the M3UA
             High Usage Abatement setting."
    ::= { ptiSegway 0 7329 }

ptM3UAASPM3uaAssocHighReceiveUsageOnset NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "The amount of traffic being transmitted to an M3UA ASP on an association has received normal levels.
             The conditions of this clear event are controlled by the user using the M3UA
             High Usage Onset setting."
    ::= { ptiSegway 0 7330 }

ptM3UAASPM3uaAssocHighReceiveUsageAbatement NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "The amount of traffic being received from an M3UA ASP has received normal levels.
             The conditions of this clear event are controlled by the user using the M3UA
             High Usage Abatement setting."
    ::= { ptiSegway 0 7331 }

ptM3UAASPAssociationM3uaMultiASPAssocHighTransmitUsageOnset NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "The amount of traffic being transmitted by the SG on a single M3UA Multi ASP association
             has reached excessive levels.
             The conditions of this clear event are controlled by the user using the M3UA
             High Usage Onset setting."
    ::= { ptiSegway 0 7332 }

ptM3UAASPAssociationM3uaMultiASPAssocHighTransmitUsageAbatem NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "The amount of traffic being transmitted to an M3UA ASP has received normal levels.
             The conditions of this clear event are controlled by the user using the M3UA
             High Usage Abatement setting."
    ::= { ptiSegway 0 7333 }

ptM3UAASPAssociationM3uaMultiASPAssocHighReceiveUsageOnset NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "The amount of traffic being received by the SG on a single M3UA Multi ASP association
             has received normal levels.
             The conditions of this clear event are controlled by the user using the M3UA
             High Usage Onset setting."
    ::= { ptiSegway 0 7334 }

ptM3UAASPAssociationM3uaMultiASPAssocHighReceiveUsageAbateme NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "The amount of traffic being received by the SG on a single M3UA Multi ASP association
             has resumed normal levels.
             The conditions of this clear event are controlled by the user using the M3UA
             High Usage Abatement setting."
    ::= { ptiSegway 0 7335 }

ptM3UAASPAssociationM3uaMultiAssocPathLoss NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An path is down on a multi-homed user connection"
    ::= { ptiSegway 0 7340 }

ptM3UAASPAssociationM3uaMultiAssocPathEstablished NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An path is up on a multi-homed user connection"
    ::= { ptiSegway 0 7341 }

ptM3UAASPAssociationM3uaMultiAssocMinStreamsFail NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An M3UA multi association has been established with less than the minimum 2 steam requirement"
    ::= { ptiSegway 0 7342 }

ptM3UAASPAssociationM3uaMultiAssocMinStreamsClear NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "The M3UA multi association causing the minimum stream alarm has been aborted or removed"
    ::= { ptiSegway 0 7343 }

ptMTP3NAMtp3NASGSyncFail NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA Sync Failed notification is sent when Dinamo refuses 
             to synchronize the newly added NA value from the MTP3 because it will cause a mismatch with the C20 Core."
    ::= { ptiSegway 0 7344 }

ptMTP3NAMtp3NASGSyncSucc NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MTP3 NA Sync Success notification is sent when Dinamo
             synchronizes with the newly added MTP3 NA configuration after a previous failure is corrected."
    ::= { ptiSegway 0 7345 }

ptM3UAASPM3uaAssocMinStreamsFail NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "An M3UA ASP association has been established with less than the minimum 2 steam requirement"
    ::= { ptiSegway 0 7346 }

ptM3UAASPM3uaAssocMinStreamsClear NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPPort, 
                      ptSGM3UAASPID }
    STATUS          current
    DESCRIPTION     
            "The M3UA ASP association causing the minimum stream alarm has been aborted or removed"
    ::= { ptiSegway 0 7347 }

ptSUAASPSuaAssocMinStreamsFail NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "An SUA ASP association has been established with less than the minimum 2 steam requirement"
    ::= { ptiSegway 0 7348 }

ptSUAASPSuaAssocMinStreamsClear NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPPort, ptSGSUAASPID }
    STATUS          current
    DESCRIPTION     
            "The SUA ASP association causing the minimum stream alarm has been aborted or removed"
    ::= { ptiSegway 0 7349 }

ptM3UASCTPServerM3UASCTPServerDown NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "An M3UA SCTP server is down and not accepting connections.
             
             Cause - The SG is unable to establish a server socket with 
                the current configuration. 
             
             Possible Actions - 
                If unresolved hostname alarms exist for this server, 
                troubleshoot those first.  Once the hostnames resolve the 
                condition may clear.
             
                If using hostnames, ensure they are resolving properly to 
                IP addresses that are valid for the configured Slot.
                Use IP Networking > Hostname Resolution to verify hostname configuration.
                Use IP Networking > Network Interfaces > Routing IP Network to verify Slot IP addresses.
             
                If using IP addresses, ensure the IP addresses are valid for the configured Slot.  
                Use IP Networking > Network Interfaces > Routing IP Network to verify Slot IP addresses.
             
                If IP addressing appears to be correct, it is possible that the port is in use by another
                application.   Examine the current sockets on the system by using 
                IP Networking > IP Utilities > Open Sockets.
             "
    ::= { ptiSegway 0 7350 }

ptM3UASCTPServerM3UASCTPServerUp NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "An M3UA SCTP server is up"
    ::= { ptiSegway 0 7351 }

ptM3UASCTPServerM3UASCTPServerUnresolvedHost1 NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "Indicates that M3UA SCTP Server IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7352 }

ptM3UASCTPServerM3UASCTPServerResolvedHost1 NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "M3UA SCTP Server Hostname 1 is resolved"
    ::= { ptiSegway 0 7353 }

ptM3UASCTPServerM3UASCTPServerUnresolvedHost2 NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "Indicates that M3UA SCTP Server IP Address 2 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7354 }

ptM3UASCTPServerM3UASCTPServerResolvedHost2 NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "M3UA SCTP Server Hostname 2 is resolved"
    ::= { ptiSegway 0 7355 }

ptSUASCTPServerSUASCTPServerDown NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "An SUA SCTP server is down and not accepting connections.
             
             Cause - The SG is unable to establish a server socket with 
                the current configuration. 
             
             Possible Actions - 
                If unresolved hostname alarms exist for this server, 
                troubleshoot those first.  Once the hostnames resolve the 
                condition may clear.
             
                If using hostnames, ensure they are resolving properly to 
                IP addresses that are valid for the configured Slot.
                Use IP Networking > Hostname Resolution to verify hostname configuration.
                Use IP Networking > Network Interfaces > Routing IP Network to verify Slot IP addresses.
             
                If using IP addresses, ensure the IP addresses are valid for the configured Slot.  
                Use IP Networking > Network Interfaces > Routing IP Network to verify Slot IP addresses.
             "
    ::= { ptiSegway 0 7356 }

ptSUASCTPServerSUASCTPServerUp NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "An SUA SCTP server is up"
    ::= { ptiSegway 0 7357 }

ptSUASCTPServerSUASCTPServerUnresolvedHost1 NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "Indicates that SUA SCTP Server IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7358 }

ptSUASCTPServerSUASCTPServerResolvedHost1 NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "An SUA SCTP Server Hostname 1 is resolved"
    ::= { ptiSegway 0 7359 }

ptSUASCTPServerSUASCTPServerUnresolvedHost2 NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "Indicates that SUA SCTP Server IP Address 2 hostname is not resolvable. 
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7360 }

ptSUASCTPServerSUASCTPServerResolvedHost2 NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "An SUA SCTP Server Hostname 2 is resolved"
    ::= { ptiSegway 0 7361 }

ptM3UASCTPServerM3UASCTPServerAddrListMismatch NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "Indicates that M3UA SCTP Server is not listening on all configured addresses.
             
             Cause - The M3UA SCTP Server is configured to listen on an address
                but binding to that address/port failed.
             
             Possible Actions - Determine if another application is using the 
                desired address/port, which is preventing the server from binding
                to the address.  This can be done using IP Networking > IP Utilities > Open Sockets.
             
                Determine if the IP addresses are actually valid for the slot that the
                server is listening on.  Use Network Interaces > View Network Interfaces for the
                corresponding slot to see if the address is configured for one of the interfaces.
                If you are using hostnames, you will first need to check which addresses the hostname
                resolves to using IP Networking > Hostname Resolution (if using DNS you will need to check
                the DNS Server configuration).
             
                If using hostnames, it is possible that each address was not resolvable at startup. 
                If there are no hostname resolution alarms present for the M3UA SCTP Server, it is possible
                that deactivating and reactivating the server will correct the issue. 
             
             Freq - This trap occurs only when the addresses the server is listening on
                do not match the addresses configured."
    ::= { ptiSegway 0 7362 }

ptM3UASCTPServerM3UASCTPServerAddrListEqual NOTIFICATION-TYPE
    OBJECTS         { ptTrapType, ptTrapSequenceNumber, ptTrapSeverity, 
                      ptTrapProbableCause, ptTrapClearType, 
                      ptTrapDateAndTime, ptTrapItemOID, 
                      ptSGM3UASCTPServerSlot, 
                      ptSGM3UASCTPServerIPAddress1, 
                      ptSGM3UASCTPServerIPAddress2, 
                      ptSGM3UASCTPServerPort }
    STATUS          current
    DESCRIPTION     
            "M3UA SCTP Server is now listening on all expected addresses."
    ::= { ptiSegway 0 7363 }

ptSUASCTPServerSUASCTPServerAddrListMismatch NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "Indicates that SUA SCTP Server is not listening on all configured addresses.
             
             Cause - The SUA SCTP Server is configured to listen on an address
                but binding to that address/port failed.
             
             Possible Actions - Determine if another application is using the 
                desired address/port, which is preventing the server from binding
                to the address.  This can be done using IP Networking > IP Utilities > Open Sockets.
             
                Determine if the IP addresses are actually valid for the slot that the
                server is listening on.  Use Network Interaces > View Network Interfaces for the
                corresponding slot to see if the address is configured for one of the interfaces.
                If you are using hostnames, you will first need to check which addresses the hostname
                resolves to using IP Networking > Hostname Resolution (if using DNS you will need to check
                the DNS Server configuration).
             
                If using hostnames, it is possible that each address was not resolvable at startup. 
                If there are no hostname resolution alarms present for the SUA SCTP Server, it is possible
                that deactivating and reactivating the server will correct the issue. 
             
             Freq - This trap occurs only when the addresses the server is listening on
                do not match the addresses configured."
    ::= { ptiSegway 0 7364 }

ptSUASCTPServerSUASCTPServerAddrListEqual NOTIFICATION-TYPE
    OBJECTS         { ptTrapType, ptTrapSequenceNumber, ptTrapSeverity, 
                      ptTrapProbableCause, ptTrapClearType, 
                      ptTrapDateAndTime, ptTrapItemOID, 
                      ptSGSUASCTPServerSlot, ptSGSUASCTPServerIPAddress1, 
                      ptSGSUASCTPServerIPAddress2, ptSGSUASCTPServerPort }
    STATUS          current
    DESCRIPTION     
            "M3UA SCTP Server is now listening on all expected addresses."
    ::= { ptiSegway 0 7365 }

ptM3UAASPAssociationM3uaSP2KMultiAssocConnLoss NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An ASP multi association loss notification is sent when the
             connection between an ASP and SG is lost."
    ::= { ptiSegway 0 7366 }

ptM3UAASPAssociationM3uaSP2KMultiAssocConnEstablished NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An ASP multi association established notification is sent when the
             connection between an ASP and SG is established."
    ::= { ptiSegway 0 7367 }

ptM3UAASPAssociationM3uaSP2KMultiAssocDeactivated NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An M3UA multi association has been deactivated by the user. 
             Possible uses are to block an ASP from connecting whilst performing 
             configuration maintenance."
    ::= { ptiSegway 0 7368 }

ptM3UAASPAssociationM3uaSP2KMultiAssocActivated NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An M3UA multi association has been 
             activated by the user."
    ::= { ptiSegway 0 7369 }

ptMTP3NAMTP3NAsMsuDiscardSet NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MSU has been unexpectedly discarded on MTP3 NA Connection in the last 5-minute interval."
    ::= { ptiSegway 0 7370 }

ptMTP3NAMTP3NAsMsuDiscardClear NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "Clear event for MSU has been unexpectedly discarded on MTP3 NA Connection."
    ::= { ptiSegway 0 7371 }

ptSCCPNASCCPNAsMsuDiscardSet NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "An MSU has been unexpectedly discarded on SCCP NA Connection in the last 5-minute interval."
    ::= { ptiSegway 0 7372 }

ptSCCPNASCCPNAsMsuDiscardClear NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "Clear event for MSU has been unexpectedly discarded on SCCP NA Connection."
    ::= { ptiSegway 0 7373 }

ptM3UAASPM3UAMsuDiscardSet NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPIPAddress2, 
                      ptSGM3UAASPPort, ptSGM3UAASPID, ptSGM3UAASPName }
    STATUS          current
    DESCRIPTION     
            "An M3UA message has been unexpectedly discarded in the last 5-minute."
    ::= { ptiSegway 0 7374 }

ptM3UAASPM3UAMsuDiscardClear NOTIFICATION-TYPE
    OBJECTS         { ptTrapType, ptTrapSequenceNumber, ptTrapSeverity, 
                      ptTrapProbableCause, ptTrapClearType, 
                      ptTrapDateAndTime, ptTrapItemOID, 
                      ptSGM3UAASPIPAddress1, ptSGM3UAASPIPAddress2, 
                      ptSGM3UAASPPort, ptSGM3UAASPID, ptSGM3UAASPName }
    STATUS          current
    DESCRIPTION     
            "The discarded M3UA message alarm has been cleared as no further M3UA messages have been unexpectedly discarded."
    ::= { ptiSegway 0 7375 }

ptM3UAMultiAssociationASPM3UAMultiAssocDiscardSet NOTIFICATION-TYPE
    OBJECTS         { ptTrapType, ptTrapSequenceNumber, ptTrapSeverity, 
                      ptTrapProbableCause, ptTrapClearType, 
                      ptTrapDateAndTime, ptTrapItemOID, 
                      ptSGM3UAMultiAssociationASPID, 
                      ptSGM3UAMultiAssociationASPName }
    STATUS          current
    DESCRIPTION     
            "An M3UA Multi ASP message has been unexpectedly discarded in the last 5-minute."
    ::= { ptiSegway 0 7376 }

ptM3UAMultiAssociationASPM3UAMultiAssocDiscardClear NOTIFICATION-TYPE
    OBJECTS         { ptTrapType, ptTrapSequenceNumber, ptTrapSeverity, 
                      ptTrapProbableCause, ptTrapClearType, 
                      ptTrapDateAndTime, ptTrapItemOID, 
                      ptSGM3UAMultiAssociationASPID, 
                      ptSGM3UAMultiAssociationASPName }
    STATUS          current
    DESCRIPTION     
            "The discarded M3UA Multi ASP message alarm has been cleared as no further message have been discarded."
    ::= { ptiSegway 0 7377 }

ptSUAASPSUAMsuDiscardSet NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPIPAddress2, 
                      ptSGSUAASPPort, ptSGSUAASPID, ptSGSUAASPName }
    STATUS          current
    DESCRIPTION     
            "An SUA message has been unexpectedly discarded in the last 5-minute."
    ::= { ptiSegway 0 7378 }

ptSUAASPSUAMsuDiscardClear NOTIFICATION-TYPE
    OBJECTS         { ptTrapType, ptTrapSequenceNumber, ptTrapSeverity, 
                      ptTrapProbableCause, ptTrapClearType, 
                      ptTrapDateAndTime, ptTrapItemOID, 
                      ptSGSUAASPIPAddress1, ptSGSUAASPIPAddress2, 
                      ptSGSUAASPPort, ptSGSUAASPID, ptSGSUAASPName }
    STATUS          current
    DESCRIPTION     
            "The discarded SUA message alarm has been cleared as no further SUA messages have been unexpectedly discarded."
    ::= { ptiSegway 0 7379 }

ptSFGUASFGUAMsuDiscardSet NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "An MSU destined to SFG UA has been unexpectedly discarded in the last 5-minute interval."
    ::= { ptiSegway 0 7380 }

ptSFGUASFGUAMsuDiscardClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for MSU destined to SFG UA has been unexpectedly discarded."
    ::= { ptiSegway 0 7381 }

ptM3UAAppServerM3UADiscardMsuFromPeerSet NOTIFICATION-TYPE
    OBJECTS         { ptTrapType, ptTrapSequenceNumber, ptTrapSeverity, 
                      ptTrapProbableCause, ptTrapClearType, 
                      ptTrapDateAndTime, ptTrapItemOID, 
                      ptSGM3UAAppServerRoutingContext, 
                      ptSGM3UAAppServerDPC, ptSGM3UAAppServerSI, 
                      ptSGM3UAAppServerNetworkAppearance, 
                      ptSGM3UAAppServerApplicationID }
    STATUS          current
    DESCRIPTION     
            "An MSU has been unexpectedly discarded between peers on M3UA AS in the last 5-minute."
    ::= { ptiSegway 0 7382 }

ptM3UAAppServerM3UADiscardMsuFromPeerClear NOTIFICATION-TYPE
    OBJECTS         { ptTrapType, ptTrapSequenceNumber, ptTrapSeverity, 
                      ptTrapProbableCause, ptTrapClearType, 
                      ptTrapDateAndTime, ptTrapItemOID, 
                      ptSGM3UAAppServerRoutingContext, 
                      ptSGM3UAAppServerDPC, ptSGM3UAAppServerSI, 
                      ptSGM3UAAppServerNetworkAppearance, 
                      ptSGM3UAAppServerApplicationID }
    STATUS          current
    DESCRIPTION     
            "Alarm for discard MSU unexpectedly between peers on M3UA AS has been cleared as no further MSU have been unexpectedly discarded."
    ::= { ptiSegway 0 7383 }

ptSUAAppServerSUADiscardMsuFromPeerSet NOTIFICATION-TYPE
    OBJECTS         { ptTrapType, ptTrapSequenceNumber, ptTrapSeverity, 
                      ptTrapProbableCause, ptTrapClearType, 
                      ptTrapDateAndTime, ptTrapItemOID, 
                      ptSGSUAAppServerRoutingContext, 
                      ptSGSUAAppServerDPC, ptSGSUAAppServerSSN, 
                      ptSGSUAAppServerNetworkAppearance, 
                      ptSGSUAAppServerApplicationID }
    STATUS          current
    DESCRIPTION     
            "An MSU has been unexpectedly discarded between peers on SUA AS in the last 5-minute."
    ::= { ptiSegway 0 7384 }

ptSUAAppServerSUADiscardMsuFromPeerClear NOTIFICATION-TYPE
    OBJECTS         { ptTrapType, ptTrapSequenceNumber, ptTrapSeverity, 
                      ptTrapProbableCause, ptTrapClearType, 
                      ptTrapDateAndTime, ptTrapItemOID, 
                      ptSGSUAAppServerRoutingContext, 
                      ptSGSUAAppServerDPC, ptSGSUAAppServerSSN, 
                      ptSGSUAAppServerNetworkAppearance, 
                      ptSGSUAAppServerApplicationID }
    STATUS          current
    DESCRIPTION     
            "Alarm for discard MSU unexpectedly between peers on SUA AS has been cleared as no further MSU have been unexpectedly discarded."
    ::= { ptiSegway 0 7385 }

ptMTP3NAMTP3NAsDiscardMsuFromPeerSet NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "An MSU has been unexpectedly discarded between peers on MTP3 NA Connection in the last 5-minute interval."
    ::= { ptiSegway 0 7386 }

ptMTP3NAMTP3NAsDiscardMsuFromPeerClear NOTIFICATION-TYPE
    OBJECTS         { ptTrapType, ptTrapSequenceNumber, ptTrapSeverity, 
                      ptTrapProbableCause, ptTrapClearType, 
                      ptTrapDateAndTime, ptTrapItemOID, 
                      ptSGMTP3NANetworkAppearance }
    STATUS          current
    DESCRIPTION     
            "Clear event for MSU has been unexpectedly discarded between peers on MTP3 NA Connection."
    ::= { ptiSegway 0 7387 }

ptSCCPNASCCPNAsDiscardMsuFromPeerSet NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "An MSU has been unexpectedly discarded between peers on SCCP NA Connection in the last 5-minute interval."
    ::= { ptiSegway 0 7388 }

ptSCCPNASCCPNAsDiscardMsuFromPeerClear NOTIFICATION-TYPE
    OBJECTS         { ptTrapType, ptTrapSequenceNumber, ptTrapSeverity, 
                      ptTrapProbableCause, ptTrapClearType, 
                      ptTrapDateAndTime, ptTrapItemOID, 
                      ptSGSCCPNANetworkAppearance }
    STATUS          current
    DESCRIPTION     
            "Clear event for MSU has been unexpectedly discarded between peers on SCCP NA Connection."
    ::= { ptiSegway 0 7389 }

ptSFGUASFGUAExchangeDown NOTIFICATION-TYPE
    OBJECTS         { ptTrapType, ptTrapSequenceNumber, ptTrapSeverity, 
                      ptTrapProbableCause, ptTrapClearType, 
                      ptTrapDateAndTime, ptTrapItemOID, 
                      ptSGSFGUAExchangeName, ptSGSFGUAExchangeStatus }
    STATUS          current
    DESCRIPTION     
            "This trap indicates that the SFG UA exchange is down.  
             Cause: SS7 DB routing application is not listening.
               ptOriginatingOID: DYNAMIC
               ptTrapType: 2 communicationAlarm 
               ptTrapSeverity: 1 critical
               ptTrapProbableCause: 6 Communications subsystem error 
               ptTrapClearType: 1 fmic"
    ::= { ptiSegway 0 7400 }

ptSFGUASFGUAExchangeUp NOTIFICATION-TYPE
    OBJECTS         { ptTrapType, ptTrapSequenceNumber, ptTrapSeverity, 
                      ptTrapProbableCause, ptTrapClearType, 
                      ptTrapDateAndTime, ptTrapItemOID, 
                      ptSGSFGUAExchangeName, ptSGSFGUAExchangeStatus }
    STATUS          current
    DESCRIPTION     
            "This trap indicates that the SFG UA exchange is now up.  
             Cause: SS7 DB routing application is now available and ready.
               ptOriginatingOID: DYNAMIC
               ptTrapType: 2 communicationAlarm 
               ptTrapSeverity: 5 cleared 
               ptTrapProbableCause: 6 Communications subsystem error 
               ptTrapClearType: 1 fmic"
    ::= { ptiSegway 0 7401 }

ptSFGUASCCPAppServerSFGUADataDiscardSet NOTIFICATION-TYPE
    OBJECTS         { ptTrapType, ptTrapSequenceNumber, ptTrapSeverity, 
                      ptTrapProbableCause, ptTrapClearType, 
                      ptTrapDateAndTime, ptTrapItemOID, 
                      ptSGSFGUASCCPAppServerRoutingContext }
    STATUS          current
    DESCRIPTION     
            "Obsolete as of 18.1.0
             
             This trap indicates that a data message has been received  at the SCCP SFG UA
             Application Server and was discarded as routing to SFG SCCP UAs is not supported
             
             Cause - Possible causes include incorrect configuration 
             in the Gateway screening tables for the incoming linkset indicated by the DPC.
             
             Action - Check that the provisioning in gateway screening is correct.
             Freq - this trap will occur if a data message is received at an SFG UA 
             application server. It will remain active as long as there are data messages
             arriving within a 5 minute period.
             
             ptOriginatingOID: DYNAMIC
             ptTrapType: 2 communicationAlarm 
             ptTrapSeverity: 3 minor 
             ptTrapProbableCause: 6 Communications subsystem error 
             ptTrapClearType: 1 fmic"
    ::= { ptiSegway 0 7402 }

ptSFGUASCCPAppServerSFGUADataDiscardClear NOTIFICATION-TYPE
    OBJECTS         { ptTrapType, ptTrapSequenceNumber, ptTrapSeverity, 
                      ptTrapProbableCause, ptTrapClearType, 
                      ptTrapDateAndTime, ptTrapItemOID, 
                      ptSGSFGUASCCPAppServerRoutingContext }
    STATUS          current
    DESCRIPTION     
            "Obsolete as of 18.1.0
             
             This trap indicates that condition which caused the  
             discarding of data messages at an SCCP SFG UA Application
             server has been resolved or that no messages have been received in a 
             5 minute period.
             
             Action:  None
             
             Freq - this trap occurs after a provisioning change has occurred to
                    address data messages being routed to the unsupported SFG SCCP UA
                    application server.
             
             ptOriginatingOID: DYNAMIC
             ptTrapType: 2 communicationAlarm 
             ptTrapSeverity: 3 minor 
             ptTrapProbableCause: 6 Communications subsystem error 
             ptTrapClearType: 1 fmic"
    ::= { ptiSegway 0 7403 }

ptM3UAASPAssociationM3uaMultiAssocConnLoss NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An ASP multi association loss notification is sent when the
             connection between an ASP and SG is lost."
    ::= { ptiSegway 0 7404 }

ptM3UAASPAssociationM3uaMultiAssocConnEstablished NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An ASP multi association established notification is sent when the
             connection between an ASP and SG is established."
    ::= { ptiSegway 0 7405 }

ptM3UAASPAssociationM3uaMultiAssocDeactivated NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An M3UA multi association has been deactivated by the user. 
             Possible uses are to block an ASP from connecting whilst performing 
             configuration maintenance."
    ::= { ptiSegway 0 7406 }

ptM3UAASPAssociationM3uaMultiAssocActivated NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "An M3UA multi association has been 
             activated by the user."
    ::= { ptiSegway 0 7407 }

ptM3UAConfiguredASPM3UAConfASPUnresolvedHost1 NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "Indicates that M3UA Configured ASP IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7500 }

ptM3UAConfiguredASPM3UAConfASPResolvedHost1 NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "M3UA Configured ASP IP Address 1 hostname is resolved"
    ::= { ptiSegway 0 7501 }

ptM3UAConfiguredASPM3UAConfASPUnresolvedHost2 NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "Indicates that M3UA Configured ASP IP Address 2 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7502 }

ptM3UAConfiguredASPM3UAConfASPResolvedHost2 NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "M3UA Configured ASP IP Address 2 Hostname is resolved"
    ::= { ptiSegway 0 7503 }

ptM3UAConfiguredASPM3UAConfASPEndPtConflict NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "Indicates that two or more M3UA Configured ASPs have conflicting SCTP endpoints.
             
             Cause - Same transport address defined for two or more M3UA Configured ASPs.
             
             Possible Actions - Ensure that the detected SCTP endpoint conflicts are resolved. 
                A transport address can be defined for one and only one M3UA Configured ASP.
             
             Freq - This trap occurs when a transport address is defined for two or more M3UA Configured ASPs.
             "
    ::= { ptiSegway 0 7504 }

ptM3UAConfiguredASPM3UAConfASPEndPtConflictResolved NOTIFICATION-TYPE
    OBJECTS         { ptTrapType, ptTrapSequenceNumber, ptTrapSeverity, 
                      ptTrapProbableCause, ptTrapClearType, 
                      ptTrapDateAndTime, ptTrapItemOID, 
                      ptSGM3UAConfiguredASPID, ptSGM3UAConfiguredASPPort, 
                      ptSGM3UAConfiguredASPIPAddress1, 
                      ptSGM3UAConfiguredASPIPAddress2, 
                      ptSGM3UAConfiguredASPName }
    STATUS          current
    DESCRIPTION     
            "IP Conflicts with existing M3UA Configured ASPs resolved"
    ::= { ptiSegway 0 7505 }

ptSUAConfiguredASPSUAConfASPUnresolvedHost1 NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "Indicates that SUA Configured ASP IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7600 }

ptSUAConfiguredASPSUAConfASPResolvedHost1 NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "SUA Configured ASP IP Address 1 hostname is resolved"
    ::= { ptiSegway 0 7601 }

ptSUAConfiguredASPSUAConfASPUnresolvedHost2 NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "Indicates that SUA Configured ASP IP Address 2 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7602 }

ptSUAConfiguredASPSUAConfASPResolvedHost2 NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "SUA Configured ASP IP Address 2 hostname is resolved"
    ::= { ptiSegway 0 7603 }

ptSUAConfiguredASPSUAConfASPEndPtConflict NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "Indicates that two or more SUA Configured ASPs have conflicting SCTP endpoints.
             
             Cause - Same transport address defined for two or more SUA Configured ASPs.
             
             Possible Actions - Ensure that the detected SCTP endpoint conflicts are resolved. 
                A transport address can be defined for one and only one SUA Configured ASP.
             
             Freq - This trap occurs when a transport address is defined for two or more SUA Configured ASPs.
             "
    ::= { ptiSegway 0 7604 }

ptSUAConfiguredASPSUAConfASPEndPtConflictResolved NOTIFICATION-TYPE
    OBJECTS         { ptTrapType, ptTrapSequenceNumber, ptTrapSeverity, 
                      ptTrapProbableCause, ptTrapClearType, 
                      ptTrapDateAndTime, ptTrapItemOID, 
                      ptSGSUAConfiguredASPID, ptSGSUAConfiguredASPPort, 
                      ptSGSUAConfiguredASPIPAddress1, 
                      ptSGSUAConfiguredASPIPAddress2, 
                      ptSGSUAConfiguredASPName }
    STATUS          current
    DESCRIPTION     
            "IP Conflicts with existing SUA Configured ASPs resolved"
    ::= { ptiSegway 0 7605 }

ptM3UAASPAssociationM3UAASPAssocUnresolvedLocalHost1 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "Indicates that M3UA ASP Association Local IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7700 }

ptM3UAASPAssociationM3UAASPAssocResolvedLocalHost1 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "M3UA ASP Association Local IP Address 1 hostname is resolved"
    ::= { ptiSegway 0 7701 }

ptM3UAASPAssociationM3UAASPAssocUnresolvedLocalHost2 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "Indicates that M3UA ASP Association Local IP Address 2 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7702 }

ptM3UAASPAssociationM3UAASPAssocResolvedLocalHost2 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "M3UA ASP Association Local IP Address 2 hostname is resolved"
    ::= { ptiSegway 0 7703 }

ptM3UAASPAssociationM3UAASPAssocUnresolvedRemoteHost1 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress1, 
                      ptSGM3UAASPAssociationRemoteIPAddress2, 
                      ptSGM3UAASPAssociationRemoteIPAddress2, 
                      ptSGM3UAASPAssociationRemotePort, 
                      ptSGM3UAASPAssociationRemotePort }
    STATUS          current
    DESCRIPTION     
            "Indicates that M3UA ASP Association Remote IP Address 1 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7704 }

ptM3UAASPAssociationM3UAASPAssocResolvedRemoteHost1 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress1, 
                      ptSGM3UAASPAssociationRemoteIPAddress2, 
                      ptSGM3UAASPAssociationRemoteIPAddress2, 
                      ptSGM3UAASPAssociationRemotePort, 
                      ptSGM3UAASPAssociationRemotePort }
    STATUS          current
    DESCRIPTION     
            "M3UA ASP Association Remote IP Address 1 hostname is resolved"
    ::= { ptiSegway 0 7705 }

ptM3UAASPAssociationM3UAASPAssocUnresolvedRemoteHost2 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress1, 
                      ptSGM3UAASPAssociationRemoteIPAddress2, 
                      ptSGM3UAASPAssociationRemoteIPAddress2, 
                      ptSGM3UAASPAssociationRemotePort, 
                      ptSGM3UAASPAssociationRemotePort }
    STATUS          current
    DESCRIPTION     
            "Indicates that M3UA ASP Association Remote IP Address 2 hostname is not resolvable.
             
             Cause - The SG is unable to resolve the hostname.
             
             Possible Actions - If the DSC has been set up to use a DNS server, 
                ensure the DNS server is reachable and confirm that the hostname
                has been configured.
             
                If the hostname is intended to resolve locally, ensure the proper hostname entry 
                has been added using IP Networking > Hostname Resolution.
             
             Freq - This trap occurs when the configured hostname becomes unresolvable.
             "
    ::= { ptiSegway 0 7706 }

ptM3UAASPAssociationM3UAASPAssocResolvedRemoteHost2 NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress1, 
                      ptSGM3UAASPAssociationRemoteIPAddress2, 
                      ptSGM3UAASPAssociationRemoteIPAddress2, 
                      ptSGM3UAASPAssociationRemotePort, 
                      ptSGM3UAASPAssociationRemotePort }
    STATUS          current
    DESCRIPTION     
            "M3UA ASP Association Remote IP Address 2 hostname is resolved"
    ::= { ptiSegway 0 7707 }

ptM3UAASPAssociationM3UAASPAssocEndPtConflict NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "Indicates that an M3UA ASP Association has conflicting SCTP endpoints with one or more existing
             M3UA ASP Association and/or one or more M3UA/SUA SCTP Servers .
             
                 Cause - Same transport address defined for two or more M3UA ASP Associations, or for both 
                 an M3UA ASP Association and an M3UA/SUA SCTP server.
             
                 Possible Actions - Ensure that the detected SCTP endpoint conflicts are resolved. 
                    A transport address can be defined for one and only one M3UA ASP Association or M3UA/SUA SCTP Server.
                 
                 Freq - This trap occurs when a transport address is defined for two or more SUA Configured ASPs.
             "
    ::= { ptiSegway 0 7708 }

ptM3UAASPAssociationM3UAASPAssocEndPtConflictResolved NOTIFICATION-TYPE
    OBJECTS         { ptTrapType, ptTrapSequenceNumber, ptTrapSeverity, 
                      ptTrapProbableCause, ptTrapClearType, 
                      ptTrapDateAndTime, ptTrapItemOID, 
                      ptSGM3UAASPAssociationAssociationID, 
                      ptSGM3UAASPAssociationSlot, 
                      ptSGM3UAASPAssociationRemoteIPAddress1, 
                      ptSGM3UAASPAssociationRemoteIPAddress2, 
                      ptSGM3UAASPAssociationRemotePort, 
                      ptSGM3UAASPAssociationLocalIPAddress1, 
                      ptSGM3UAASPAssociationLocalIPAddress2, 
                      ptSGM3UAASPAssociationLocalPort }
    STATUS          current
    DESCRIPTION     
            "IP Conflicts with existing M3UA ASP Associations or M3UA/SUA SCTP Servers resolved"
    ::= { ptiSegway 0 7709 }

ptLinksetLinksetPCMappingInUse NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "The Linkset PC Mapping field is not empty and so PC Mapping will be performed on this linkset."
    ::= { ptiSegway 0 8000 }

ptLinksetLinksetPCMappingEmpty NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "The Linkset PC Mapping field is empty and PC Mapping will NOT be performed on this linkset."
    ::= { ptiSegway 0 8001 }

ptLinksetLinksetOPCVerificationDisabled NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "The Linkset OPC verification field is set to a value other than enabled. Please verify the performed OPC checks are required"
    ::= { ptiSegway 0 8002 }

ptLinksetLinksetOPCVerificationEnabled NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "The Linkset OPC verification field is set to enabled. Standard OPC verification will be performed for incoming message on this linkset"
    ::= { ptiSegway 0 8003 }

ptLocalRedirectRecordLocalRedirectDuplicateThrottleOn NOTIFICATION-TYPE
    OBJECTS         { ptTrapType, ptTrapSequenceNumber, ptTrapSeverity, 
                      ptTrapProbableCause, ptTrapClearType, 
                      ptTrapDateAndTime, ptTrapItemOID, 
                      ptMTPLocalRedirectRecordDPC, 
                      ptMTPLocalRedirectRecordMessageCategory }
    STATUS          current
    DESCRIPTION     
            "The Local Redirect Record Duplicate Throttle has hit the maximum limit."
    ::= { ptiSegway 0 8004 }

ptLocalRedirectRecordLocalRedirectDuplicateThrottleOff NOTIFICATION-TYPE
    OBJECTS         { ptTrapType, ptTrapSequenceNumber, ptTrapSeverity, 
                      ptTrapProbableCause, ptTrapClearType, 
                      ptTrapDateAndTime, ptTrapItemOID, 
                      ptMTPLocalRedirectRecordDPC, 
                      ptMTPLocalRedirectRecordMessageCategory }
    STATUS          current
    DESCRIPTION     
            "  This event indicates that the Local Redirect Record has not hit its maximum rate for
             duplicating MSUs during the last five minutes.
             The Local Redirect Record Duplicate is no longer at the maximum limit.
             \nClears event 8004 LocalRedirectDuplicateThrottleOn."
    ::= { ptiSegway 0 8005 }

ptMigrationRecordMigrationRecordSetToDiscard NOTIFICATION-TYPE
    OBJECTS         { ptTrapType, ptTrapSequenceNumber, ptTrapSeverity, 
                      ptTrapProbableCause, ptTrapClearType, 
                      ptTrapDateAndTime, ptTrapItemOID, 
                      ptMTPMigrationRecordOPC, ptMTPMigrationRecordDPC, 
                      ptMTPMigrationRecordMessageCategory }
    STATUS          current
    DESCRIPTION     
            "A Migration Record has its New DPC attribute set to Discard"
    ::= { ptiSegway 0 8006 }

ptMigrationRecordMigrationRecordSetToDiscardClear NOTIFICATION-TYPE
    OBJECTS         { ptTrapType, ptTrapSequenceNumber, ptTrapSeverity, 
                      ptTrapProbableCause, ptTrapClearType, 
                      ptTrapDateAndTime, ptTrapItemOID, 
                      ptMTPMigrationRecordOPC, ptMTPMigrationRecordDPC, 
                      ptMTPMigrationRecordMessageCategory }
    STATUS          current
    DESCRIPTION     
            "A Migration Record no longer has its New DPC attribute set to Discard"
    ::= { ptiSegway 0 8007 }

ptLSLinkSs7L3LinkAlarmsDisabled NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "LS Link alarms are disabled."
    ::= { ptiSegway 0 8100 }

ptLSLinkSs7L3LinkAlarmsEnabled NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "LS Link alarms are enabled."
    ::= { ptiSegway 0 8101 }

ptM2PALinkM2paL3LinkDeactivated NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been deactivated.
             Causes ,Corrective actions and Frequency:  
               1) ptSpecificTrapCause = operatorDeactivation 
                  Cause  - Operator deactivates link.
                  Action - Operator can activate the link again.
                  Freq   - Operator dependant. 
                   
               2) ptSpecificTrapCause = timerT17Expiry
                  Cause  - Event appears between each attempt to perform an initial 
                           alignment procedure. After an unsuccessful attempt, a delay
                           T17 expires before the next attempt is initiated.
                  Action - Operator can activate the link.  
                  Freq   - T19 expiry, T19 can take a value between 800 - 1500 ms
             
               3) ptSpecificTrapCause = unknownCause
             
             References
               1) Table 1 Q.752, SL Failure
               2) Q.704 (07/96) Section 12.2 
                             
               ptOriginatingOID:    DYNAMIC ptLink
               ptTrapType:          2 communicationAlarm
               ptTrapSeverity:      3 minor
               ptTrapProbableCause: 29 Loss of signal   
               ptTrapClearType:     1 fmic
             "
    ::= { ptiSegway 0 8103 }

ptM2PALinkM2paL3LinkActivated NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been activated
             either by operator or as a result of a successful restoration 
             which was initiated upon detection of an inactive link.
             This trap could also be generated at restart without a previous
             corresponding trap 201.
             
             References
               1)  Q.752, SL Restoration
               2)  Q.704, (07/96) Section 12.2
               
               ptOriginatingOID:    DYNAMIC ptLink
               ptTrapType:          2 communicationAlarm
               ptTrapSeverity:      5 cleared
               ptTrapProbableCause: 29 Loss of signal 
               ptTrapClearType:     1 fmic              
             "
    ::= { ptiSegway 0 8104 }

ptM2PALinkM2paL3LinkLocalInhibited NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been inhibited 
             by operator at the local node.
               Cause  - Operator inhibits the link.
               Action - Operator can uninhibit the link.
               Freq   - Operator dependant. 
             
             References
               1) Table 2 Q.752, Start of local inhibition
               2) Q.704 , (07/96) Section 10       
             
               ptOriginatingOID:    DYNAMIC ptLink
               ptTrapType:          11 qualityofserviceAlarm
               ptTrapSeverity:      4  warning
               ptTrapProbableCause: 43 Resource at or near capacity   
               ptTrapClearType:     1 fmic
             "
    ::= { ptiSegway 0 8105 }

ptM2PALinkM2paL3LinkLocalUninhibited NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been uninhibited at the 
             local node by operator.
             
             References
               1) Table 2 Q.752, End of local inhibition
               2) Q.704 , (07/96) Section 10       
             
               ptOriginatingOID:    DYNAMIC ptLink
               ptTrapType:          11 qualityofserviceAlarm
               ptTrapSeverity:      5 cleared
               ptTrapProbableCause: 43 Resource at or near capacity
               ptTrapClearType:     1 fmic     
             "
    ::= { ptiSegway 0 8106 }

ptM2PALinkM2paL3LinkRemoteInhibited NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been inhibited at a 
             remote node.
               Cause  - Operator has inhibited remote end of the link.
               Action - Link is inhibited until the operator uninhibits the 
                        remote end of the link.
               Freq   - Operator dependant. 
             
             References
               1) Table 2 Q.752, Start of remote inhibition
               2) Q.704 , (07/96) Section 10       
             
               ptOriginatingOID:    DYNAMIC ptLink
             	 		 		 		      ptTrapType:          11 qualityofserviceAlarm 
               ptTrapSeverity:      4 warning
               ptTrapProbableCause: 43 Resource at or near capacity  
               ptTrapClearType:     1 fmic         
             "
    ::= { ptiSegway 0 8107 }

ptM2PALinkM2paL3LinkRemoteUninhibited NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been uninhibited 
             at the remote end of a link. This can be requested by the operator
             or by signaling routing control function . Signaling routing 
             control will initiate signaling link uninhibit if an inhibited 
             link is found to be a member of a link set in a route to a destination
             which has become inaccessible. 
             
             References
               1) Table 2 Q.752, End of remote inhibition
               2) Q.704 , (07/96) Section 10       
             
               ptOriginatingOID:    DYNAMIC ptLink
             	 		 		 		      ptTrapType:          11 qualityofserviceAlarm
               ptTrapSeverity:      5 cleared
               ptTrapProbableCause: 43 Resource at or near capacity  
               ptTrapClearType:     1 fmic             
             "
    ::= { ptiSegway 0 8108 }

ptM2PALinkM2paL3LinkInhibitDenied NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an attempt to inhibit an M2PA signaling link 
             has failed.
             
             Causes ,Corrective actions and Frequency: 
               1) ptSpecificTrapCause = DPC not available 
                  Cause  - This trap occurs when a request to inhibit a link will
                           result in a destination becoming inaccessible and therefore
                           the request is denied.
                  Action - Operator will have to create another link 
                           to access the destination before attempting to inhibit this 
                           one.
                  Freq   - Depends on how many destinations have single links and how
                           often management wants to inhibit them. 
             
               2) ptSpecificTrapCause = Negative ACK from remote end
                  Cause  - This trap occurs when a request to inhibit the link at the 
                           remote end of a link results in a destination becoming 
                           inaccessible. 
                  Action - Operator will have to wait until another link is available
                           to the destination before inhibiting this one.  
                  Freq   - Depends on how many destinations have single links and how
                           often management wants to inhibit them. 
             
               3) ptSpecificTrapCause = UnknownCause 
             
             References
               1) Q.704 , (07/96) Section 10.2       
             
             
              ptOriginatingOID:    DYNAMIC ptLink
              ptTrapType:          10 processingAlarm 
              ptTrapSeverity:      2 major
              ptTrapProbableCause: 56 Underlying resource unavailable 
              ptTrapClearType:     2 oic       
             "
    ::= { ptiSegway 0 8109 }

ptM2PALinkM2paL3LinkUninhibitDenied NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an attempt to uninhibit an M2PA signaling link has failed.
             
             Cause  - A request to uninhibit a link from the local node to a 
                      destination will fail if all the routes to the destination
                      are unavailable.
             Action - Operator will have to wait until a route to the destination
                      becomes available in order that it can send an uninhibit link 
                      message. 
             Freq   - Operator dependant.
             
             References
             1) Q.704 , (07/96) Section 10.2       
             
             ptOriginatingOID:    DYNAMIC ptLink
             ptTrapType:          10 processingAlarm
             ptTrapSeverity:      4 warning
             ptTrapProbableCause: 56 Underlying resource unavailable
             ptTrapClearType:     2 oic
             "
    ::= { ptiSegway 0 8111 }

ptM2PALinkM2paL3LinkRemoteBlocked NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been blocked at a remote node.
             
             Cause  - Signaling link is blocked at the remote node of the link
                      by operator intervention or due to processor outage.
             Action - The link will be unblocked when the remote node of the 
                      link become unblocked. 
             Freq   - Operator dependant.
             
             References
             1) Table 2 Q.752 Start of Remote Processor Outage
             2) Q.704 Section 3.3.5      
             
             ptOriginatingOID:      DYNAMIC ptLink
             ptTrapType:            2 communicationAlarm
             ptTrapSeverity:        3 minor
             ptTrapProbableCause:   42 Remote node transmission error  
             ptTrapClearType:       1 fmic
             "
    ::= { ptiSegway 0 8113 }

ptM2PALinkM2paL3LinkRemoteUnblocked NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been unblocked at a remote node.
             
             Causes ,Corrective actions and Frequency  
               1) ptSpecificTrapCause = linkDeactivated 
                  Cause  -  Unknown Cause
             
               2) ptSpecificTrapCause = unknownCause
             
             References
               1) Table 2 Q.752 Stop of Remote Processor Outage
               2) Q.704 Section 3.3.5      
             
               ptOriginatingOID:    DYNAMIC ptLink
               ptTrapType:          2 communicationAlarm
               ptTrapSeverity:      5 cleared
               ptTrapProbableCause: 42 Remote node transmission error  
               ptTrapClearType:     1 fmic
             "
    ::= { ptiSegway 0 8114 }

ptM2PALinkM2paL3LinkLocalBlocked NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been blocked at the local node by 
             the operator.
             
                  Cause  - Operator blocks a link.
                  Action - Operator can unblock the link. 
                  Freq   - Operator dependant.
             
             
                References
                  1) Q.704 Section 3.2      
             
                  ptOriginatingOID:    DYNAMIC ptLink
                  ptTrapType:          10 processingAlarm
                  ptTrapSeverity:      3 minor
                  ptTrapProbableCause: 56 Underlying resource unavailable
                  ptTrapClearType:     1 fmic       
             "
    ::= { ptiSegway 0 8115 }

ptM2PALinkM2paL3LinkLocalUnblocked NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that an M2PA signaling link has been unblocked at the local node 
             by the operator.
             
                References
                 1) Q.704 Section 3.2      
             
                 ptOriginatingOID:    DYNAMIC ptLink
                 ptTrapType:          10 processingAlarm
                 ptTrapSeverity:      5 cleared
                 ptTrapProbableCause: 56 Underlying resource unavailable
                 ptTrapClearType:     1 fmic
             "
    ::= { ptiSegway 0 8116 }

ptM2PALinkM2paLinkCongested NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkLinkName }
    STATUS          current
    DESCRIPTION     
            "This trap indicates that an M2PA signaling link is congested.
             
             Causes and Corrective Action  
               1) ptSpecificTrapCause = managementInitiated 
                  Cause  - Protocol manager detects the condition.  
             
               2) ptSpecificTrapCause = linkCongestion 
                  Cause  - Trap occurs when the thresholds for the number of MSUs
                           in the transmission or re-transmission buffer are exceeded.  
                  Action - Wait until the MSUs are sent .
             
             References
               1) Q.704 , Section 3.8.2 
             
               ptOriginatingOID:    DYNAMIC ptLink
               ptTrapType:          10 processingAlarm
               ptTrapSeverity:      3 minor
               ptTrapProbableCause: 49 Storage capacity problem
               ptTrapClearType:     1 fmic
             "
    ::= { ptiSegway 0 8119 }

ptM2PALinkM2paLinkUncongested NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkLinkName }
    STATUS          current
    DESCRIPTION     
            "This trap indicates that an M2PA signaling link is no longer congested.
             
             Causes and Frequency  
               1) ptSpecificTrapCause = managementInitiated 
                  Cause  - Protocol Manager detects the condition
             
               2) ptSpecificTrapCause = linkUncongested 
                  Cause  - Trap occurs when the number of MSUs in the transmission
                           or re-transmission buffer goes from a value in excess of
                           the thresholds for congestion to a value which is less 
                           than the thresholds.   
                  Freq   - Dependant on throughput of MSUs .
             
             References
               1) Q.704 , Section 3.8.2 
             
               ptOriginatingOID:    DYNAMIC ptLink
               ptTrapType:          10 processingAlarm
               ptTrapSeverity:      5 cleared
               ptTrapProbableCause: 49 Storage capacity problem
               ptTrapClearType:     1 fmic       
             "
    ::= { ptiSegway 0 8120 }

ptM2PALinkM2paLinkUnaligned NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL2State, 
                      ptMTPM2PALinkLinkName }
    STATUS          current
    DESCRIPTION     
            "This trap indicates that an M2PA signaling link has lost alignment.
             
             Cause  - After a signaling link failure is detected, signaling link
                      initial alignment will take place. The Alignment procedure 
                      passes through a number of states and when the procedure 
                      enters the state not aligned this trap is sent.
             Action - If the initial alignment procedure does not work, then the 
                      operator will have to intervene in order that the link 
                      alignment succeeds.
             Freq   - This trap will continue to appear each time the initial 
                      alignment procedure enters the state not aligned. This
                      may happen a number of times as the initial alignment 
                      procedure is repeated until alignment has been completed
                      successfully. 
                   
             References
               1) Q.703 , (07/96) Section 7.3 
             
             
               ptOriginatingOID:    DYNAMIC ptLink
               ptTrapType:          2 communicationAlarm
               ptTrapSeverity:      3 minor
               ptTrapProbableCause: 6 Communications subsystem error
               ptTrapClearType:     1 fmic       
             "
    ::= { ptiSegway 0 8121 }

ptM2PALinkM2paLinkAligned NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL2State, 
                      ptMTPM2PALinkLinkName }
    STATUS          current
    DESCRIPTION     
            "This trap indicates that an M2PA signaling link has been aligned.
             
             Cause  - After a signaling link failure is detected, signaling link
                      initial alignment will take place. The Alignment procedure 
                      passes through a number of states and when the procedure 
                      enters the state aligned this trap is sent.
             Freq   - Once the alignment procedure enters the aligned state then
                      the alignment procedure will not be repeated. 
                   
             References
             1) Q.703 , (07/96) Section 7.3 
             
             ptOriginatingOID:    DYNAMIC ptLink
             ptTrapType:          2 communicationAlarm
             ptTrapSeverity:      5 cleared
             ptTrapProbableCause: 6 Communications subsystem error 
             ptTrapClearType:     1 fmic       
             "
    ::= { ptiSegway 0 8122 }

ptM2PALinkM2paL3LinkUsageAlarmSet NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "Obsolete as of 8.2.0.
             
             This trap indicates that the average traffic over this link exceeds 
             predefined threshold. There is potential for traffic loss if this 
             condition persists
             
               References
                 This is PTI proprietary trap.
             
                 ptOriginatingOID:    DYNAMIC ptLink
                 ptTrapType:          11 qualityofserviceAlarm
                 ptTrapSeverity:      4 warning
                 ptTrapProbableCause: 51 Threshold crossed 
                 ptTrapClearType:     2 oic              
             "
    ::= { ptiSegway 0 8124 }

ptM2PALinkM2paL3LinkFailCraftRefTimerExpiry NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that the fail link craft referral timer expired
             without having signaling link activated. The fail link craft referral timer
             is the duration allowed for a signaling link to come into service.
             After expiry of this timer, this alarm is generated as per
             the system configuration.
             
               References
                 1) GR246 Core, section 12.2.1, 12.3.1, 12.3.2
                 2) GR-82-CORE,  CR6-43 [673]
                 3) GR-310-CORE, Issue 3, Section 8.1
                 
                 ptOriginatingOID:    DYNAMIC ptLink
                 ptTrapType:          2 communicationAlarm
                 ptTrapSeverity:      4 warning
                 ptTrapProbableCause: 29 Loss of signal 
                 ptTrapClearType:     2 oic
             "
    ::= { ptiSegway 0 8125 }

ptM2PALinkM2paLinkSCTPUnavailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "This trap indicates that a signaling link is unavailable
             for user traffic because the underlying SCTP Association is
             unavailable.
             Cleared by m2paLinkSCTPAvailable.
             
                 Cause  - Most likely an IP Network issues, or perhaps
                          communication was lost to a DRE.
                 
                 Action - Check the availability of the corresponding DRE.
                          If available, troubleshoot the IP connectivity.
             
                 Freq   - Operator dependant.
             
               References
                 1) GR310CORE Issue 3 Section 8.6 (REPT-SCTP-ASOCTRMD)
             
                 ptOriginatingOID:      DYNAMIC ptLink
                 ptTrapType:            2 communicationAlarm
                 ptTrapSeverity:        3 minor
                 ptTrapProbableCause:  29 Loss of signal   
                 ptTrapClearType:       1 fmic
             "
    ::= { ptiSegway 0 8126 }

ptM2PALinkM2paLinkSCTPAvailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "This trap indicates that an M2PA SCTP Association
             has been established.
             Clears m2paLinkSCTPUnavailable.
             
             References
               1) GR310CORE Issue 3 Section 8.6 (REPT-SCTP-ASOCESTB)
             
               ptOriginatingOID:      DYNAMIC ptLink
               ptTrapType:            2 communicationAlarm
               ptTrapSeverity:        5 cleared
               ptTrapProbableCause:  29 Loss of signal   
               ptTrapClearType:       1 fmic
             "
    ::= { ptiSegway 0 8127 }

ptM2PALinkM2paLinkSCTPPathUnavailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "This trap indicates that the SCTP Association that
             carries M2PA Traffic is operating in a vulnerable
             state, an additional path failure could cause a
             link failure.
             Cleared by m2paLinkSCTPPathAvailable.
             
                 Cause  - Most likely an IP Network issue.
                 
                 Action - Troubleshoot IP connectivity.
             
                 Freq   - Operator dependant.
             
               References
                 This trap is implementation specific.
             
                 ptOriginatingOID:      DYNAMIC ptLink
                 ptTrapType:            2 communicationAlarm
                 ptTrapSeverity:        3 minor
                 ptTrapProbableCause:  29 Loss of signal   
                 ptTrapClearType:       1 fmic
             "
    ::= { ptiSegway 0 8128 }

ptM2PALinkM2paLinkSCTPPathAvailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "This trap indicates that the SCTP Association that
             carries M2PA Traffic is no longer operating with a
             path failure.
             Clears m2paLinkSCTPPathUnavailable.
             
             References
               This trap is implementation specific.
             
               ptOriginatingOID:      DYNAMIC ptLink
               ptTrapType:            2 communicationAlarm
               ptTrapSeverity:        5 cleared
               ptTrapProbableCause:  29 Loss of signal   
               ptTrapClearType:       1 fmic
             "
    ::= { ptiSegway 0 8129 }

ptM2PALinkM2paL3LinkUsageHighSet NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8130 }

ptM2PALinkM2paL3LinkUsageHighClear NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8131 }

ptM2UALinkM2uaL3LinkUsageHighSet NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8132 }

ptM2UALinkM2uaL3LinkUsageHighClear NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8133 }

ptLSLinkSs7L3LinkUsageHighSet NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8134 }

ptLSLinkSs7L3LinkUsageHighClear NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8135 }

ptATMLinkAtmL3LinkUsageHighSet NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8136 }

ptATMLinkAtmL3LinkUsageHighClear NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8137 }

ptAnnexALinkAnnexaL3LinkUsageHighSet NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8138 }

ptAnnexALinkAnnexaL3LinkUsageHighClear NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8139 }

ptATMLinkAtmL3LinkAlarmsDisabled NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "ATM Link alarms are disabled."
    ::= { ptiSegway 0 8140 }

ptATMLinkAtmL3LinkAlarmsEnabled NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "ATM Link alarms  are enabled."
    ::= { ptiSegway 0 8141 }

ptAnnexALinkAnnexaL3LinkAlarmsDisabled NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "Annex A Link alarms are disabled."
    ::= { ptiSegway 0 8142 }

ptAnnexALinkAnnexaL3LinkAlarmsEnabled NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "Annex A Link alarms are enabled."
    ::= { ptiSegway 0 8143 }

ptM2UALinkM2uaL3LinkAlarmsDisabled NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "M2UA Link alarms are disabled."
    ::= { ptiSegway 0 8144 }

ptM2UALinkM2uaL3LinkAlarmsEnabled NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "M2UA Link alarms are enabled."
    ::= { ptiSegway 0 8145 }

ptM2PALinkM2paL3LinkAlarmsDisabled NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "M2PA Link alarms are disabled."
    ::= { ptiSegway 0 8146 }

ptM2PALinkM2paL3LinkAlarmsEnabled NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "M2PA Link alarms are enabled."
    ::= { ptiSegway 0 8147 }

ptLinksetCLinkLongMsuSupportFailureSet NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This alarm indicates that the Network Appearance (NA) supports
             messages larger than 273, but the C-Linkset does not have the 
             long MSU Support option set to enabled. MTP3B traffic may be 
             lost if redirected over the C-Linkset.
             
             Action: 
               - ensure that the mate STP can support long MSUs and set
                 the Long MSU Support option to ENABLED. - or - 
               - deactivate the C-link linkset - or - 
               - reduce the NA Maximum MSU Length to 273 bytes.
             
             Freq - this trap occurs during provisioning or when the SNM
                    application is restarted.
             
                ptOriginatingOID:    DYNAMIC ptLinkset
                ptTrapType:          2 communicationAlarm 
                ptTrapSeverity:      3 minor 
                ptTrapProbableCause: 6 Communications subsystem error 
                ptTrapClearType:     1 fmic
             "
    ::= { ptiSegway 0 8148 }

ptLinksetCLinkLongMsuSupportFailureClear NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that condition set by C-link linkset not
             supporting long MSUs and the MTP NA Maximum MSU Length option
             set above 273 bytes has been resolved. 
             
             Action:  None
             
             Freq - this trap occurs after a provisioning change has occurred to 
                    address the conflict between the NA and the C-link linkset.
             
                ptOriginatingOID:    DYNAMIC ptLinkset
                ptTrapType:          2 communicationAlarm 
                ptTrapSeverity:      5 clear 
                ptTrapProbableCause: 6 Communications subsystem error 
                ptTrapClearType:     1 fmic
             "
    ::= { ptiSegway 0 8149 }

ptLinksetSs7LinksetHalfOfLinksUnavailable NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that at least half of the links of an SS7
             linkset are unavailable for user traffic.
             
             Cause  - The linkset has at least half of the links unavailable.
                      Possible reasons include:
                      - Linkset just started alignment procedure
                      - Links within linkset are no longer aligned
                       
             Action - Depends on cause 
             Freq   - This trap will appear when half of the links are unavailable 
             
                ptOriginatingOID:    DYNAMIC ptLinkset
                ptTrapType:          2 communicationAlarm 
                ptTrapSeverity:      2 major 
                ptTrapProbableCause: 6 Communications subsystem error 
                ptTrapClearType:     1 fmic
             "
    ::= { ptiSegway 0 8150 }

ptLinksetSs7LinksetHalfOfLinksAvailable NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that more than half of the links of an
             SS7 linkset are available
             
             Cause  - The linkset has more than half of the links available
                       
             Action - Depends on cause 
             Freq   - This trap will appear when more than half of the links
                      become available 
             
                ptOriginatingOID:    DYNAMIC ptLinkset
                ptTrapType:          2 communicationAlarm 
                ptTrapSeverity:      2 cleared 
                ptTrapProbableCause: 6 Communications subsystem error 
                ptTrapClearType:     1 fmic
             "
    ::= { ptiSegway 0 8151 }

ptLinksetSs7LinksetLongMsuDiscard NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetLinksetName }
    STATUS          current
    DESCRIPTION     
            "This trap indicates that a long MSU message has been received and was
             discarded in an attempt to route on a linkset that does not support
             Long MSU messages.
             This is a stateless trap (no alarm).
             
             Cause - Possible causes include incorrect setting of the  Long MSU Support
             option for the linkset. Also adjacent node, application or user part could 
             be sending long MSUs without the correct network configuration.
             
             Action - Check that the provisioning is correct.
             Freq - this trap will occur up to the maximum number of times N in the 
                    interval time M where N and M are defined for the host MTP3 NA.
             
                ptOriginatingOID:    DYNAMIC ptLinkset
                ptTrapType:          2 communicationAlarm 
                ptTrapSeverity:      3 minor 
                ptTrapProbableCause: 6 Communications subsystem error 
                ptTrapClearType:     1 fmoic
             "
    ::= { ptiSegway 0 8152 }

ptMTP3NALongMsuUnsupportedSet NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that a long MSU message has been received and was
             discarded in an attempt to route on a linkset, user part or app id that 
             does not support Long MSU messages. 
             
             This alarm will persist for the duration of the timer 
             Long MSU Discard Interval from the time of the last 
             discarded long MSU.
             
             Cause - Possible causes include incorrect setting of the  Long MSU Support
             option for the linkset, or a user part or app id not registered as 
             supporting long MSUs. Another cause could be an adjacent node or user part 
             that could be sending long MSUs without the correct NA configuration 
             in the Maximum MSU Length attribute.
             
             Action - Check that the provisioning is correct. See the sys logs and debug logs
                      for more details on the MSUs that were discarded.
             Freq - this trap will occur while long MSUs are being sent to a linkset, 
                    user part or app ID, for the duration defined by the 
                    NA attribute: Long MSU Discard Interval.  If another Long MSU is 
                    discarded during the interval, then the timer will restart. 
                    When the interval timer expires, the dashboard alarm will be removed.
             
                ptOriginatingOID:    DYNAMIC ptLinkset
                ptTrapType:          2 communicationAlarm 
                ptTrapSeverity:      3 minor 
                ptTrapProbableCause: 6 Communications subsystem error 
                ptTrapClearType:     1 fmic
             "
    ::= { ptiSegway 0 8153 }

ptMTP3NALongMsuUnsupportedClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that the timer that is monitoring the attempted
             routing of a long MSU message has expired and no new long MSU
             routing failures have occurred. The previous alarm has been cleared.
             
             Action - No action required
             Freq - this trap once after the timer has expired for monitoring long MSU
                    discards.
             
                ptOriginatingOID:    DYNAMIC ptLinkset
                ptTrapType:          2 communicationAlarm 
                ptTrapSeverity:      5 clear 
                ptTrapProbableCause: 6 Communications subsystem error 
                ptTrapClearType:     1 fmic
             "
    ::= { ptiSegway 0 8154 }

ptRoutesetRoutesetDestCongested NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "This trap indicates that destination is congested.
             Cleared by routesetDestCongestedRecovery.
             "
    ::= { ptiSegway 0 8155 }

ptMTP3NANodeSNMHostGoingStandby NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "SNM Host going Standby.
             This is a stateless trap (no alarm)."
    ::= { ptiSegway 0 8156 }

ptMTP3NANodeSNMPeerHostUnavailable NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "SNM Peer Host unavailable. "
    ::= { ptiSegway 0 8157 }

ptMTP3NANodeSNMPeerHostAvailable NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "SNM Peer Host available. "
    ::= { ptiSegway 0 8158 }

ptMTP3NANodeSNMPeerHostShuttingDown NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "SNM Peer Host available.
             This is a stateless trap (no alarm)."
    ::= { ptiSegway 0 8159 }

ptRegisteredUPUserPartLongMsuDiscard NOTIFICATION-TYPE
    OBJECTS         { ptTrapType, ptTrapSequenceNumber, ptTrapSeverity, 
                      ptTrapProbableCause, ptTrapClearType, 
                      ptTrapDateAndTime, ptTrapItemOID, 
                      ptMTPRegisteredUPContext, 
                      ptMTPRegisteredUPPointCode, ptMTPRegisteredUPSI }
    STATUS          current
    DESCRIPTION     
            "This trap indicates that a long MSU message has been received and was
             discarded in an attempt to route on a user part that does not support
             long MSUs.
                   ptOriginatingOID:    DYNAMIC ptLinkset
                   ptTrapType:          2 communicationAlarm 
                   ptTrapSeverity:      3 Minor 
                   ptTrapProbableCause: 6 Communications subsystem error 
                   ptTrapClearType:     1 fmic
                   "
    ::= { ptiSegway 0 8160 }

ptMTP3NANodeL4LostAppConnection NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "Lost some L4 application connection.
             This is a stateless trap (no alarm)."
    ::= { ptiSegway 0 8161 }

ptMTP3NANodeL4NewAppConnection NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "Some L4 application has connected."
    ::= { ptiSegway 0 8162 }

ptGenericLinkGenericL3LinkAlarmsDisabled NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalPort, 
                      ptMTPGenericLinkRemoteIPAddress1, 
                      ptMTPGenericLinkRemotePort, 
                      ptMTPGenericLinkL3State, ptMTPGenericLinkLinkType }
    STATUS          current
    DESCRIPTION     
            "Generic Link alarms are disabled."
    ::= { ptiSegway 0 8163 }

ptGenericLinkGenericL3LinkAlarmsEnabled NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalPort, 
                      ptMTPGenericLinkRemoteIPAddress1, 
                      ptMTPGenericLinkRemotePort, 
                      ptMTPGenericLinkL3State, ptMTPGenericLinkLinkType }
    STATUS          current
    DESCRIPTION     
            "Generic Link alarms are enabled."
    ::= { ptiSegway 0 8164 }

ptMTP3NAManagerMtp3LostConnectionToLicenceD NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "NA lost connection to License Daemon"
    ::= { ptiSegway 0 8165 }

ptMTP3NAManagerMtp3ConnectedToLicenceD NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "NA connected succefully to License Daemon"
    ::= { ptiSegway 0 8166 }

ptRegisteredAppIDAppIdLongMsuDiscard NOTIFICATION-TYPE
    OBJECTS         { ptTrapType, ptTrapSequenceNumber, ptTrapSeverity, 
                      ptTrapProbableCause, ptTrapClearType, 
                      ptTrapDateAndTime, ptTrapItemOID, 
                      ptMTPRegisteredAppIDName }
    STATUS          current
    DESCRIPTION     
            "This trap indicates that a long MSU message has been received and was
             discarded in an attempt to route on a App ID that does not support
             long MSUs."
    ::= { ptiSegway 0 8167 }

ptLSLinkSs7L3LinkOscillationFilterSet NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that Link Oscillation Filter Timer T32 has started 
             "
    ::= { ptiSegway 0 8168 }

ptLSLinkSs7L3LinkOscillationFilterClear NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that Link Oscillation Filter Timer T32 has expired 
             "
    ::= { ptiSegway 0 8169 }

ptATMLinkAtmL3LinkOscillationFilterSet NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that Link Oscillation Filter Timer T32 has started 
             "
    ::= { ptiSegway 0 8170 }

ptATMLinkAtmL3LinkOscillationFilterClear NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that Link Oscillation Filter Timer T32 has expired 
             
             "
    ::= { ptiSegway 0 8171 }

ptM2UALinkM2uaL3LinkOscillationFilterSet NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that Link Oscillation Filter Timer T32 has started 
             "
    ::= { ptiSegway 0 8172 }

ptM2UALinkM2uaL3LinkOscillationFilterClear NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that Link Oscillation Filter Timer T32 has expired 
             "
    ::= { ptiSegway 0 8173 }

ptM2PALinkM2paL3LinkOscillationFilterSet NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that Link Oscillation Filter Timer T32 has started 
             "
    ::= { ptiSegway 0 8174 }

ptM2PALinkM2paL3LinkOscillationFilterClear NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that Link Oscillation Filter Timer T32 has expired 
             "
    ::= { ptiSegway 0 8175 }

ptRoutesetRouteSetAlarmsDisabled NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "Routeset alarms are disabled."
    ::= { ptiSegway 0 8176 }

ptRoutesetRouteSetAlarmsEnabled NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "Routeset alarms are enabled."
    ::= { ptiSegway 0 8177 }

ptRoutesetRoutesetDestCongestedRecovery NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState }
    STATUS          current
    DESCRIPTION     
            "This trap indicates that destination is no longer congested.
             Clears routesetDestCongested.
             "
    ::= { ptiSegway 0 8178 }

ptLSLinkSs7L3LinkUnavailable NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link is unavailable
             for user traffic.
             Cleared by ss7L3LinkAvailable.
             
                 Cause  - The link is unavailable to user traffic for some
                          reason (e.g. out of service, blocked, inhibited).
                 
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8179 }

ptLSLinkSs7L3LinkAvailable NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that a signaling link is available
             for user traffic.
             Clears ss7L3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8180 }

ptAnnexALinkAnnexaL3LinkUnavailable NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link is unavailable
             for user traffic.
             Cleared by annexaL3LinkAvailable.
             
                 Cause  - The link is unavailable to user traffic for some
                          reason (e.g. out of service, blocked, inhibited).
                 
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8181 }

ptAnnexALinkAnnexaL3LinkAvailable NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that a signaling link is available
             for user traffic.
             Clears annexaL3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8182 }

ptATMLinkAtmL3LinkUnavailable NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link is unavailable
             for user traffic.
             Cleared by atmL3LinkAvailable.
             
                 Cause  - The link is unavailable to user traffic for some
                          reason (e.g. out of service, blocked, inhibited).
                 
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8183 }

ptATMLinkAtmL3LinkAvailable NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that a signaling link is available
             for user traffic.
             Clears atmL3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8184 }

ptM2PALinkM2paL3LinkUnavailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that a signaling link is unavailable
             for user traffic.
             Cleared by m2paL3LinkAvailable.
             
                 Cause  - The link is unavailable to user traffic for some
                          reason (e.g. out of service, blocked, inhibited).
                 
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8185 }

ptM2PALinkM2paL3LinkAvailable NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalPort, 
                      ptMTPM2PALinkRemoteIPAddress1, 
                      ptMTPM2PALinkRemotePort, ptMTPM2PALinkL3State, 
                      ptMTPM2PALinkLinkName }
    STATUS          current
    DESCRIPTION     
            "This trap indicates that a signaling link is available
             for user traffic.
             Clears m2paL3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8186 }

ptM2UALinkM2uaL3LinkUnavailable NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that a signaling link is unavailable
             for user traffic.
             Cleared by m2uaL3LinkAvailable.
             
                 Cause  - The link is unavailable to user traffic for some
                          reason (e.g. out of service, blocked, inhibited).
                 
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8187 }

ptM2UALinkM2uaL3LinkAvailable NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that a signaling link is available
             for user traffic.
             Clears m2uaL3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8188 }

ptMTP3NANodeMTPRestartBegin NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "A Local MTP Restart procedure has begun."
    ::= { ptiSegway 0 8189 }

ptMTP3NANodeMTPRestartEnd NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "A Local MTP Restart procedure has completed."
    ::= { ptiSegway 0 8190 }

ptMTP3NANodeMTPRestartInProgress NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "A Local MTP Restart procedure is ongoing.
             This is a stateless trap (no alarm)."
    ::= { ptiSegway 0 8191 }

ptDRELoadingManagerMtp3LinkRebalancingTriggered NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "As part of the proper distribution of DRE loading, the links on all
             DREs have been redistributed. This action has been triggered by the
             DRE loading audit or by user action.
             This is a stateless trap (no alarm)."
    ::= { ptiSegway 0 8192 }

ptRoutesetRoutesetC20ProvError NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState, 
                      ptMTPRoutesetRoutesetID }
    STATUS          current
    DESCRIPTION     
            "This trap indicates that there is a routeset provisioning on the C20 Core. "
    ::= { ptiSegway 0 8193 }

ptRoutesetRoutesetC20ProvClear NOTIFICATION-TYPE
    OBJECTS         { ptTrapType, ptTrapSequenceNumber, ptTrapSeverity, 
                      ptTrapProbableCause, ptTrapClearType, 
                      ptTrapDateAndTime, ptTrapItemOID, 
                      ptMTPRoutesetContext, ptMTPRoutesetDPC, 
                      ptMTPRoutesetCLLI, ptMTPRoutesetDestinationState, 
                      ptMTPRoutesetRoutesetID }
    STATUS          current
    DESCRIPTION     
            "This trap indicates that the routeset provisioning on the C20 Core
             has been corrected."
    ::= { ptiSegway 0 8194 }

ptMTP3NAMtp3AppIDLinkOutage NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "The MTP3 NA has lost the AppID registration and is in Link Outage."
    ::= { ptiSegway 0 8195 }

ptMTP3NAMtp3AppIDLinkOutageClear NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "The MTP3 NA has the AppID registration and is no longer in Link Outage."
    ::= { ptiSegway 0 8196 }

ptMTP3NANoActiveRSSet NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "An MSU destined to an undefined or inactive routeset has been discarded 
             within the last 5 minutes.
             
             Check the debuglog for paced logging of the discarded MSU(s) information which
             will include routing label breakdown.
             
             The issue may be resolved by updating the Gateway Screening if the destination
             is unexpected or by adding and activating a routeset for the associated DPC.
             "
    ::= { ptiSegway 0 8197 }

ptMTP3NANoActiveRSClear NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "Clear event for MSU destined to undefined or inactive routeset has been discarded"
    ::= { ptiSegway 0 8198 }

ptMSAMsaThreshold1Crossed NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 1 is crossed."
    ::= { ptiSegway 0 8200 }

ptMSAMsaThreshold2Crossed NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 2 is crossed."
    ::= { ptiSegway 0 8201 }

ptMSAMsaThreshold3Crossed NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 3 is crossed."
    ::= { ptiSegway 0 8202 }

ptMSAMsaThreshold3Cleared NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 3 is cleared."
    ::= { ptiSegway 0 8203 }

ptMSAMsaThreshold2Cleared NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 2 is cleared."
    ::= { ptiSegway 0 8204 }

ptMSAMsaThreshold1Cleared NOTIFICATION-TYPE
    OBJECTS         { ptTrapType, ptTrapSequenceNumber, ptTrapSeverity, 
                      ptTrapProbableCause, ptTrapClearType, 
                      ptTrapDateAndTime, ptTrapItemOID, ptmsaMSAName }
    STATUS          current
    DESCRIPTION     
            "This trap indicates the MSA threshold 1 is cleared."
    ::= { ptiSegway 0 8205 }

ptMTP3NAManagerMtp3DebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: At least one debug attribute is not set to the recommended value.
             
             Possible Actions -
                 The user should perform the 'Restore Debug Defaults' action to rest all
                 debug attributes to their recommended values."
    ::= { ptiSegway 0 8206 }

ptMTP3NAManagerMtp3DebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 8207 }

ptLinksetMtp3LinksetDebugLevelNotRecommended NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetLinksetName }
    STATUS          current
    DESCRIPTION     
            "This trap indicates that at least one MTP3 NA debug attribute has been changed to a non recommended value.
             
             Cause: A user has altered at least one NA debugging attribute to a non recommended value.
             
             Possible Actions -
                 The user should perform the 'Restore Debug Defaults' action to reset all
                 debug attributes to their recommended values."
    ::= { ptiSegway 0 8208 }

ptLinksetMtp3LinksetDebugLevelRecommended NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetLinksetName }
    STATUS          current
    DESCRIPTION     
            "The MTP3 link debugging attributes are set to their recommended values."
    ::= { ptiSegway 0 8209 }

ptMTP3NAMtp3NADebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: At least one debug attribute is not set to the recommended value.
             
             Possible Actions -
                 The user should perform the 'Restore Debug Defaults' action to reset all
                 debug attributes to their recommended values."
    ::= { ptiSegway 0 8210 }

ptMTP3NAMtp3NADebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The MTP3 NA debug attributes are set to their recommended values."
    ::= { ptiSegway 0 8211 }

ptProcessEventTrafficStatusNotReady NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer traffic status is not ready. 
             Not raised during initialization."
    ::= { ptiSegway 0 8300 }

ptProcessEventTrafficStatusReady NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer traffic status is ready."
    ::= { ptiSegway 0 8301 }

ptProcessEventFileWriteFailure NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer had a write failure."
    ::= { ptiSegway 0 8302 }

ptProcessEventFileWriteSuccess NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer no longer has a write failure."
    ::= { ptiSegway 0 8303 }

ptProcessEventSlotMgrNotConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer slot manager is not connected.
             Not raised during initialization."
    ::= { ptiSegway 0 8304 }

ptProcessEventSlotMgrConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer slot manager is connected."
    ::= { ptiSegway 0 8305 }

ptProcessEventStatsMgrNotConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer stats manager is not connected.
             Not raised during initialization."
    ::= { ptiSegway 0 8306 }

ptProcessEventStatsMgrConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer stats manager is connected."
    ::= { ptiSegway 0 8307 }

ptProcessEventIMFMgrNotConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer IMF manager is not connected.
             Not raised during initialization."
    ::= { ptiSegway 0 8308 }

ptProcessEventIMFMgrConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer IMF manager is connected."
    ::= { ptiSegway 0 8309 }

ptProcessEventLowerLayerNotConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer lower layer is not connected.
             Not raised during initialization."
    ::= { ptiSegway 0 8310 }

ptProcessEventLowerLayerNotConnectedCleared NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer lower layer is no longer not connected."
    ::= { ptiSegway 0 8311 }

ptProcessEventLowerLayerPartiallyConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer lower layer is partially connected.
             Not raised during initialization."
    ::= { ptiSegway 0 8312 }

ptProcessEventLowerLayerConnected NOTIFICATION-TYPE
    OBJECTS         { ptTrapType, ptTrapSequenceNumber, ptTrapSeverity, 
                      ptTrapProbableCause, ptTrapClearType, 
                      ptTrapDateAndTime, ptTrapItemOID, 
                      ptpeereventProcessEventSlot, 
                      ptpeereventProcessEventName }
    STATUS          current
    DESCRIPTION     
            "This trap indicates the peer lower layer is now connected."
    ::= { ptiSegway 0 8313 }

ptIMFTrafficProcessImfTrafficLossNotif NOTIFICATION-TYPE
    OBJECTS         { ptTrapType, ptTrapSequenceNumber, ptTrapSeverity, 
                      ptTrapProbableCause, ptTrapClearType, 
                      ptTrapDateAndTime, ptTrapItemOID, 
                      ptimfIMFTrafficProcessName, 
                      ptimfIMFTrafficProcessSlot }
    STATUS          current
    DESCRIPTION     
            "IMF process has noticed a traffic loss."
    ::= { ptiSegway 0 8400 }

ptIMFTrafficProcessImfTrafficLossClear NOTIFICATION-TYPE
    OBJECTS         { ptTrapType, ptTrapSequenceNumber, ptTrapSeverity, 
                      ptTrapProbableCause, ptTrapClearType, 
                      ptTrapDateAndTime, ptTrapItemOID, 
                      ptimfIMFTrafficProcessName, 
                      ptimfIMFTrafficProcessSlot }
    STATUS          current
    DESCRIPTION     
            "IMF process has no traffic loss for last 5 minutes."
    ::= { ptiSegway 0 8401 }

ptIMFPacketCaptureImfPacketCaptureActive NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "A packet capture is running on the processors and may impact overall capacity."
    ::= { ptiSegway 0 8402 }

ptIMFPacketCaptureImfPacketCaptureClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "The packet capture has been stopped on the processors."
    ::= { ptiSegway 0 8403 }

ptIMFConfigurationIMFDebugLevelNotRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "At least one debug attribute is not set to the recommended value.
             
             Cause: A debug attribute is not set to a recommended level.
             
             Possible Actions -
               The user should perform the 'Restore Debug Defaults' action to reset all
               debug attributes to their default values."
    ::= { ptiSegway 0 8405 }

ptIMFConfigurationIMFDebugLevelRecommended NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "All debug attributes are set to their recommended values."
    ::= { ptiSegway 0 8406 }

ptGenericLinkGenericL3LinkDeactivated NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalPort, 
                      ptMTPGenericLinkRemoteIPAddress1, 
                      ptMTPGenericLinkRemotePort, 
                      ptMTPGenericLinkL3State, ptMTPGenericLinkLinkType }
    STATUS          current
    DESCRIPTION     
            "This trap indicates that a Generic signaling link has been deactivated.
             Causes ,Corrective actions and Frequency:  
               1) ptSpecificTrapCause = operatorDeactivation 
                  Cause  - Operator deactivates link.
                  Action - Operator can activate the link again.
                  Freq   - Operator dependant. 
                   
               2) ptSpecificTrapCause = timerT17Expiry
                  Cause  - Event appears between each attempt to perform an initial 
                           alignment procedure. After an unsuccessful attempt, a delay
                           T17 expires before the next attempt is initiated.
                  Action - Operator can activate the link.  
                  Freq   - T19 expiry, T19 can take a value between 800 - 1500 ms
             
               3) ptSpecificTrapCause = unknownCause
             
             References
               1) Table 1 Q.752, SL Failure
               2) Q.704 (07/96) Section 12.2 
                             
               ptOriginatingOID:    DYNAMIC ptLink
               ptTrapType:          2 communicationAlarm
               ptTrapSeverity:      3 minor
               ptTrapProbableCause: 29 Loss of signal   
               ptTrapClearType:     1 fmic
             "
    ::= { ptiSegway 0 8424 }

ptGenericLinkGenericL3LinkActivated NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalPort, 
                      ptMTPGenericLinkRemoteIPAddress1, 
                      ptMTPGenericLinkRemotePort, 
                      ptMTPGenericLinkL3State, ptMTPGenericLinkLinkType }
    STATUS          current
    DESCRIPTION     
            "This trap indicates that a Generic signaling link has been activated
             either by operator or as a result of a successful restoration 
             which was initiated upon detection of an inactive link.
             This trap could also be generated at restart without a previous
             corresponding trap 201.
             
             References
               1)  Q.752, SL Restoration
               2)  Q.704, (07/96) Section 12.2
               
               ptOriginatingOID:    DYNAMIC ptLink
               ptTrapType:          2 communicationAlarm
               ptTrapSeverity:      5 cleared
               ptTrapProbableCause: 29 Loss of signal 
               ptTrapClearType:     1 fmic              
             "
    ::= { ptiSegway 0 8425 }

ptGenericLinkGenericLinkSCTPUnavailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that a signaling link is unavailable
             for user traffic because the underlying SCTP Association is
             unavailable.
             Cleared by GenericLinkSCTPAvailable.
             
                 Cause  - Most likely an IP Network issues, or perhaps
                          communication was lost to a DRE.
                 
                 Action - Check the availability of the corresponding DRE.
                          If available, troubleshoot the IP connectivity.
             
                 Freq   - Operator dependant.
             
               References
                 1) GR310CORE Issue 3 Section 8.6 (REPT-SCTP-ASOCTRMD)
             
                 ptOriginatingOID:      DYNAMIC ptLink
                 ptTrapType:            2 communicationAlarm
                 ptTrapSeverity:        3 minor
                 ptTrapProbableCause:  29 Loss of signal   
                 ptTrapClearType:       1 fmic
             "
    ::= { ptiSegway 0 8426 }

ptGenericLinkGenericLinkSCTPAvailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that a Generic Link SCTP Association
             has been established.
             Clears GenericLinkSCTPUnavailable.
             
             References
               1) GR310CORE Issue 3 Section 8.6 (REPT-SCTP-ASOCESTB)
             
               ptOriginatingOID:      DYNAMIC ptLink
               ptTrapType:            2 communicationAlarm
               ptTrapSeverity:        5 cleared
               ptTrapProbableCause:  29 Loss of signal   
               ptTrapClearType:       1 fmic
             "
    ::= { ptiSegway 0 8427 }

ptGenericLinkGenericLinkSCTPPathUnavailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that the SCTP Association that
             carries traffic is operating in a vulnerable
             state, an additional path failure could cause a
             link failure.
             Cleared by GenericLinkSCTPPathAvailable.
             
                 Cause  - Most likely an IP Network issue.
                 
                 Action - Troubleshoot IP connectivity.
             
                 Freq   - Operator dependant.
             
               References
                 This trap is implementation specific.
             
                 ptOriginatingOID:      DYNAMIC ptLink
                 ptTrapType:            2 communicationAlarm
                 ptTrapSeverity:        3 minor
                 ptTrapProbableCause:  29 Loss of signal   
                 ptTrapClearType:       1 fmic
             "
    ::= { ptiSegway 0 8428 }

ptGenericLinkGenericLinkSCTPPathAvailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that the SCTP Association that
             carries traffic is no longer operating with a
             path failure.
             Clears GenericLinkSCTPPathUnavailable.
             
             References
               This trap is implementation specific.
             
               ptOriginatingOID:      DYNAMIC ptLink
               ptTrapType:            2 communicationAlarm
               ptTrapSeverity:        5 cleared
               ptTrapProbableCause:  29 Loss of signal   
               ptTrapClearType:       1 fmic
             "
    ::= { ptiSegway 0 8429 }

ptGenericLinkGenericL3LinkOscillationFilterSet NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that Link Oscillation Filter Timer T32 has started
             "
    ::= { ptiSegway 0 8430 }

ptGenericLinkGenericL3LinkOscillationFilterClear NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that Link Oscillation Filter Timer T32 has expired
             "
    ::= { ptiSegway 0 8431 }

ptGenericLinkGenericL3LinkUnavailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that a signaling link is unavailable
             for user traffic.
             Cleared by GenericL3LinkAvailable.
             
                 Cause  - The link is unavailable to user traffic for some
                          reason (e.g. out of service, blocked, inhibited).
             
                 Action - Depends on link state.
             
                 Freq   - Operator dependant.
             
               References
                 1) GR310CORE Issue 3 Section 8.1
                 2) GR246CORE Issue 10
                 3) GR82CORE  Issue 10
                 4) Q.704
             
                 ptOriginatingOID:      DYNAMIC ptLink
                 ptTrapType:            2 communicationAlarm
                 ptTrapSeverity:        3 minor
                 ptTrapProbableCause:   6 Communication subsystem error
                 ptTrapClearType:       1 fmic
             "
    ::= { ptiSegway 0 8432 }

ptGenericLinkGenericL3LinkAvailable NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that a signaling link is available
             for user traffic.
             Clears GenericL3LinkUnavailable.
             
             References
               1) GR310CORE Issue 3 Section 8.1
               2) GR246CORE Issue 10
               3) GR82CORE  Issue 10
               4) Q.704
             
               ptOriginatingOID:      DYNAMIC ptLink
               ptTrapType:            2 communicationAlarm
               ptTrapSeverity:        5 cleared
               ptTrapProbableCause:   6 Communication subsystem error
               ptTrapClearType:       1 fmic
             "
    ::= { ptiSegway 0 8433 }

ptGenericLinkGenericLinkUnaligned NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL2State, ptMTPGenericLinkLinkType }
    STATUS          current
    DESCRIPTION     
            "This trap indicates that an Generic signaling link has lost alignment.
             
             Cause  - After a signaling link failure is detected, signaling link
                      initial alignment will take place. The Alignment procedure
                      passes through a number of states and when the procedure
                      enters the state not aligned this trap is sent.
             Action - If the initial alignment procedure does not work, then the
                      operator will have to intervene in order that the link
                      alignment succeeds.
             Freq   - This trap will continue to appear each time the initial
                      alignment procedure enters the state not aligned. This
                      may happen a number of times as the initial alignment
                      procedure is repeated until alignment has been completed
                      successfully.
             
             References
               1) Q.703 , (07/96) Section 7.3
             
             
               ptOriginatingOID:    DYNAMIC ptLink
               ptTrapType:          2 communicationAlarm
               ptTrapSeverity:      3 minor
               ptTrapProbableCause: 6 Communications subsystem error
               ptTrapClearType:     1 fmic
             "
    ::= { ptiSegway 0 8434 }

ptGenericLinkGenericLinkAligned NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL2State, ptMTPGenericLinkLinkType }
    STATUS          current
    DESCRIPTION     
            "This trap indicates that an generic signaling link has been aligned.
             
             Cause  - After a signaling link failure is detected, signaling link
                      initial alignment will take place. The Alignment procedure
                      passes through a number of states and when the procedure
                      enters the state aligned this trap is sent.
             Freq   - Once the alignment procedure enters the aligned state then
                      the alignment procedure will not be repeated.
             
             References
             1) Q.703 , (07/96) Section 7.3
             
             ptOriginatingOID:    DYNAMIC ptLink
             ptTrapType:          2 communicationAlarm
             ptTrapSeverity:      5 cleared
             ptTrapProbableCause: 6 Communications subsystem error
             ptTrapClearType:     1 fmic
             "
    ::= { ptiSegway 0 8435 }

ptGenericLinkGenericL3LinkUsageHighSet NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that the average traffic over this link exceeds
             predefined threshold. There is potential for traffic loss if this
             condition persists.
             
               References
                 This is PTI proprietary trap.
             
                 ptOriginatingOID:    DYNAMIC ptLink
                 ptTrapType:          11 qualityofserviceAlarm
                 ptTrapSeverity:      3 minor
                 ptTrapProbableCause: 51 Threshold crossed
                 ptTrapClearType:     1 fmic
             "
    ::= { ptiSegway 0 8437 }

ptGenericLinkGenericL3LinkUsageHighClear NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that the average traffic over this link no longer
             exceeds predefined threshold. There is no longer potential for traffic
             loss due to extensive traffic.
             
               References
                 This is PTI proprietary trap.
             
                 ptOriginatingOID:    DYNAMIC ptLink
                 ptTrapType:          11 qualityofserviceAlarm
                 ptTrapSeverity:      5 cleared
                 ptTrapProbableCause: 51 Threshold crossed
                 ptTrapClearType:     1 fmic
             "
    ::= { ptiSegway 0 8438 }

ptRADIUSServerRadiusServerUnavailable NOTIFICATION-TYPE
    OBJECTS         { ptTrapType, ptTrapSequenceNumber, ptTrapSeverity, 
                      ptTrapProbableCause, ptTrapClearType, 
                      ptTrapDateAndTime, ptTrapItemOID, 
                      ptuppRADIUSServerAddress, ptuppRADIUSServerTimeout }
    STATUS          current
    DESCRIPTION     
            "One of the configured RADIUS servers failed to respond to a request within its configured timeout."
    ::= { ptiSegway 0 8500 }

ptRADIUSServerRadiusServerClear NOTIFICATION-TYPE
    OBJECTS         { ptTrapType, ptTrapSequenceNumber, ptTrapSeverity, 
                      ptTrapProbableCause, ptTrapClearType, 
                      ptTrapDateAndTime, ptTrapItemOID, 
                      ptuppRADIUSServerAddress, ptuppRADIUSServerTimeout }
    STATUS          current
    DESCRIPTION     
            "A RADIUS server which previously failed to respond to a request within its configured timeout has now done so."
    ::= { ptiSegway 0 8501 }

ptLinksetSs7LinksetDeactivated NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that an SS7 linkset has been deactivated by the user."
    ::= { ptiSegway 0 8600 }

ptLinksetSs7LinksetActivated NOTIFICATION-TYPE
    OBJECTS         { ptTrapType, ptTrapSequenceNumber, ptTrapSeverity, 
                      ptTrapProbableCause, ptTrapClearType, 
                      ptTrapDateAndTime, ptTrapItemOID, ptMTPLinksetAPC, 
                      ptMTPLinksetCLLI, ptMTPLinksetState, 
                      ptMTPLinksetLinksetName }
    STATUS          current
    DESCRIPTION     
            "This trap indicates that an SS7 linkset has been activated by the user."
    ::= { ptiSegway 0 8601 }

ptMTP3NADiscardMsuToL4Set NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "An MSU destined to an L4 user has been discarded within the last 30 seconds"
    ::= { ptiSegway 0 9950 }

ptMTP3NADiscardMsuToL4Clear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for MSU destined to an L4 user has been discarded"
    ::= { ptiSegway 0 9951 }

ptMTP3NADiscardMsuToL2Set NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "An MSU destined to SS7/IP network has been discarded within the last 30 seconds."
    ::= { ptiSegway 0 9952 }

ptMTP3NADiscardMsuToL2Clear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for MSU destined to SS7/IP network has been discarded"
    ::= { ptiSegway 0 9953 }

ptMTP3NAMtp3LinkInvalidOpcDetect NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 discarded link messages with invalid OPC.
             This alarm will clear automatically if no more message with invalid OPC
             is detected for 5 minutes."
    ::= { ptiSegway 0 9954 }

ptMTP3NAMtp3LinkInvalidOpcClear NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 no longer detects messages with invalid OPC for 5 minutes."
    ::= { ptiSegway 0 9955 }

ptMTP3NAMtp3UserOpcEqualsDpcDetect NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 discarded user messages with OPC equals DPC.
             This alarm will clear automatically if no more message with invalid OPC
             is detected for 5 minutes."
    ::= { ptiSegway 0 9956 }

ptMTP3NAMtp3UserOpcEqualsDpcClear NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 no longer detects user messages with OPC equals DPC for 5 minutes."
    ::= { ptiSegway 0 9957 }

ptMTP3NADiscardMsuFromPeerSet NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "An MSU was discarded for a reason that might not correspond to an existing alarm.
             This alarm is not generated for MSUs discarded because the destination is unavailable or congested (since destinations unavailable or congested have their own alarms)
             "
    ::= { ptiSegway 0 9958 }

ptMTP3NADiscardMsuFromPeerClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for MSU discarded from an MTP3 peer"
    ::= { ptiSegway 0 9959 }

ptMTP3NAInvalidIncomingTraffic NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "An incoming MSU was discarded due to an invalid formatting.  
             This could be a malicious event or just misformed data."
    ::= { ptiSegway 0 9960 }

ptMTP3NAInvalidIncomingTrafficClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for invalid incoming traffic."
    ::= { ptiSegway 0 9961 }

ptDREDRECongestion NOTIFICATION-TYPE
    OBJECTS         { ptTrapType, ptTrapSequenceNumber, ptTrapSeverity, 
                      ptTrapProbableCause, ptTrapClearType, 
                      ptTrapDateAndTime, ptTrapItemOID, ptMTPDREContext }
    STATUS          current
    DESCRIPTION     
            "The inter-DRE communication is congested."
    ::= { ptiSegway 0 9962 }

ptDREDRECongestionClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for DRE congestion."
    ::= { ptiSegway 0 9963 }

ptL4ConnectionL4ConnCongestion NOTIFICATION-TYPE
    OBJECTS         { ptTrapType, ptTrapSequenceNumber, ptTrapSeverity, 
                      ptTrapProbableCause, ptTrapClearType, 
                      ptTrapDateAndTime, ptTrapItemOID, 
                      ptMTPL4ConnectionContext }
    STATUS          current
    DESCRIPTION     
            "The L4 connection is congested."
    ::= { ptiSegway 0 9964 }

ptL4ConnectionL4ConnCongestionClear NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "Clear event for L4 connection congestion."
    ::= { ptiSegway 0 9965 }

ptMTP3NANodeStatusPendingLic NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NASS7NodeType, 
                      ptMTPMTP3NAStatus }
    STATUS          current
    DESCRIPTION     
            "An attempt by the MTP3 NA to obtain a software license has failed"
    ::= { ptiSegway 0 9979 }

ptMTP3NANodeStatusReceivedLic NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NASS7NodeType, 
                      ptMTPMTP3NAStatus }
    STATUS          current
    DESCRIPTION     
            "An attempt by the MTP3 NA to obtain a software license has succeeded"
    ::= { ptiSegway 0 9980 }

ptMTP3NANodeNoSTPRoutingLicense NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NASS7NodeType, 
                      ptMTPMTP3NAStatus }
    STATUS          current
    DESCRIPTION     
            "An attempt by the MTP3 NA to obtain a STP Routing license has failed"
    ::= { ptiSegway 0 9981 }

ptMTP3NANodeSTPRoutingLicenseAcquired NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NASS7NodeType, 
                      ptMTPMTP3NAStatus }
    STATUS          current
    DESCRIPTION     
            "An attempt by the MTP3 NA to obtain a STP Routing license has succeeded"
    ::= { ptiSegway 0 9982 }

ptMTP3NAManagerMtp3NAManagerConfigWriteError NOTIFICATION-TYPE
    OBJECTS         { ptTrapType, ptTrapSequenceNumber, ptTrapSeverity, 
                      ptTrapProbableCause, ptTrapClearType, 
                      ptTrapDateAndTime, ptTrapItemOID }
    STATUS          current
    DESCRIPTION     
            "This trap indicates that there was an error writing the
             MTP3 NA Manager configuration file to disk.  Recent changes
             may not have been committed to persistent storage.
             This is a stateless trap (no alarm).
                       
                    Cause  - A configuration file write could fail for a number of
                             reasons, including but not limited to
             
                              - disk full
             
                              - file permissions
             
                              - temporary file and real file are on different
                                mount points
             
                             If the cause is not evident, the
                             corresponding syslog entry may have more
                             details.
             
                    Action - Resolve the issue with the disk, then
                             prompt a rewrite of the configuration file
                             by modifying a value in the UI.
             
                    Freq   - This trap occurs if there is an error
                             committing the configuration to persistent storage.
                    
                    References 
                       None.  This is implementation specific.
             "
    ::= { ptiSegway 0 9983 }

ptMTP3NAMtp3NAConfigWriteError NOTIFICATION-TYPE
    OBJECTS         { ptTrapType, ptTrapSequenceNumber, ptTrapSeverity, 
                      ptTrapProbableCause, ptTrapClearType, 
                      ptTrapDateAndTime, ptTrapItemOID, 
                      ptMTPMTP3NAContext, ptMTPMTP3NALocalPointCode, 
                      ptMTPMTP3NASS7NodeType }
    STATUS          current
    DESCRIPTION     
            "This trap indicates that there was an error writing the
             MTP3 NA configuration file to disk.  Recent changes may not
             have been committed to persistent storage.
             This is a stateless trap (no alarm).
                       
                    Cause  - A configuration file write could fail for a number of
                             reasons, including but not limited to
             
                              - disk full
             
                              - file permissions
             
                              - temporary file and real file are on different
                                mount points
             
                             If the cause is not evident, the
                             corresponding syslog entry may have more
                             details.
             
                    Action - Resolve the issue with the disk, then
                             prompt a rewrite of the configuration file
                             by modifying a value in the UI.
             
                    Freq   - This trap occurs if there is an error
                             committing the configuration to persistent storage.
                    
                    References 
                       None.  This is implementation specific.
             "
    ::= { ptiSegway 0 9984 }

ptMTP3NAMtp3SLSLinkAuditFailure NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 detected an unavailable link in an SLS Table. MSU loss is possible.
             \nThis alarm should resolve itself in less than four minutes.
             If this alarm does not clear itself you should consult ptidbglog to
             determine the routeset and/or link that is having an issue and
             prompt a regeneration of the SLS tables by changing routing in
             some way, such as resetting an unavailable link, changing the
             cost of a route, or resetting route state."
    ::= { ptiSegway 0 9985 }

ptMTP3NAMtp3SLSLinkAuditFailureClear NOTIFICATION-TYPE
    OBJECTS         { ptTrapType, ptTrapSequenceNumber, ptTrapSeverity, 
                      ptTrapProbableCause, ptTrapClearType, 
                      ptTrapDateAndTime, ptTrapItemOID, 
                      ptMTPMTP3NAContext }
    STATUS          current
    DESCRIPTION     
            "MTP3 no longer detects an unavailable link in an SLS Table."
    ::= { ptiSegway 0 9986 }

ptLSLinkSs7SLSLinkAuditFailure NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "MTP3 detected an unavailable link in an SLS Table. MSU loss is possible.
             Cleared by ss7SLSLinkAuditFailureClear.
             
                 Cause  - MTP3 detected an unavailable link in an SLS Table.
                 
                 Action - This alarm should resolve itself in less than four minutes.
                          If this alarm does not clear itself you should reset the link
                          using the 'Reset' action on the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9987 }

ptLSLinkSs7SLSLinkAuditFailureClear NOTIFICATION-TYPE
    OBJECTS         { ptTrapType, ptTrapSequenceNumber, ptTrapSeverity, 
                      ptTrapProbableCause, ptTrapClearType, 
                      ptTrapDateAndTime, ptTrapItemOID, ptMTPLSLinkAPC, 
                      ptMTPLSLinkSLC, ptMTPLSLinkCage, 
                      ptMTPLSLinkChassisSlot, ptMTPLSLinkChannel, 
                      ptMTPLSLinkL3State, ptMTPLSLinkLinkName }
    STATUS          current
    DESCRIPTION     
            "This trap indicates that an SLS Table Link Audit
             has concluded and this link is no longer included
             incorrectly in SLS Tables. The link may have been
             removed from SLS Tables, or its state may have
             changed so it is now appropriate for use in SLS
             Tables.
               
             Clears ss7SLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9988 }

ptATMLinkAtmSLSLinkAuditFailure NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "MTP3 detected an unavailable link in an SLS Table. MSU loss is possible.
             Cleared by atmSLSLinkAuditFailureClear.
             
                 Cause  - MTP3 detected an unavailable link in an SLS Table.
                 
                 Action - This alarm should resolve itself in less than four minutes.
                          If this alarm does not clear itself you should reset the link
                          using the 'Reset' action on the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9989 }

ptATMLinkAtmSLSLinkAuditFailureClear NOTIFICATION-TYPE
    OBJECTS         { ptTrapType, ptTrapSequenceNumber, ptTrapSeverity, 
                      ptTrapProbableCause, ptTrapClearType, 
                      ptTrapDateAndTime, ptTrapItemOID, ptMTPATMLinkAPC, 
                      ptMTPATMLinkSLC, ptMTPATMLinkCage, 
                      ptMTPATMLinkChannel, ptMTPATMLinkL3State, 
                      ptMTPATMLinkLinkName }
    STATUS          current
    DESCRIPTION     
            "This trap indicates that an SLS Table Link Audit
             has concluded and this link is no longer included
             incorrectly in SLS Tables. The link may have been
             removed from SLS Tables, or its state may have
             changed so it is now appropriate for use in SLS
             Tables.
               
             Clears atmSLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9990 }

ptAnnexALinkAnnexaSLSLinkAuditFailure NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "MTP3 detected an unavailable link in an SLS Table. MSU loss is possible.
             Cleared by annexaSLSLinkAuditFailureClear.
             
                 Cause  - MTP3 detected an unavailable link in an SLS Table.
                 
                 Action - This alarm should resolve itself in less than four minutes.
                          If this alarm does not clear itself you should reset the link
                          using the 'Reset' action on the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9991 }

ptAnnexALinkAnnexaSLSLinkAuditFailureClear NOTIFICATION-TYPE
    OBJECTS         { ptTrapType, ptTrapSequenceNumber, ptTrapSeverity, 
                      ptTrapProbableCause, ptTrapClearType, 
                      ptTrapDateAndTime, ptTrapItemOID, 
                      ptMTPAnnexALinkAPC, ptMTPAnnexALinkSLC, 
                      ptMTPAnnexALinkCage, ptMTPAnnexALinkChassisSlot, 
                      ptMTPAnnexALinkChannel, ptMTPAnnexALinkL3State, 
                      ptMTPAnnexALinkLinkName }
    STATUS          current
    DESCRIPTION     
            "This trap indicates that an SLS Table Link Audit
             has concluded and this link is no longer included
             incorrectly in SLS Tables. The link may have been
             removed from SLS Tables, or its state may have
             changed so it is now appropriate for use in SLS
             Tables.
               
             Clears annexaSLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9992 }

ptM2UALinkM2uaSLSLinkAuditFailure NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "MTP3 detected an unavailable link in an SLS Table. MSU loss is possible.
             Cleared by m2uaSLSLinkAuditFailureClear.
             
                 Cause  - MTP3 detected an unavailable link in an SLS Table.
                 
                 Action - This alarm should resolve itself in less than four minutes.
                          If this alarm does not clear itself you should reset the link
                          using the 'Reset' action on the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9993 }

ptM2UALinkM2uaSLSLinkAuditFailureClear NOTIFICATION-TYPE
    OBJECTS         { ptTrapType, ptTrapSequenceNumber, ptTrapSeverity, 
                      ptTrapProbableCause, ptTrapClearType, 
                      ptTrapDateAndTime, ptTrapItemOID, ptMTPM2UALinkAPC, 
                      ptMTPM2UALinkSLC, ptMTPM2UALinkCage, 
                      ptMTPM2UALinkIID, ptMTPM2UALinkL3State, 
                      ptMTPM2UALinkLinkName }
    STATUS          current
    DESCRIPTION     
            "This trap indicates that an SLS Table Link Audit
             has concluded and this link is no longer included
             incorrectly in SLS Tables. The link may have been
             removed from SLS Tables, or its state may have
             changed so it is now appropriate for use in SLS
             Tables.
               
             Clears m2uaSLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9994 }

ptM2PALinkM2paSLSLinkAuditFailure NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "MTP3 detected an unavailable link in an SLS Table. MSU loss is possible.
             Cleared by m2paSLSLinkAuditFailureClear.
             
                 Cause  - MTP3 detected an unavailable link in an SLS Table.
                 
                 Action - This alarm should resolve itself in less than four minutes.
                          If this alarm does not clear itself you should reset the link
                          using the 'Reset' action on the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9995 }

ptM2PALinkM2paSLSLinkAuditFailureClear NOTIFICATION-TYPE
    OBJECTS         { ptTrapType, ptTrapSequenceNumber, ptTrapSeverity, 
                      ptTrapProbableCause, ptTrapClearType, 
                      ptTrapDateAndTime, ptTrapItemOID, ptMTPM2PALinkAPC, 
                      ptMTPM2PALinkSLC, ptMTPM2PALinkLocalIPAddress1, 
                      ptMTPM2PALinkLocalIPAddress2, 
                      ptMTPM2PALinkLocalPort, 
                      ptMTPM2PALinkRemoteIPAddress1, 
                      ptMTPM2PALinkRemoteIPAddress2, 
                      ptMTPM2PALinkRemotePort, ptMTPM2PALinkL3State, 
                      ptMTPM2PALinkLinkName }
    STATUS          current
    DESCRIPTION     
            "This trap indicates that an SLS Table Link Audit
             has concluded and this link is no longer included
             incorrectly in SLS Tables. The link may have been
             removed from SLS Tables, or its state may have
             changed so it is now appropriate for use in SLS
             Tables.
               
             Clears m2paSLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9996 }

ptGenericLinkGenericSLSLinkAuditFailure NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "MTP3 detected an unavailable link in an SLS Table. MSU loss is possible.
             Cleared by GenericSLSLinkAuditFailureClear.
             
                 Cause  - MTP3 detected an unavailable link in an SLS Table.
                 
                 Action - This alarm should resolve itself in less than four minutes.
                          If this alarm does not clear itself you should deactivate and
                          activate the link.
             
                 Freq   - Operator dependant.
             
               References
                 None. This is an implementation specific audit.
             
                 ptOriginatingOID:      DYNAMIC ptLink
                 ptTrapType:            2 communicationAlarm
                 ptTrapSeverity:        1 critical
                 ptTrapProbableCause:   6 Communication subsystem error
                 ptTrapClearType:       1 fmic
             "
    ::= { ptiSegway 0 9997 }

ptGenericLinkGenericSLSLinkAuditFailureClear NOTIFICATION-TYPE
    OBJECTS         { ptTrapType, ptTrapSequenceNumber, ptTrapSeverity, 
                      ptTrapProbableCause, ptTrapClearType, 
                      ptTrapDateAndTime, ptTrapItemOID, 
                      ptMTPGenericLinkSLC, 
                      ptMTPGenericLinkLocalIPAddress1, 
                      ptMTPGenericLinkLocalIPAddress2, 
                      ptMTPGenericLinkLocalPort, 
                      ptMTPGenericLinkRemoteIPAddress1, 
                      ptMTPGenericLinkRemoteIPAddress2, 
                      ptMTPGenericLinkRemotePort, 
                      ptMTPGenericLinkL3State, ptMTPGenericLinkLinkType }
    STATUS          current
    DESCRIPTION     
            "This trap indicates that an SLS Table Link Audit
             has concluded and this link is no longer included
             incorrectly in SLS Tables. The link may have been
             removed from SLS Tables, or its state may have
             changed so it is now appropriate for use in SLS
             Tables.
               
             Clears GenericSLSLinkAuditFailure.
             
             References
               None. This is an implementation specific audit.
             
               ptOriginatingOID:      DYNAMIC ptLink
               ptTrapType:            2 communicationAlarm
               ptTrapSeverity:        5 cleared
               ptTrapProbableCause:   6 Communication subsystem error
               ptTrapClearType:       1 fmic
             "
    ::= { ptiSegway 0 9998 }

END -- end of module PTISEGWAY-MIB.
