--
-- This SMIv1 module has been generated by smidump 0.2-cvs. Do not edit.
--

FOUNDRY-SN-SW-L4-SWITCH-GROUP-MIB DEFINITIONS ::= BEGIN

IMPORTS
    snL4
        FROM FOUNDRY-SN-ROOT-MIB
    OBJECT-TYPE
        FROM RFC-1212
    Counter, IpAddress
        FROM RFC1155-SMI;

L4RowSts ::=
    INTEGER { other(1), valid(2), delete(3), create(4), modify(5) }

L4Status ::=
    INTEGER { disabled(0), enabled(1) }

L4ServerName ::=
    OCTET STRING (SIZE(1..32))

L4Flag ::=
    INTEGER { false(0), true(1) }

L4DeleteState ::=
    INTEGER { done(0), waitunbind(1), waitdelete(2) }

WebCacheState ::=
    INTEGER { disabled(0), enabled(1), failed(2), testing(3), suspect(4), 
                        shutdown(5), active(6) }

PhysAddress ::=
    OCTET STRING

DisplayString ::=
    OCTET STRING

snL4Gen OBJECT IDENTIFIER
    ::= { snL4 1 }

snL4MaxSessionLimit OBJECT-TYPE
    SYNTAX          INTEGER (0..1000000)
    ACCESS          read-write
    DESCRIPTION     
            "numbers of maximum session (L4 cache) entries"
    ::= { snL4Gen 1 }

snL4TcpSynLimit OBJECT-TYPE
    SYNTAX          INTEGER (1..65535)
    ACCESS          read-write
    DESCRIPTION     
            "Numbers of connection per second"
    ::= { snL4Gen 2 }

snL4slbGlobalSDAType OBJECT-TYPE
    SYNTAX          INTEGER { leastconnection(1), roundrobin(2), 
                        weighted(3) }
    ACCESS          read-write
    DESCRIPTION     
            "Global Session Distribution Algorithm(SDA)"
    ::= { snL4Gen 3 }

snL4slbTotalConnections OBJECT-TYPE
    SYNTAX          Counter
    ACCESS          read-only
    DESCRIPTION     
            "Total connections in this device"
    ::= { snL4Gen 4 }

snL4slbLimitExceeds OBJECT-TYPE
    SYNTAX          INTEGER
    ACCESS          read-only
    DESCRIPTION     
            "exceeds snL4TCPSynLimit (numbers of connection per second)"
    ::= { snL4Gen 5 }

snL4slbForwardTraffic OBJECT-TYPE
    SYNTAX          Counter
    ACCESS          read-only
    DESCRIPTION     
            "Client->Server"
    ::= { snL4Gen 6 }

snL4slbReverseTraffic OBJECT-TYPE
    SYNTAX          Counter
    ACCESS          read-only
    DESCRIPTION     
            "Server->Client"
    ::= { snL4Gen 7 }

snL4slbDrops OBJECT-TYPE
    SYNTAX          INTEGER
    ACCESS          read-only
    DESCRIPTION     
            ""
    ::= { snL4Gen 8 }

snL4slbDangling OBJECT-TYPE
    SYNTAX          INTEGER
    ACCESS          read-only
    DESCRIPTION     
            ""
    ::= { snL4Gen 9 }

snL4slbDisableCount OBJECT-TYPE
    SYNTAX          INTEGER
    ACCESS          read-only
    DESCRIPTION     
            ""
    ::= { snL4Gen 10 }

snL4slbAged OBJECT-TYPE
    SYNTAX          INTEGER
    ACCESS          read-only
    DESCRIPTION     
            ""
    ::= { snL4Gen 11 }

snL4slbFinished OBJECT-TYPE
    SYNTAX          INTEGER
    ACCESS          read-only
    DESCRIPTION     
            "FIN_or_RST"
    ::= { snL4Gen 12 }

snL4FreeSessionCount OBJECT-TYPE
    SYNTAX          INTEGER
    ACCESS          read-only
    DESCRIPTION     
            "Maximum sessions - used sessions"
    ::= { snL4Gen 13 }

snL4BackupInterface OBJECT-TYPE
    SYNTAX          INTEGER (0..26)
    ACCESS          read-write
    DESCRIPTION     
            "backup monitoring port"
    ::= { snL4Gen 14 }

snL4BackupMacAddr OBJECT-TYPE
    SYNTAX          PhysAddress
    ACCESS          read-write
    DESCRIPTION     
            "Associated MAC address for backup monitoring port"
    ::= { snL4Gen 15 }

snL4Active OBJECT-TYPE
    SYNTAX          L4Flag
    ACCESS          read-only
    DESCRIPTION     
            ""
    ::= { snL4Gen 16 }

snL4Redundancy OBJECT-TYPE
    SYNTAX          INTEGER
    ACCESS          read-only
    DESCRIPTION     
            ""
    ::= { snL4Gen 17 }

snL4Backup OBJECT-TYPE
    SYNTAX          L4Flag
    ACCESS          read-only
    DESCRIPTION     
            "true->StandBy,false->active"
    ::= { snL4Gen 18 }

snL4BecomeActive OBJECT-TYPE
    SYNTAX          INTEGER
    ACCESS          read-only
    DESCRIPTION     
            "How many times this device become active"
    ::= { snL4Gen 19 }

snL4BecomeStandBy OBJECT-TYPE
    SYNTAX          INTEGER
    ACCESS          read-only
    DESCRIPTION     
            "How many times this device become standby"
    ::= { snL4Gen 20 }

snL4BackupState OBJECT-TYPE
    SYNTAX          INTEGER { slbSyncComplete(0), slbSyncReqMap(1), 
                        slbSyncreqMac(2), slbSyncreqServers(3), 
                        slbSyncReqL4(4) }
    ACCESS          read-only
    DESCRIPTION     
            "Backup state"
    ::= { snL4Gen 21 }

snL4NoPDUSent OBJECT-TYPE
    SYNTAX          INTEGER
    ACCESS          read-only
    DESCRIPTION     
            ""
    ::= { snL4Gen 22 }

snL4NoPDUCount OBJECT-TYPE
    SYNTAX          INTEGER
    ACCESS          read-only
    DESCRIPTION     
            ""
    ::= { snL4Gen 23 }

snL4NoPortMap OBJECT-TYPE
    SYNTAX          INTEGER
    ACCESS          read-only
    DESCRIPTION     
            ""
    ::= { snL4Gen 24 }

snL4unsuccessfulConn OBJECT-TYPE
    SYNTAX          INTEGER
    ACCESS          read-only
    DESCRIPTION     
            "Unsuccessfull connection"
    ::= { snL4Gen 25 }

snL4PingInterval OBJECT-TYPE
    SYNTAX          INTEGER (1..10)
    ACCESS          read-write
    DESCRIPTION     
            "Ping retries interval"
    DEFVAL          { 2 }
    ::= { snL4Gen 26 }

snL4PingRetry OBJECT-TYPE
    SYNTAX          INTEGER (2..10)
    ACCESS          read-write
    DESCRIPTION     
            "Ping retries attempts"
    DEFVAL          { 4 }
    ::= { snL4Gen 27 }

snL4TcpAge OBJECT-TYPE
    SYNTAX          INTEGER (2..60)
    ACCESS          read-write
    DESCRIPTION     
            "TCP reset age"
    DEFVAL          { 30 }
    ::= { snL4Gen 28 }

snL4UdpAge OBJECT-TYPE
    SYNTAX          INTEGER (2..60)
    ACCESS          read-write
    DESCRIPTION     
            "UDP reset age"
    DEFVAL          { 5 }
    ::= { snL4Gen 29 }

snL4EnableMaxSessionLimitReachedTrap OBJECT-TYPE
    SYNTAX          INTEGER { disabled(0), enabled(1) }
    ACCESS          read-write
    DESCRIPTION     
            "Enable/disable maximum number of connections reached trap."
    ::= { snL4Gen 30 }

snL4EnableTcpSynLimitReachedTrap OBJECT-TYPE
    SYNTAX          INTEGER { disabled(0), enabled(1) }
    ACCESS          read-write
    DESCRIPTION     
            "Enable/disable the number of TCP SYN limits reached trap."
    ::= { snL4Gen 31 }

snL4EnableRealServerUpTrap OBJECT-TYPE
    SYNTAX          INTEGER { disabled(0), enabled(1) }
    ACCESS          read-write
    DESCRIPTION     
            "Enable/disable the real server up trap."
    ::= { snL4Gen 32 }

snL4EnableRealServerDownTrap OBJECT-TYPE
    SYNTAX          INTEGER { disabled(0), enabled(1) }
    ACCESS          read-write
    DESCRIPTION     
            "Enable/disable the real server down trap."
    ::= { snL4Gen 33 }

snL4EnableRealServerPortUpTrap OBJECT-TYPE
    SYNTAX          INTEGER { disabled(0), enabled(1) }
    ACCESS          read-write
    DESCRIPTION     
            "Enable/disable the real server TCP port up trap."
    ::= { snL4Gen 34 }

snL4EnableRealServerPortDownTrap OBJECT-TYPE
    SYNTAX          INTEGER { disabled(0), enabled(1) }
    ACCESS          read-write
    DESCRIPTION     
            "Enable/disable the real server TCP port down trap."
    ::= { snL4Gen 35 }

snL4EnableRealServerMaxConnLimitReachedTrap OBJECT-TYPE
    SYNTAX          INTEGER { disabled(0), enabled(1) }
    ACCESS          read-write
    DESCRIPTION     
            "Enable/disable the real server maximum number of
             connections reached trap."
    ::= { snL4Gen 36 }

snL4EnableBecomeStandbyTrap OBJECT-TYPE
    SYNTAX          INTEGER { disabled(0), enabled(1) }
    ACCESS          read-write
    DESCRIPTION     
            "Enable/disable trap of the server load balancing
             switch changes state from active to standby."
    ::= { snL4Gen 37 }

snL4EnableBecomeActiveTrap OBJECT-TYPE
    SYNTAX          INTEGER { disabled(0), enabled(1) }
    ACCESS          read-write
    DESCRIPTION     
            "Enable/disable trap of the server load balancing
             switch changes state from standby to active."
    ::= { snL4Gen 38 }

snL4slbRouterInterfacePortMask OBJECT-TYPE
    SYNTAX          INTEGER
    ACCESS          read-write
    DESCRIPTION     
            "Router interface port mask."
    ::= { snL4Gen 39 }

snL4MaxNumWebCacheGroup OBJECT-TYPE
    SYNTAX          INTEGER
    ACCESS          read-only
    DESCRIPTION     
            "The maximum number of server cache groups"
    ::= { snL4Gen 40 }

snL4MaxNumWebCachePerGroup OBJECT-TYPE
    SYNTAX          INTEGER
    ACCESS          read-only
    DESCRIPTION     
            "The maximum number of WEB Cache servers in each of web cache group"
    ::= { snL4Gen 41 }

snL4WebCacheStateful OBJECT-TYPE
    SYNTAX          L4Status
    ACCESS          read-write
    DESCRIPTION     
            "The WEB Cache servers cache-stateful"
    ::= { snL4Gen 42 }

snL4EnableGslbHealthCheckIpUpTrap OBJECT-TYPE
    SYNTAX          INTEGER { disabled(0), enabled(1) }
    ACCESS          read-write
    DESCRIPTION     
            "Health check IP up."
    ::= { snL4Gen 43 }

snL4EnableGslbHealthCheckIpDownTrap OBJECT-TYPE
    SYNTAX          INTEGER { disabled(0), enabled(1) }
    ACCESS          read-write
    DESCRIPTION     
            "Health check IP down."
    ::= { snL4Gen 44 }

snL4EnableGslbHealthCheckIpPortUpTrap OBJECT-TYPE
    SYNTAX          INTEGER { disabled(0), enabled(1) }
    ACCESS          read-write
    DESCRIPTION     
            "Health check IP port up."
    ::= { snL4Gen 45 }

snL4EnableGslbHealthCheckIpPortDownTrap OBJECT-TYPE
    SYNTAX          INTEGER { disabled(0), enabled(1) }
    ACCESS          read-write
    DESCRIPTION     
            "Health check IP port down."
    ::= { snL4Gen 46 }

snL4EnableGslbRemoteGslbSiDownTrap OBJECT-TYPE
    SYNTAX          INTEGER { disabled(0), enabled(1) }
    ACCESS          read-write
    DESCRIPTION     
            "Connection to GSLB ServerIron is down."
    ::= { snL4Gen 47 }

snL4EnableGslbRemoteGslbSiUpTrap OBJECT-TYPE
    SYNTAX          INTEGER { disabled(0), enabled(1) }
    ACCESS          read-write
    DESCRIPTION     
            "Connection to GSLB ServerIron is up."
    ::= { snL4Gen 48 }

snL4EnableGslbRemoteSiDownTrap OBJECT-TYPE
    SYNTAX          INTEGER { disabled(0), enabled(1) }
    ACCESS          read-write
    DESCRIPTION     
            "GSLB connection to remote ServerIron is down."
    ::= { snL4Gen 49 }

snL4EnableGslbRemoteSiUpTrap OBJECT-TYPE
    SYNTAX          INTEGER { disabled(0), enabled(1) }
    ACCESS          read-write
    DESCRIPTION     
            "GSLB connection to remote ServerIron is up."
    ::= { snL4Gen 50 }

snL4VirtualServer OBJECT IDENTIFIER
    ::= { snL4 2 }

snL4VirtualServerTable OBJECT-TYPE
    SYNTAX          SEQUENCE OF SnL4VirtualServerEntry
    ACCESS          not-accessible
    DESCRIPTION     
            "Virtual Server table."
    ::= { snL4VirtualServer 1 }

snL4VirtualServerEntry OBJECT-TYPE
    SYNTAX          SnL4VirtualServerEntry
    ACCESS          not-accessible
    DESCRIPTION     
            "An entry in L4 Virtual Server table."
    INDEX           { snL4VirtualServerIndex }
    ::= { snL4VirtualServerTable 1 }

SnL4VirtualServerEntry ::=
    SEQUENCE {
        snL4VirtualServerIndex          INTEGER,
        snL4VirtualServerName           L4ServerName,
        snL4VirtualServerVirtualIP      IpAddress,
        snL4VirtualServerAdminStatus    L4Status,
        snL4VirtualServerSDAType        INTEGER,
        snL4VirtualServerRowStatus      L4RowSts,
        snL4VirtualServerDeleteState    L4DeleteState
    }

snL4VirtualServerIndex OBJECT-TYPE
    SYNTAX          INTEGER (1..64)
    ACCESS          read-only
    DESCRIPTION     
            "The table index for a Virtual Server  entry."
    ::= { snL4VirtualServerEntry 1 }

snL4VirtualServerName OBJECT-TYPE
    SYNTAX          L4ServerName
    ACCESS          read-write
    DESCRIPTION     
            "Virtual server name."
    ::= { snL4VirtualServerEntry 2 }

snL4VirtualServerVirtualIP OBJECT-TYPE
    SYNTAX          IpAddress
    ACCESS          read-write
    DESCRIPTION     
            "Virtual Server IP Address."
    ::= { snL4VirtualServerEntry 3 }

snL4VirtualServerAdminStatus OBJECT-TYPE
    SYNTAX          L4Status
    ACCESS          read-write
    DESCRIPTION     
            "Virtual Server status is ether disabled(0) or enabled(1)."
    ::= { snL4VirtualServerEntry 4 }

snL4VirtualServerSDAType OBJECT-TYPE
    SYNTAX          INTEGER { default(0), leastconnection(1), 
                        roundrobin(2), weighted(3) }
    ACCESS          read-write
    DESCRIPTION     
            "TCP/UDP Sessions Distribution Algorithms Type."
    ::= { snL4VirtualServerEntry 5 }

snL4VirtualServerRowStatus OBJECT-TYPE
    SYNTAX          L4RowSts
    ACCESS          read-write
    DESCRIPTION     
            "To create or delete a virtual server
             entry."
    ::= { snL4VirtualServerEntry 6 }

snL4VirtualServerDeleteState OBJECT-TYPE
    SYNTAX          L4DeleteState
    ACCESS          read-only
    DESCRIPTION     
            "Delete operation state."
    ::= { snL4VirtualServerEntry 7 }

snL4RealServer OBJECT IDENTIFIER
    ::= { snL4 3 }

snL4RealServerTable OBJECT-TYPE
    SYNTAX          SEQUENCE OF SnL4RealServerEntry
    ACCESS          not-accessible
    DESCRIPTION     
            "Real Server table."
    ::= { snL4RealServer 1 }

snL4RealServerEntry OBJECT-TYPE
    SYNTAX          SnL4RealServerEntry
    ACCESS          not-accessible
    DESCRIPTION     
            "An entry in the Real Server table."
    INDEX           { snL4RealServerIndex }
    ::= { snL4RealServerTable 1 }

SnL4RealServerEntry ::=
    SEQUENCE {
        snL4RealServerIndex             INTEGER,
        snL4RealServerName              L4ServerName,
        snL4RealServerIP                IpAddress,
        snL4RealServerAdminStatus       L4Status,
        snL4RealServerMaxConnections    INTEGER,
        snL4RealServerWeight            INTEGER,
        snL4RealServerRowStatus         L4RowSts,
        snL4RealServerDeleteState       L4DeleteState
    }

snL4RealServerIndex OBJECT-TYPE
    SYNTAX          INTEGER (1..256)
    ACCESS          read-only
    DESCRIPTION     
            "The table index for a Real Server entry."
    ::= { snL4RealServerEntry 1 }

snL4RealServerName OBJECT-TYPE
    SYNTAX          L4ServerName
    ACCESS          read-write
    DESCRIPTION     
            "Real server name."
    ::= { snL4RealServerEntry 2 }

snL4RealServerIP OBJECT-TYPE
    SYNTAX          IpAddress
    ACCESS          read-write
    DESCRIPTION     
            "Real Server IP Address."
    ::= { snL4RealServerEntry 3 }

snL4RealServerAdminStatus OBJECT-TYPE
    SYNTAX          L4Status
    ACCESS          read-write
    DESCRIPTION     
            "Real Server status is ether disabled(0) or enabled(1)."
    ::= { snL4RealServerEntry 4 }

snL4RealServerMaxConnections OBJECT-TYPE
    SYNTAX          INTEGER (0..1000000)
    ACCESS          read-write
    DESCRIPTION     
            "Real Server Maximum Connection allowed."
    ::= { snL4RealServerEntry 5 }

snL4RealServerWeight OBJECT-TYPE
    SYNTAX          INTEGER (1..20)
    ACCESS          read-write
    DESCRIPTION     
            "Real Server weight"
    ::= { snL4RealServerEntry 6 }

snL4RealServerRowStatus OBJECT-TYPE
    SYNTAX          L4RowSts
    ACCESS          read-write
    DESCRIPTION     
            "To create or delete a real server entry."
    ::= { snL4RealServerEntry 7 }

snL4RealServerDeleteState OBJECT-TYPE
    SYNTAX          L4DeleteState
    ACCESS          read-only
    DESCRIPTION     
            "Delete operation state."
    ::= { snL4RealServerEntry 8 }

snL4VirtualServerPort OBJECT IDENTIFIER
    ::= { snL4 4 }

snL4VirtualServerPortTable OBJECT-TYPE
    SYNTAX          SEQUENCE OF SnL4VirtualServerPortEntry
    ACCESS          not-accessible
    DESCRIPTION     
            "Virtual Server Port table."
    ::= { snL4VirtualServerPort 1 }

snL4VirtualServerPortEntry OBJECT-TYPE
    SYNTAX          SnL4VirtualServerPortEntry
    ACCESS          not-accessible
    DESCRIPTION     
            "An entry in the Virtual Server Port table."
    INDEX           { snL4VirtualServerPortIndex }
    ::= { snL4VirtualServerPortTable 1 }

SnL4VirtualServerPortEntry ::=
    SEQUENCE {
        snL4VirtualServerPortIndex      INTEGER,
        snL4VirtualServerPortServerName L4ServerName,
        snL4VirtualServerPortPort       INTEGER,
        snL4VirtualServerPortAdminStatus L4Status,
        snL4VirtualServerPortSticky     INTEGER,
        snL4VirtualServerPortConcurrent INTEGER,
        snL4VirtualServerPortRowStatus  L4RowSts,
        snL4VirtualServerPortDeleteState L4DeleteState
    }

snL4VirtualServerPortIndex OBJECT-TYPE
    SYNTAX          INTEGER (1..2048)
    ACCESS          read-only
    DESCRIPTION     
            "The index for Virtual Server Port entry."
    ::= { snL4VirtualServerPortEntry 1 }

snL4VirtualServerPortServerName OBJECT-TYPE
    SYNTAX          L4ServerName
    ACCESS          read-write
    DESCRIPTION     
            ""
    ::= { snL4VirtualServerPortEntry 2 }

snL4VirtualServerPortPort OBJECT-TYPE
    SYNTAX          INTEGER (0..65535)
    ACCESS          read-write
    DESCRIPTION     
            ""
    ::= { snL4VirtualServerPortEntry 3 }

snL4VirtualServerPortAdminStatus OBJECT-TYPE
    SYNTAX          L4Status
    ACCESS          read-write
    DESCRIPTION     
            ""
    ::= { snL4VirtualServerPortEntry 4 }

snL4VirtualServerPortSticky OBJECT-TYPE
    SYNTAX          INTEGER { disabled(0), enabled(1) }
    ACCESS          read-write
    DESCRIPTION     
            ""
    ::= { snL4VirtualServerPortEntry 5 }

snL4VirtualServerPortConcurrent OBJECT-TYPE
    SYNTAX          INTEGER { disabled(0), enabled(1) }
    ACCESS          read-write
    DESCRIPTION     
            ""
    ::= { snL4VirtualServerPortEntry 6 }

snL4VirtualServerPortRowStatus OBJECT-TYPE
    SYNTAX          L4RowSts
    ACCESS          read-write
    DESCRIPTION     
            "To create or delete a virtual server  port entry."
    ::= { snL4VirtualServerPortEntry 7 }

snL4VirtualServerPortDeleteState OBJECT-TYPE
    SYNTAX          L4DeleteState
    ACCESS          read-only
    DESCRIPTION     
            "Delete operation state."
    ::= { snL4VirtualServerPortEntry 8 }

snL4RealServerPort OBJECT IDENTIFIER
    ::= { snL4 5 }

snL4RealServerPortTable OBJECT-TYPE
    SYNTAX          SEQUENCE OF SnL4RealServerPortEntry
    ACCESS          not-accessible
    DESCRIPTION     
            "Real Server Port table."
    ::= { snL4RealServerPort 1 }

snL4RealServerPortEntry OBJECT-TYPE
    SYNTAX          SnL4RealServerPortEntry
    ACCESS          not-accessible
    DESCRIPTION     
            "An entry in the Real Server Port table."
    INDEX           { snL4RealServerPortIndex }
    ::= { snL4RealServerPortTable 1 }

SnL4RealServerPortEntry ::=
    SEQUENCE {
        snL4RealServerPortIndex         INTEGER,
        snL4RealServerPortServerName    L4ServerName,
        snL4RealServerPortPort          INTEGER,
        snL4RealServerPortAdminStatus   L4Status,
        snL4RealServerPortRowStatus     L4RowSts,
        snL4RealServerPortDeleteState   L4DeleteState
    }

snL4RealServerPortIndex OBJECT-TYPE
    SYNTAX          INTEGER (1..2048)
    ACCESS          read-only
    DESCRIPTION     
            "The index for Real Server Port entry."
    ::= { snL4RealServerPortEntry 1 }

snL4RealServerPortServerName OBJECT-TYPE
    SYNTAX          L4ServerName
    ACCESS          read-write
    DESCRIPTION     
            ""
    ::= { snL4RealServerPortEntry 2 }

snL4RealServerPortPort OBJECT-TYPE
    SYNTAX          INTEGER (0..65535)
    ACCESS          read-write
    DESCRIPTION     
            ""
    ::= { snL4RealServerPortEntry 3 }

snL4RealServerPortAdminStatus OBJECT-TYPE
    SYNTAX          L4Status
    ACCESS          read-write
    DESCRIPTION     
            ""
    ::= { snL4RealServerPortEntry 4 }

snL4RealServerPortRowStatus OBJECT-TYPE
    SYNTAX          L4RowSts
    ACCESS          read-write
    DESCRIPTION     
            "To create or delete a Real server  port entry."
    ::= { snL4RealServerPortEntry 5 }

snL4RealServerPortDeleteState OBJECT-TYPE
    SYNTAX          L4DeleteState
    ACCESS          read-only
    DESCRIPTION     
            "Delete operation state."
    ::= { snL4RealServerPortEntry 6 }

snL4Bind OBJECT IDENTIFIER
    ::= { snL4 6 }

snL4BindTable OBJECT-TYPE
    SYNTAX          SEQUENCE OF SnL4BindEntry
    ACCESS          not-accessible
    DESCRIPTION     
            "Bind table."
    ::= { snL4Bind 1 }

snL4BindEntry OBJECT-TYPE
    SYNTAX          SnL4BindEntry
    ACCESS          not-accessible
    DESCRIPTION     
            "An entry in the Bind table."
    INDEX           { snL4BindIndex }
    ::= { snL4BindTable 1 }

SnL4BindEntry ::=
    SEQUENCE {
        snL4BindIndex                   INTEGER,
        snL4BindVirtualServerName       L4ServerName,
        snL4BindVirtualPortNumber       INTEGER,
        snL4BindRealServerName          L4ServerName,
        snL4BindRealPortNumber          INTEGER,
        snL4BindRowStatus               INTEGER
    }

snL4BindIndex OBJECT-TYPE
    SYNTAX          INTEGER (1..2048)
    ACCESS          read-only
    DESCRIPTION     
            "The index for Bind entry."
    ::= { snL4BindEntry 1 }

snL4BindVirtualServerName OBJECT-TYPE
    SYNTAX          L4ServerName
    ACCESS          read-write
    DESCRIPTION     
            ""
    ::= { snL4BindEntry 2 }

snL4BindVirtualPortNumber OBJECT-TYPE
    SYNTAX          INTEGER (0..65535)
    ACCESS          read-write
    DESCRIPTION     
            ""
    ::= { snL4BindEntry 3 }

snL4BindRealServerName OBJECT-TYPE
    SYNTAX          L4ServerName
    ACCESS          read-write
    DESCRIPTION     
            ""
    ::= { snL4BindEntry 4 }

snL4BindRealPortNumber OBJECT-TYPE
    SYNTAX          INTEGER (0..65535)
    ACCESS          read-write
    DESCRIPTION     
            ""
    ::= { snL4BindEntry 5 }

snL4BindRowStatus OBJECT-TYPE
    SYNTAX          INTEGER { other(1), valid(2), delete(3), create(4) }
    ACCESS          read-write
    DESCRIPTION     
            "To create or delete bind entry."
    ::= { snL4BindEntry 6 }

snL4VirtualServerStatus OBJECT IDENTIFIER
    ::= { snL4 7 }

snL4VirtualServerStatusTable OBJECT-TYPE
    SYNTAX          SEQUENCE OF SnL4VirtualServerStatusEntry
    ACCESS          not-accessible
    DESCRIPTION     
            "Virtual Server Status table."
    ::= { snL4VirtualServerStatus 1 }

snL4VirtualServerStatusEntry OBJECT-TYPE
    SYNTAX          SnL4VirtualServerStatusEntry
    ACCESS          not-accessible
    DESCRIPTION     
            "An entry in L4 Virtual Server Status table."
    INDEX           { snL4VirtualServerStatusIndex }
    ::= { snL4VirtualServerStatusTable 1 }

SnL4VirtualServerStatusEntry ::=
    SEQUENCE {
        snL4VirtualServerStatusIndex    INTEGER,
        snL4VirtualServerStatusName     L4ServerName,
        snL4VirtualServerStatusReceivePkts  Counter,
        snL4VirtualServerStatusTransmitPkts   Counter,
        snL4VirtualServerStatusTotalConnections       Counter
    }

snL4VirtualServerStatusIndex OBJECT-TYPE
    SYNTAX          INTEGER (1..64)
    ACCESS          read-only
    DESCRIPTION     
            "The table index for a Virtual Server  Status entry."
    ::= { snL4VirtualServerStatusEntry 1 }

snL4VirtualServerStatusName OBJECT-TYPE
    SYNTAX          L4ServerName
    ACCESS          read-only
    DESCRIPTION     
            "Virtual server name."
    ::= { snL4VirtualServerStatusEntry 2 }

snL4VirtualServerStatusReceivePkts OBJECT-TYPE
    SYNTAX          Counter
    ACCESS          read-only
    DESCRIPTION     
            ""
    ::= { snL4VirtualServerStatusEntry 3 }

snL4VirtualServerStatusTransmitPkts OBJECT-TYPE
    SYNTAX          Counter
    ACCESS          read-only
    DESCRIPTION     
            ""
    ::= { snL4VirtualServerStatusEntry 4 }

snL4VirtualServerStatusTotalConnections OBJECT-TYPE
    SYNTAX          Counter
    ACCESS          read-only
    DESCRIPTION     
            ""
    ::= { snL4VirtualServerStatusEntry 5 }

snL4RealServerStatus OBJECT IDENTIFIER
    ::= { snL4 8 }

snL4RealServerStatusTable OBJECT-TYPE
    SYNTAX          SEQUENCE OF SnL4RealServerStatusEntry
    ACCESS          not-accessible
    DESCRIPTION     
            "Real Server Status table."
    ::= { snL4RealServerStatus 1 }

snL4RealServerStatusEntry OBJECT-TYPE
    SYNTAX          SnL4RealServerStatusEntry
    ACCESS          not-accessible
    DESCRIPTION     
            "An entry in the Real Server Status table."
    INDEX           { snL4RealServerStatusIndex }
    ::= { snL4RealServerStatusTable 1 }

SnL4RealServerStatusEntry ::=
    SEQUENCE {
        snL4RealServerStatusIndex       INTEGER,
        snL4RealServerStatusName        L4ServerName,
        snL4RealServerStatusRealIP      IpAddress,
        snL4RealServerStatusReceivePkts Counter,
        snL4RealServerStatusTransmitPkts Counter,
        snL4RealServerStatusCurConnections  INTEGER,
        snL4RealServerStatusTotalConnections    Counter,
        snL4RealServerStatusAge         INTEGER,
        snL4RealServerStatusState       INTEGER,
        snL4RealServerStatusReassignments INTEGER,
        snL4RealServerStatusReassignmentLimit     INTEGER,
        snL4RealServerStatusFailedPortExists    INTEGER,
        snL4RealServerStatusFailTime    INTEGER,
        snL4RealServerStatusPeakConnections   INTEGER
    }

snL4RealServerStatusIndex OBJECT-TYPE
    SYNTAX          INTEGER (1..256)
    ACCESS          read-only
    DESCRIPTION     
            "The table index for a Real Server Status entry."
    ::= { snL4RealServerStatusEntry 1 }

snL4RealServerStatusName OBJECT-TYPE
    SYNTAX          L4ServerName
    ACCESS          read-only
    DESCRIPTION     
            ""
    ::= { snL4RealServerStatusEntry 2 }

snL4RealServerStatusRealIP OBJECT-TYPE
    SYNTAX          IpAddress
    ACCESS          read-only
    DESCRIPTION     
            ""
    ::= { snL4RealServerStatusEntry 3 }

snL4RealServerStatusReceivePkts OBJECT-TYPE
    SYNTAX          Counter
    ACCESS          read-only
    DESCRIPTION     
            ""
    ::= { snL4RealServerStatusEntry 4 }

snL4RealServerStatusTransmitPkts OBJECT-TYPE
    SYNTAX          Counter
    ACCESS          read-only
    DESCRIPTION     
            ""
    ::= { snL4RealServerStatusEntry 5 }

snL4RealServerStatusCurConnections OBJECT-TYPE
    SYNTAX          INTEGER
    ACCESS          read-only
    DESCRIPTION     
            ""
    ::= { snL4RealServerStatusEntry 6 }

snL4RealServerStatusTotalConnections OBJECT-TYPE
    SYNTAX          Counter
    ACCESS          read-only
    DESCRIPTION     
            ""
    ::= { snL4RealServerStatusEntry 7 }

snL4RealServerStatusAge OBJECT-TYPE
    SYNTAX          INTEGER
    ACCESS          read-only
    DESCRIPTION     
            ""
    ::= { snL4RealServerStatusEntry 8 }

snL4RealServerStatusState OBJECT-TYPE
    SYNTAX          INTEGER { serverdisabled(0), serverenabled(1), 
                        serverfailed(2), servertesting(3), 
                        serversuspect(4), servershutdown(5), 
                        serveractive(6) }
    ACCESS          read-only
    DESCRIPTION     
            ""
    ::= { snL4RealServerStatusEntry 9 }

snL4RealServerStatusReassignments OBJECT-TYPE
    SYNTAX          INTEGER
    ACCESS          read-only
    DESCRIPTION     
            ""
    ::= { snL4RealServerStatusEntry 10 }

snL4RealServerStatusReassignmentLimit OBJECT-TYPE
    SYNTAX          INTEGER
    ACCESS          read-only
    DESCRIPTION     
            ""
    ::= { snL4RealServerStatusEntry 11 }

snL4RealServerStatusFailedPortExists OBJECT-TYPE
    SYNTAX          INTEGER
    ACCESS          read-only
    DESCRIPTION     
            ""
    ::= { snL4RealServerStatusEntry 12 }

snL4RealServerStatusFailTime OBJECT-TYPE
    SYNTAX          INTEGER
    ACCESS          read-only
    DESCRIPTION     
            ""
    ::= { snL4RealServerStatusEntry 13 }

snL4RealServerStatusPeakConnections OBJECT-TYPE
    SYNTAX          INTEGER
    ACCESS          read-only
    DESCRIPTION     
            ""
    ::= { snL4RealServerStatusEntry 14 }

snL4VirtualServerPortStatus OBJECT IDENTIFIER
    ::= { snL4 9 }

snL4VirtualServerPortStatusTable OBJECT-TYPE
    SYNTAX          SEQUENCE OF SnL4VirtualServerPortStatusEntry
    ACCESS          not-accessible
    DESCRIPTION     
            "Virtual Server Port Status table."
    ::= { snL4VirtualServerPortStatus 1 }

snL4VirtualServerPortStatusEntry OBJECT-TYPE
    SYNTAX          SnL4VirtualServerPortStatusEntry
    ACCESS          not-accessible
    DESCRIPTION     
            "An entry in the Virtual Server Port Status table."
    INDEX           { snL4VirtualServerPortStatusIndex }
    ::= { snL4VirtualServerPortStatusTable 1 }

SnL4VirtualServerPortStatusEntry ::=
    SEQUENCE {
        snL4VirtualServerPortStatusIndex INTEGER,
        snL4VirtualServerPortStatusPort INTEGER,
        snL4VirtualServerPortStatusServerName     L4ServerName,
        snL4VirtualServerPortStatusCurrentConnection            INTEGER,
        snL4VirtualServerPortStatusTotalConnection          Counter,
        snL4VirtualServerPortStatusPeakConnection         INTEGER
    }

snL4VirtualServerPortStatusIndex OBJECT-TYPE
    SYNTAX          INTEGER
    ACCESS          read-only
    DESCRIPTION     
            "The index for Virtual Server Port Status entry."
    ::= { snL4VirtualServerPortStatusEntry 1 }

snL4VirtualServerPortStatusPort OBJECT-TYPE
    SYNTAX          INTEGER (1..2048)
    ACCESS          read-only
    DESCRIPTION     
            ""
    ::= { snL4VirtualServerPortStatusEntry 2 }

snL4VirtualServerPortStatusServerName OBJECT-TYPE
    SYNTAX          L4ServerName
    ACCESS          read-only
    DESCRIPTION     
            ""
    ::= { snL4VirtualServerPortStatusEntry 3 }

snL4VirtualServerPortStatusCurrentConnection OBJECT-TYPE
    SYNTAX          INTEGER
    ACCESS          read-only
    DESCRIPTION     
            ""
    ::= { snL4VirtualServerPortStatusEntry 4 }

snL4VirtualServerPortStatusTotalConnection OBJECT-TYPE
    SYNTAX          Counter
    ACCESS          read-only
    DESCRIPTION     
            ""
    ::= { snL4VirtualServerPortStatusEntry 5 }

snL4VirtualServerPortStatusPeakConnection OBJECT-TYPE
    SYNTAX          INTEGER
    ACCESS          read-only
    DESCRIPTION     
            ""
    ::= { snL4VirtualServerPortStatusEntry 6 }

snL4RealServerPortStatus OBJECT IDENTIFIER
    ::= { snL4 10 }

snL4RealServerPortStatusTable OBJECT-TYPE
    SYNTAX          SEQUENCE OF SnL4RealServerPortStatusEntry
    ACCESS          not-accessible
    DESCRIPTION     
            "Real Server Port Status table."
    ::= { snL4RealServerPortStatus 1 }

snL4RealServerPortStatusEntry OBJECT-TYPE
    SYNTAX          SnL4RealServerPortStatusEntry
    ACCESS          not-accessible
    DESCRIPTION     
            "An entry in the Real Server Port Status table."
    INDEX           { snL4RealServerPortStatusIndex }
    ::= { snL4RealServerPortStatusTable 1 }

SnL4RealServerPortStatusEntry ::=
    SEQUENCE {
        snL4RealServerPortStatusIndex   INTEGER,
        snL4RealServerPortStatusPort    INTEGER,
        snL4RealServerPortStatusServerName  L4ServerName,
        snL4RealServerPortStatusReassignCount     INTEGER,
        snL4RealServerPortStatusState   INTEGER,
        snL4RealServerPortStatusFailTime INTEGER,
        snL4RealServerPortStatusCurrentConnection         INTEGER,
        snL4RealServerPortStatusTotalConnection       Counter,
        snL4RealServerPortStatusRxPkts  Counter,
        snL4RealServerPortStatusTxPkts  Counter,
        snL4RealServerPortStatusRxBytes Counter,
        snL4RealServerPortStatusTxBytes Counter,
        snL4RealServerPortStatusPeakConnection      INTEGER
    }

snL4RealServerPortStatusIndex OBJECT-TYPE
    SYNTAX          INTEGER (1..2048)
    ACCESS          read-only
    DESCRIPTION     
            "The index for Real Server Port Status entry."
    ::= { snL4RealServerPortStatusEntry 1 }

snL4RealServerPortStatusPort OBJECT-TYPE
    SYNTAX          INTEGER
    ACCESS          read-only
    DESCRIPTION     
            ""
    ::= { snL4RealServerPortStatusEntry 2 }

snL4RealServerPortStatusServerName OBJECT-TYPE
    SYNTAX          L4ServerName
    ACCESS          read-only
    DESCRIPTION     
            ""
    ::= { snL4RealServerPortStatusEntry 3 }

snL4RealServerPortStatusReassignCount OBJECT-TYPE
    SYNTAX          INTEGER
    ACCESS          read-only
    DESCRIPTION     
            ""
    ::= { snL4RealServerPortStatusEntry 4 }

snL4RealServerPortStatusState OBJECT-TYPE
    SYNTAX          INTEGER { disabled(0), enabled(1), failed(2), 
                        testing(3), suspect(4), shutdown(5), active(6) }
    ACCESS          read-only
    DESCRIPTION     
            "Real server port state"
    ::= { snL4RealServerPortStatusEntry 5 }

snL4RealServerPortStatusFailTime OBJECT-TYPE
    SYNTAX          INTEGER
    ACCESS          read-only
    DESCRIPTION     
            "Only useful, if real server port state is failed.
             Indicating how seconds has been elapsed from the last retry."
    ::= { snL4RealServerPortStatusEntry 6 }

snL4RealServerPortStatusCurrentConnection OBJECT-TYPE
    SYNTAX          INTEGER
    ACCESS          read-only
    DESCRIPTION     
            "Real server port current connection"
    ::= { snL4RealServerPortStatusEntry 7 }

snL4RealServerPortStatusTotalConnection OBJECT-TYPE
    SYNTAX          Counter
    ACCESS          read-only
    DESCRIPTION     
            "Real server port total connection"
    ::= { snL4RealServerPortStatusEntry 8 }

snL4RealServerPortStatusRxPkts OBJECT-TYPE
    SYNTAX          Counter
    ACCESS          read-only
    DESCRIPTION     
            "Real server port receive packets."
    ::= { snL4RealServerPortStatusEntry 9 }

snL4RealServerPortStatusTxPkts OBJECT-TYPE
    SYNTAX          Counter
    ACCESS          read-only
    DESCRIPTION     
            "Real server port transmit packets."
    ::= { snL4RealServerPortStatusEntry 10 }

snL4RealServerPortStatusRxBytes OBJECT-TYPE
    SYNTAX          Counter
    ACCESS          read-only
    DESCRIPTION     
            "Real server port receive bytes."
    ::= { snL4RealServerPortStatusEntry 11 }

snL4RealServerPortStatusTxBytes OBJECT-TYPE
    SYNTAX          Counter
    ACCESS          read-only
    DESCRIPTION     
            "Real server port transmit bytes."
    ::= { snL4RealServerPortStatusEntry 12 }

snL4RealServerPortStatusPeakConnection OBJECT-TYPE
    SYNTAX          INTEGER
    ACCESS          read-only
    DESCRIPTION     
            "peak connection for real server port."
    ::= { snL4RealServerPortStatusEntry 13 }

snL4Policy OBJECT IDENTIFIER
    ::= { snL4 11 }

snL4PolicyTable OBJECT-TYPE
    SYNTAX          SEQUENCE OF SnL4PolicyEntry
    ACCESS          not-accessible
    DESCRIPTION     
            "L4 policy table."
    ::= { snL4Policy 1 }

snL4PolicyEntry OBJECT-TYPE
    SYNTAX          SnL4PolicyEntry
    ACCESS          not-accessible
    DESCRIPTION     
            "An entry of the L4 policy table."
    INDEX           { snL4PolicyId }
    ::= { snL4PolicyTable 1 }

SnL4PolicyEntry ::=
    SEQUENCE {
        snL4PolicyId                    INTEGER,
        snL4PolicyPriority              INTEGER,
        snL4PolicyScope                 INTEGER,
        snL4PolicyProtocol              INTEGER,
        snL4PolicyPort                  INTEGER,
        snL4PolicyRowStatus             INTEGER
    }

snL4PolicyId OBJECT-TYPE
    SYNTAX          INTEGER (1..64)
    ACCESS          read-only
    DESCRIPTION     
            "The  ID to identify a  entry."
    ::= { snL4PolicyEntry 1 }

snL4PolicyPriority OBJECT-TYPE
    SYNTAX          INTEGER { level0(0), level1(1), level2(2), level3(3), 
                        level4(4), level5(5), level6(6), level7(7) }
    ACCESS          read-write
    DESCRIPTION     
            "The Stand alone stackable switch L4 Policy Priority values are:
             normal(0)   		 -- normal prority
             high(1) 	 		 -- high prority
             cache(2) 	 		 -- prority for cache
             transparent(3) 	 -- prority for transparent
             The BigIron switch L4 Priority values are:
             level0(0), level1(1), level2(2), level3(3),
             level4(4), level5(5), level6(6), level7(7) "
    ::= { snL4PolicyEntry 2 }

snL4PolicyScope OBJECT-TYPE
    SYNTAX          INTEGER { global(0), local(1) }
    ACCESS          read-write
    DESCRIPTION     
            " Scope of the  local or global.
             Global  automatic apply to all port.
             Local  apply to a port."
    ::= { snL4PolicyEntry 3 }

snL4PolicyProtocol OBJECT-TYPE
    SYNTAX          INTEGER { udp(0), tcp(1) }
    ACCESS          read-write
    DESCRIPTION     
            ""
    ::= { snL4PolicyEntry 4 }

snL4PolicyPort OBJECT-TYPE
    SYNTAX          INTEGER (0..65535)
    ACCESS          read-write
    DESCRIPTION     
            ""
    ::= { snL4PolicyEntry 5 }

snL4PolicyRowStatus OBJECT-TYPE
    SYNTAX          INTEGER { invalid(1), valid(2), delete(3), create(4), 
                        modify(5) }
    ACCESS          read-write
    DESCRIPTION     
            "This object is used to create and
             delete row in the table and control
             if they are used. The values
             that can be written are:
             delete(3)...deletes the row
             create(4)...creates a new row
             modify(5)...modifies an exsisting row
             
             If the row exists, then a SET with
             value of create(4) returns error
             'badValue'. Deleted rows go away
             immediately. The following values
             can be returned on reads:
             invalid(1)...Setting it to 'invalid' has the effect of
                          rendering it inoperative.
             valid(2).....the row exists and is valid"
    ::= { snL4PolicyEntry 6 }

snL4PolicyPortAccess OBJECT IDENTIFIER
    ::= { snL4 12 }

snL4PolicyPortAccessTable OBJECT-TYPE
    SYNTAX          SEQUENCE OF SnL4PolicyPortAccessEntry
    ACCESS          not-accessible
    DESCRIPTION     
            "ip interface L4 policy access table."
    ::= { snL4PolicyPortAccess 1 }

snL4PolicyPortAccessEntry OBJECT-TYPE
    SYNTAX          SnL4PolicyPortAccessEntry
    ACCESS          not-accessible
    DESCRIPTION     
            "An entry of the ip interface L4 policy access  table."
    INDEX           { snL4PolicyPortAccessPort }
    ::= { snL4PolicyPortAccessTable 1 }

SnL4PolicyPortAccessEntry ::=
    SEQUENCE {
        snL4PolicyPortAccessPort        INTEGER,
        snL4PolicyPortAccessList        OCTET STRING,
        snL4PolicyPortAccessRowStatus   INTEGER
    }

snL4PolicyPortAccessPort OBJECT-TYPE
    SYNTAX          INTEGER
    ACCESS          read-only
    DESCRIPTION     
            "The ip interface to which the L4 policy  applies."
    ::= { snL4PolicyPortAccessEntry 1 }

snL4PolicyPortAccessList OBJECT-TYPE
    SYNTAX          OCTET STRING (SIZE(1..64))
    ACCESS          read-write
    DESCRIPTION     
            "An ip L4 policy  list, of which each octet contains
             a  ID number that forms a group of s. A
             valid entry in the snL4PolicyTable with the
             corresponding  ID number (i.e. snL4PolicyId)
             must have been created before a  list is initialized."
    ::= { snL4PolicyPortAccessEntry 2 }

snL4PolicyPortAccessRowStatus OBJECT-TYPE
    SYNTAX          INTEGER { invalid(1), valid(2), delete(3), create(4), 
                        modify(5) }
    ACCESS          read-write
    DESCRIPTION     
            "This object is used to create and
             delete row in the table and control
             if they are used. The values
             that can be written are:
             delete(3)...deletes the row
             create(4)...creates a new row
             modify(5)...modifies an exsisting row
             
             If the row exists, then a SET with
             value of create(4) returns error
             'badValue'. Deleted rows go away
             immediately. The following values
             can be returned on reads:
             invalid(1)...Setting it to 'invalid' has the effect of
                          rendering it inoperative.
             valid(2).....the row exists and is valid"
    ::= { snL4PolicyPortAccessEntry 3 }

snL4Trap OBJECT IDENTIFIER
    ::= { snL4 13 }

snL4TrapRealServerIP OBJECT-TYPE
    SYNTAX          IpAddress
    ACCESS          not-accessible
    DESCRIPTION     
            "Real server IP address."
    ::= { snL4Trap 1 }

snL4TrapRealServerName OBJECT-TYPE
    SYNTAX          L4ServerName
    ACCESS          not-accessible
    DESCRIPTION     
            "Real server name."
    ::= { snL4Trap 2 }

snL4TrapRealServerPort OBJECT-TYPE
    SYNTAX          INTEGER
    ACCESS          not-accessible
    DESCRIPTION     
            "Transport protocol port number of the real server."
    ::= { snL4Trap 3 }

snL4TrapRealServerCurConnections OBJECT-TYPE
    SYNTAX          INTEGER
    ACCESS          not-accessible
    DESCRIPTION     
            "Real Server current connections."
    ::= { snL4Trap 4 }

snL4WebCache OBJECT IDENTIFIER
    ::= { snL4 14 }

snL4WebCacheTable OBJECT-TYPE
    SYNTAX          SEQUENCE OF SnL4WebCacheEntry
    ACCESS          not-accessible
    DESCRIPTION     
            "Real Server table."
    ::= { snL4WebCache 1 }

snL4WebCacheEntry OBJECT-TYPE
    SYNTAX          SnL4WebCacheEntry
    ACCESS          not-accessible
    DESCRIPTION     
            "An entry in the Real Server table."
    INDEX           { snL4WebCacheIP }
    ::= { snL4WebCacheTable 1 }

SnL4WebCacheEntry ::=
    SEQUENCE {
        snL4WebCacheIP                  IpAddress,
        snL4WebCacheName                L4ServerName,
        snL4WebCacheAdminStatus         L4Status,
        snL4WebCacheMaxConnections      INTEGER,
        snL4WebCacheWeight              INTEGER,
        snL4WebCacheRowStatus           L4RowSts,
        snL4WebCacheDeleteState         L4DeleteState
    }

snL4WebCacheIP OBJECT-TYPE
    SYNTAX          IpAddress
    ACCESS          read-only
    DESCRIPTION     
            "Real Server IP Address."
    ::= { snL4WebCacheEntry 1 }

snL4WebCacheName OBJECT-TYPE
    SYNTAX          L4ServerName
    ACCESS          read-write
    DESCRIPTION     
            "Real server name."
    ::= { snL4WebCacheEntry 2 }

snL4WebCacheAdminStatus OBJECT-TYPE
    SYNTAX          L4Status
    ACCESS          read-write
    DESCRIPTION     
            "Real Server status is ether disabled(0) or enabled(1)."
    ::= { snL4WebCacheEntry 3 }

snL4WebCacheMaxConnections OBJECT-TYPE
    SYNTAX          INTEGER (0..1000000)
    ACCESS          read-write
    DESCRIPTION     
            "Real Server Maximum Connection allowed."
    ::= { snL4WebCacheEntry 4 }

snL4WebCacheWeight OBJECT-TYPE
    SYNTAX          INTEGER (1..20)
    ACCESS          read-write
    DESCRIPTION     
            "Real Server weight"
    ::= { snL4WebCacheEntry 5 }

snL4WebCacheRowStatus OBJECT-TYPE
    SYNTAX          L4RowSts
    ACCESS          read-write
    DESCRIPTION     
            "To create or delete a real server entry."
    ::= { snL4WebCacheEntry 6 }

snL4WebCacheDeleteState OBJECT-TYPE
    SYNTAX          L4DeleteState
    ACCESS          read-only
    DESCRIPTION     
            "Delete operation state."
    ::= { snL4WebCacheEntry 7 }

snL4WebCacheGroup OBJECT IDENTIFIER
    ::= { snL4 15 }

snL4WebCacheGroupTable OBJECT-TYPE
    SYNTAX          SEQUENCE OF SnL4WebCacheGroupEntry
    ACCESS          not-accessible
    DESCRIPTION     
            "Web Cache Group table."
    ::= { snL4WebCacheGroup 1 }

snL4WebCacheGroupEntry OBJECT-TYPE
    SYNTAX          SnL4WebCacheGroupEntry
    ACCESS          not-accessible
    DESCRIPTION     
            "An entry in the  Web Cache Group table."
    INDEX           { snL4WebCacheGroupId }
    ::= { snL4WebCacheGroupTable 1 }

SnL4WebCacheGroupEntry ::=
    SEQUENCE {
        snL4WebCacheGroupId             INTEGER,
        snL4WebCacheGroupName           L4ServerName,
        snL4WebCacheGroupWebCacheIpList OCTET STRING,
        snL4WebCacheGroupDestMask       IpAddress,
        snL4WebCacheGroupSrcMask        IpAddress,
        snL4WebCacheGroupAdminStatus    INTEGER,
        snL4WebCacheGroupRowStatus      L4RowSts
    }

snL4WebCacheGroupId OBJECT-TYPE
    SYNTAX          INTEGER
    ACCESS          read-only
    DESCRIPTION     
            "The identification for a Web Cache Group entry.
             The limit is from 1 to snL4MaxNumWebCacheGroup."
    ::= { snL4WebCacheGroupEntry 1 }

snL4WebCacheGroupName OBJECT-TYPE
    SYNTAX          L4ServerName
    ACCESS          read-write
    DESCRIPTION     
            "Web Cache Group name."
    ::= { snL4WebCacheGroupEntry 2 }

snL4WebCacheGroupWebCacheIpList OBJECT-TYPE
    SYNTAX          OCTET STRING
    ACCESS          read-write
    DESCRIPTION     
            "A list of the Server Cache Group Real Server IP Address.
             The number of IP Address is from 1 (4 OCTETs) to the 
             snL4MaxNumServersPerWebCacheGroup, maximum number of 
             server IP Address allowed in the list."
    ::= { snL4WebCacheGroupEntry 3 }

snL4WebCacheGroupDestMask OBJECT-TYPE
    SYNTAX          IpAddress
    ACCESS          read-write
    DESCRIPTION     
            "Cache Server Group Destination Mask."
    ::= { snL4WebCacheGroupEntry 4 }

snL4WebCacheGroupSrcMask OBJECT-TYPE
    SYNTAX          IpAddress
    ACCESS          read-write
    DESCRIPTION     
            "Cache Server Group Source Mask."
    ::= { snL4WebCacheGroupEntry 5 }

snL4WebCacheGroupAdminStatus OBJECT-TYPE
    SYNTAX          INTEGER { disabled(0), enabled(1) }
    ACCESS          read-write
    DESCRIPTION     
            "The WEB Cache Group is set either
             enabled(1)...........activated.
             disabled(0)..........disabled."
    ::= { snL4WebCacheGroupEntry 6 }

snL4WebCacheGroupRowStatus OBJECT-TYPE
    SYNTAX          L4RowSts
    ACCESS          read-write
    DESCRIPTION     
            "To create or delete a Web Cache Group entry."
    ::= { snL4WebCacheGroupEntry 7 }

snL4WebCacheTrafficStats OBJECT IDENTIFIER
    ::= { snL4 16 }

snL4WebCacheTrafficStatsTable OBJECT-TYPE
    SYNTAX          SEQUENCE OF SnL4WebCacheTrafficStatsEntry
    ACCESS          not-accessible
    DESCRIPTION     
            "Web Cache Traffic Statistics table."
    ::= { snL4WebCacheTrafficStats 1 }

snL4WebCacheTrafficStatsEntry OBJECT-TYPE
    SYNTAX          SnL4WebCacheTrafficStatsEntry
    ACCESS          not-accessible
    DESCRIPTION     
            "An entry in the Web Cache Traffic Statistics table."
    INDEX           { snL4WebCacheTrafficIp, snL4WebCacheTrafficPort }
    ::= { snL4WebCacheTrafficStatsTable 1 }

SnL4WebCacheTrafficStatsEntry ::=
    SEQUENCE {
        snL4WebCacheTrafficIp           IpAddress,
        snL4WebCacheTrafficPort         INTEGER,
        snL4WebCacheCurrConnections     INTEGER,
        snL4WebCacheTotalConnections    INTEGER,
        snL4WebCacheTxPkts              Counter,
        snL4WebCacheRxPkts              Counter,
        snL4WebCacheTxOctets            Counter,
        snL4WebCacheRxOctets            Counter,
        snL4WebCachePortState           WebCacheState
    }

snL4WebCacheTrafficIp OBJECT-TYPE
    SYNTAX          IpAddress
    ACCESS          read-only
    DESCRIPTION     
            "Cache Server IP Address."
    ::= { snL4WebCacheTrafficStatsEntry 1 }

snL4WebCacheTrafficPort OBJECT-TYPE
    SYNTAX          INTEGER (0..65535)
    ACCESS          read-only
    DESCRIPTION     
            "The WEB Cache port is one of the protocol port such as UDP, TCP etc."
    ::= { snL4WebCacheTrafficStatsEntry 2 }

snL4WebCacheCurrConnections OBJECT-TYPE
    SYNTAX          INTEGER
    ACCESS          read-only
    DESCRIPTION     
            "Number of the current connections in WEB Cache group."
    ::= { snL4WebCacheTrafficStatsEntry 3 }

snL4WebCacheTotalConnections OBJECT-TYPE
    SYNTAX          INTEGER
    ACCESS          read-only
    DESCRIPTION     
            "The total connections in WEB Cache group."
    ::= { snL4WebCacheTrafficStatsEntry 4 }

snL4WebCacheTxPkts OBJECT-TYPE
    SYNTAX          Counter
    ACCESS          read-only
    DESCRIPTION     
            "Number of the Packets sending from Client/Web-Server to Cache Server"
    ::= { snL4WebCacheTrafficStatsEntry 5 }

snL4WebCacheRxPkts OBJECT-TYPE
    SYNTAX          Counter
    ACCESS          read-only
    DESCRIPTION     
            "Number of the Packets sending from Cache Server to Client/Web-Server"
    ::= { snL4WebCacheTrafficStatsEntry 6 }

snL4WebCacheTxOctets OBJECT-TYPE
    SYNTAX          Counter
    ACCESS          read-only
    DESCRIPTION     
            "Number of the Octets sending from Client/Web-Server to Cache Server"
    ::= { snL4WebCacheTrafficStatsEntry 7 }

snL4WebCacheRxOctets OBJECT-TYPE
    SYNTAX          Counter
    ACCESS          read-only
    DESCRIPTION     
            "Number of the Octets sending from Cache Server to Client/Web-Server"
    ::= { snL4WebCacheTrafficStatsEntry 8 }

snL4WebCachePortState OBJECT-TYPE
    SYNTAX          WebCacheState
    ACCESS          read-only
    DESCRIPTION     
            "Web Cache Port state."
    ::= { snL4WebCacheTrafficStatsEntry 9 }

snL4WebUncachedTrafficStats OBJECT IDENTIFIER
    ::= { snL4 17 }

snL4WebUncachedTrafficStatsTable OBJECT-TYPE
    SYNTAX          SEQUENCE OF SnL4WebUncachedTrafficStatsEntry
    ACCESS          not-accessible
    DESCRIPTION     
            "Web Uncached Traffic Statistics table."
    ::= { snL4WebUncachedTrafficStats 1 }

snL4WebUncachedTrafficStatsEntry OBJECT-TYPE
    SYNTAX          SnL4WebUncachedTrafficStatsEntry
    ACCESS          not-accessible
    DESCRIPTION     
            "An entry in the Web Uncached Traffic Statistics table."
    INDEX           { snL4WebServerPort, snL4WebClientPort }
    ::= { snL4WebUncachedTrafficStatsTable 1 }

SnL4WebUncachedTrafficStatsEntry ::=
    SEQUENCE {
        snL4WebServerPort               INTEGER,
        snL4WebClientPort               INTEGER,
        snL4WebUncachedTxPkts           Counter,
        snL4WebUncachedRxPkts           Counter,
        snL4WebUncachedTxOctets         Counter,
        snL4WebUncachedRxOctets         Counter,
        snL4WebServerPortName           DisplayString,
        snL4WebClientPortName           DisplayString
    }

snL4WebServerPort OBJECT-TYPE
    SYNTAX          INTEGER
    ACCESS          read-only
    DESCRIPTION     
            "Web Server Port."
    ::= { snL4WebUncachedTrafficStatsEntry 1 }

snL4WebClientPort OBJECT-TYPE
    SYNTAX          INTEGER
    ACCESS          read-only
    DESCRIPTION     
            "Web Client Port."
    ::= { snL4WebUncachedTrafficStatsEntry 2 }

snL4WebUncachedTxPkts OBJECT-TYPE
    SYNTAX          Counter
    ACCESS          read-only
    DESCRIPTION     
            "Number of the Packets sending from Client port to Web Server port"
    ::= { snL4WebUncachedTrafficStatsEntry 3 }

snL4WebUncachedRxPkts OBJECT-TYPE
    SYNTAX          Counter
    ACCESS          read-only
    DESCRIPTION     
            "Number of the Packets sending from Web Server port to Client port"
    ::= { snL4WebUncachedTrafficStatsEntry 4 }

snL4WebUncachedTxOctets OBJECT-TYPE
    SYNTAX          Counter
    ACCESS          read-only
    DESCRIPTION     
            "Number of the Octets sending from Client port to Web Server port"
    ::= { snL4WebUncachedTrafficStatsEntry 5 }

snL4WebUncachedRxOctets OBJECT-TYPE
    SYNTAX          Counter
    ACCESS          read-only
    DESCRIPTION     
            "Number of the Octets sending from Web Server port to Client port"
    ::= { snL4WebUncachedTrafficStatsEntry 6 }

snL4WebServerPortName OBJECT-TYPE
    SYNTAX          DisplayString (SIZE(0..16))
    ACCESS          read-only
    DESCRIPTION     
            "Web Server Port Name string."
    ::= { snL4WebUncachedTrafficStatsEntry 7 }

snL4WebClientPortName OBJECT-TYPE
    SYNTAX          DisplayString (SIZE(0..16))
    ACCESS          read-only
    DESCRIPTION     
            "Web Client Port Name string."
    ::= { snL4WebUncachedTrafficStatsEntry 8 }

snL4WebCachePort OBJECT IDENTIFIER
    ::= { snL4 18 }

snL4WebCachePortTable OBJECT-TYPE
    SYNTAX          SEQUENCE OF SnL4WebCachePortEntry
    ACCESS          not-accessible
    DESCRIPTION     
            "Real Server Port table."
    ::= { snL4WebCachePort 1 }

snL4WebCachePortEntry OBJECT-TYPE
    SYNTAX          SnL4WebCachePortEntry
    ACCESS          not-accessible
    DESCRIPTION     
            "An entry in the Real Server Port table."
    INDEX           { snL4WebCachePortServerIp, snL4WebCachePortPort }
    ::= { snL4WebCachePortTable 1 }

SnL4WebCachePortEntry ::=
    SEQUENCE {
        snL4WebCachePortServerIp        IpAddress,
        snL4WebCachePortPort            INTEGER,
        snL4WebCachePortAdminStatus     L4Status,
        snL4WebCachePortRowStatus       L4RowSts,
        snL4WebCachePortDeleteState     L4DeleteState
    }

snL4WebCachePortServerIp OBJECT-TYPE
    SYNTAX          IpAddress
    ACCESS          read-only
    DESCRIPTION     
            "Cache Server IP Address."
    ::= { snL4WebCachePortEntry 1 }

snL4WebCachePortPort OBJECT-TYPE
    SYNTAX          INTEGER (0..65535)
    ACCESS          read-only
    DESCRIPTION     
            "The WEB Cache port is one of the protocol port such as UDP, TCP etc."
    ::= { snL4WebCachePortEntry 2 }

snL4WebCachePortAdminStatus OBJECT-TYPE
    SYNTAX          L4Status
    ACCESS          read-write
    DESCRIPTION     
            ""
    ::= { snL4WebCachePortEntry 3 }

snL4WebCachePortRowStatus OBJECT-TYPE
    SYNTAX          L4RowSts
    ACCESS          read-write
    DESCRIPTION     
            "To create or delete a Real server  port entry."
    ::= { snL4WebCachePortEntry 4 }

snL4WebCachePortDeleteState OBJECT-TYPE
    SYNTAX          L4DeleteState
    ACCESS          read-only
    DESCRIPTION     
            "Delete operation state."
    ::= { snL4WebCachePortEntry 5 }

snL4RealServerCfg OBJECT IDENTIFIER
    ::= { snL4 19 }

snL4RealServerCfgTable OBJECT-TYPE
    SYNTAX          SEQUENCE OF SnL4RealServerCfgEntry
    ACCESS          not-accessible
    DESCRIPTION     
            "Real Server table."
    ::= { snL4RealServerCfg 1 }

snL4RealServerCfgEntry OBJECT-TYPE
    SYNTAX          SnL4RealServerCfgEntry
    ACCESS          not-accessible
    DESCRIPTION     
            "An entry in the Real Server table."
    INDEX           { snL4RealServerCfgIP }
    ::= { snL4RealServerCfgTable 1 }

SnL4RealServerCfgEntry ::=
    SEQUENCE {
        snL4RealServerCfgIP             IpAddress,
        snL4RealServerCfgName           L4ServerName,
        snL4RealServerCfgAdminStatus    L4Status,
        snL4RealServerCfgMaxConnections INTEGER,
        snL4RealServerCfgWeight         INTEGER,
        snL4RealServerCfgRowStatus      L4RowSts,
        snL4RealServerCfgDeleteState    L4DeleteState
    }

snL4RealServerCfgIP OBJECT-TYPE
    SYNTAX          IpAddress
    ACCESS          read-only
    DESCRIPTION     
            "Real Server IP Address."
    ::= { snL4RealServerCfgEntry 1 }

snL4RealServerCfgName OBJECT-TYPE
    SYNTAX          L4ServerName
    ACCESS          read-write
    DESCRIPTION     
            "Real server name."
    ::= { snL4RealServerCfgEntry 2 }

snL4RealServerCfgAdminStatus OBJECT-TYPE
    SYNTAX          L4Status
    ACCESS          read-write
    DESCRIPTION     
            "Real Server status is ether disabled(0) or enabled(1)."
    ::= { snL4RealServerCfgEntry 3 }

snL4RealServerCfgMaxConnections OBJECT-TYPE
    SYNTAX          INTEGER (0..1000000)
    ACCESS          read-write
    DESCRIPTION     
            "Real Server Maximum Connection allowed."
    ::= { snL4RealServerCfgEntry 4 }

snL4RealServerCfgWeight OBJECT-TYPE
    SYNTAX          INTEGER (1..20)
    ACCESS          read-write
    DESCRIPTION     
            "Real Server weight"
    ::= { snL4RealServerCfgEntry 5 }

snL4RealServerCfgRowStatus OBJECT-TYPE
    SYNTAX          L4RowSts
    ACCESS          read-write
    DESCRIPTION     
            "To create or delete a real server entry."
    ::= { snL4RealServerCfgEntry 6 }

snL4RealServerCfgDeleteState OBJECT-TYPE
    SYNTAX          L4DeleteState
    ACCESS          read-only
    DESCRIPTION     
            "Delete operation state."
    ::= { snL4RealServerCfgEntry 7 }

snL4RealServerPortCfg OBJECT IDENTIFIER
    ::= { snL4 20 }

snL4RealServerPortCfgTable OBJECT-TYPE
    SYNTAX          SEQUENCE OF SnL4RealServerPortCfgEntry
    ACCESS          not-accessible
    DESCRIPTION     
            "Real Server Port table."
    ::= { snL4RealServerPortCfg 1 }

snL4RealServerPortCfgEntry OBJECT-TYPE
    SYNTAX          SnL4RealServerPortCfgEntry
    ACCESS          not-accessible
    DESCRIPTION     
            "An entry in the Real Server Port table."
    INDEX           { snL4RealServerPortCfgIP, snL4RealServerPortCfgPort }
    ::= { snL4RealServerPortCfgTable 1 }

SnL4RealServerPortCfgEntry ::=
    SEQUENCE {
        snL4RealServerPortCfgIP         IpAddress,
        snL4RealServerPortCfgServerName L4ServerName,
        snL4RealServerPortCfgPort       INTEGER,
        snL4RealServerPortCfgAdminStatus L4Status,
        snL4RealServerPortCfgRowStatus  L4RowSts,
        snL4RealServerPortCfgDeleteState L4DeleteState
    }

snL4RealServerPortCfgIP OBJECT-TYPE
    SYNTAX          IpAddress
    ACCESS          read-only
    DESCRIPTION     
            "The IP address for the Real Server ."
    ::= { snL4RealServerPortCfgEntry 1 }

snL4RealServerPortCfgServerName OBJECT-TYPE
    SYNTAX          L4ServerName
    ACCESS          read-only
    DESCRIPTION     
            ""
    ::= { snL4RealServerPortCfgEntry 2 }

snL4RealServerPortCfgPort OBJECT-TYPE
    SYNTAX          INTEGER (0..65535)
    ACCESS          read-only
    DESCRIPTION     
            ""
    ::= { snL4RealServerPortCfgEntry 3 }

snL4RealServerPortCfgAdminStatus OBJECT-TYPE
    SYNTAX          L4Status
    ACCESS          read-write
    DESCRIPTION     
            ""
    ::= { snL4RealServerPortCfgEntry 4 }

snL4RealServerPortCfgRowStatus OBJECT-TYPE
    SYNTAX          L4RowSts
    ACCESS          read-write
    DESCRIPTION     
            "To create or delete a Real server  port entry."
    ::= { snL4RealServerPortCfgEntry 5 }

snL4RealServerPortCfgDeleteState OBJECT-TYPE
    SYNTAX          L4DeleteState
    ACCESS          read-only
    DESCRIPTION     
            "Delete operation state."
    ::= { snL4RealServerPortCfgEntry 6 }

snL4VirtualServerCfg OBJECT IDENTIFIER
    ::= { snL4 21 }

snL4VirtualServerCfgTable OBJECT-TYPE
    SYNTAX          SEQUENCE OF SnL4VirtualServerCfgEntry
    ACCESS          not-accessible
    DESCRIPTION     
            "Virtual Server table."
    ::= { snL4VirtualServerCfg 1 }

snL4VirtualServerCfgEntry OBJECT-TYPE
    SYNTAX          SnL4VirtualServerCfgEntry
    ACCESS          not-accessible
    DESCRIPTION     
            "An entry in L4 Virtual Server table."
    INDEX           { snL4VirtualServerCfgVirtualIP }
    ::= { snL4VirtualServerCfgTable 1 }

SnL4VirtualServerCfgEntry ::=
    SEQUENCE {
        snL4VirtualServerCfgVirtualIP   IpAddress,
        snL4VirtualServerCfgName        L4ServerName,
        snL4VirtualServerCfgAdminStatus L4Status,
        snL4VirtualServerCfgSDAType     INTEGER,
        snL4VirtualServerCfgRowStatus   L4RowSts,
        snL4VirtualServerCfgDeleteState L4DeleteState
    }

snL4VirtualServerCfgVirtualIP OBJECT-TYPE
    SYNTAX          IpAddress
    ACCESS          read-only
    DESCRIPTION     
            "Virtual Server IP Address."
    ::= { snL4VirtualServerCfgEntry 1 }

snL4VirtualServerCfgName OBJECT-TYPE
    SYNTAX          L4ServerName
    ACCESS          read-write
    DESCRIPTION     
            "Virtual server name."
    ::= { snL4VirtualServerCfgEntry 2 }

snL4VirtualServerCfgAdminStatus OBJECT-TYPE
    SYNTAX          L4Status
    ACCESS          read-write
    DESCRIPTION     
            "Virtual Server status is ether disabled(0) or enabled(1)."
    ::= { snL4VirtualServerCfgEntry 3 }

snL4VirtualServerCfgSDAType OBJECT-TYPE
    SYNTAX          INTEGER { default(0), leastconnection(1), 
                        roundrobin(2), weighted(3) }
    ACCESS          read-write
    DESCRIPTION     
            "TCP/UDP Sessions Distribution Algorithms Type."
    ::= { snL4VirtualServerCfgEntry 4 }

snL4VirtualServerCfgRowStatus OBJECT-TYPE
    SYNTAX          L4RowSts
    ACCESS          read-write
    DESCRIPTION     
            "To create or delete a virtual server
             entry."
    ::= { snL4VirtualServerCfgEntry 5 }

snL4VirtualServerCfgDeleteState OBJECT-TYPE
    SYNTAX          L4DeleteState
    ACCESS          read-only
    DESCRIPTION     
            "Delete operation state."
    ::= { snL4VirtualServerCfgEntry 6 }

snL4VirtualServerPortCfg OBJECT IDENTIFIER
    ::= { snL4 22 }

snL4VirtualServerPortCfgTable OBJECT-TYPE
    SYNTAX          SEQUENCE OF SnL4VirtualServerPortCfgEntry
    ACCESS          not-accessible
    DESCRIPTION     
            "Virtual Server Port table."
    ::= { snL4VirtualServerPortCfg 1 }

snL4VirtualServerPortCfgEntry OBJECT-TYPE
    SYNTAX          SnL4VirtualServerPortCfgEntry
    ACCESS          not-accessible
    DESCRIPTION     
            "An entry in the Virtual Server Port table."
    INDEX           { snL4VirtualServerPortCfgIP, 
                      snL4VirtualServerPortCfgPort }
    ::= { snL4VirtualServerPortCfgTable 1 }

SnL4VirtualServerPortCfgEntry ::=
    SEQUENCE {
        snL4VirtualServerPortCfgIP      IpAddress,
        snL4VirtualServerPortCfgPort    INTEGER,
        snL4VirtualServerPortCfgServerName  L4ServerName,
        snL4VirtualServerPortCfgAdminStatus   L4Status,
        snL4VirtualServerPortCfgSticky  INTEGER,
        snL4VirtualServerPortCfgConcurrent  INTEGER,
        snL4VirtualServerPortCfgRowStatus L4RowSts,
        snL4VirtualServerPortCfgDeleteState   L4DeleteState
    }

snL4VirtualServerPortCfgIP OBJECT-TYPE
    SYNTAX          IpAddress
    ACCESS          read-only
    DESCRIPTION     
            "Virtual Server IP Address."
    ::= { snL4VirtualServerPortCfgEntry 1 }

snL4VirtualServerPortCfgPort OBJECT-TYPE
    SYNTAX          INTEGER (0..65535)
    ACCESS          read-only
    DESCRIPTION     
            ""
    ::= { snL4VirtualServerPortCfgEntry 2 }

snL4VirtualServerPortCfgServerName OBJECT-TYPE
    SYNTAX          L4ServerName
    ACCESS          read-only
    DESCRIPTION     
            ""
    ::= { snL4VirtualServerPortCfgEntry 3 }

snL4VirtualServerPortCfgAdminStatus OBJECT-TYPE
    SYNTAX          L4Status
    ACCESS          read-write
    DESCRIPTION     
            ""
    ::= { snL4VirtualServerPortCfgEntry 4 }

snL4VirtualServerPortCfgSticky OBJECT-TYPE
    SYNTAX          INTEGER { disabled(0), enabled(1) }
    ACCESS          read-write
    DESCRIPTION     
            ""
    ::= { snL4VirtualServerPortCfgEntry 5 }

snL4VirtualServerPortCfgConcurrent OBJECT-TYPE
    SYNTAX          INTEGER { disabled(0), enabled(1) }
    ACCESS          read-write
    DESCRIPTION     
            ""
    ::= { snL4VirtualServerPortCfgEntry 6 }

snL4VirtualServerPortCfgRowStatus OBJECT-TYPE
    SYNTAX          L4RowSts
    ACCESS          read-write
    DESCRIPTION     
            "To create or delete a virtual server  port entry."
    ::= { snL4VirtualServerPortCfgEntry 7 }

snL4VirtualServerPortCfgDeleteState OBJECT-TYPE
    SYNTAX          L4DeleteState
    ACCESS          read-only
    DESCRIPTION     
            "Delete operation state."
    ::= { snL4VirtualServerPortCfgEntry 8 }

snL4RealServerStatistic OBJECT IDENTIFIER
    ::= { snL4 23 }

snL4RealServerStatisticTable OBJECT-TYPE
    SYNTAX          SEQUENCE OF SnL4RealServerStatisticEntry
    ACCESS          not-accessible
    DESCRIPTION     
            "Real Server Statistic table."
    ::= { snL4RealServerStatistic 1 }

snL4RealServerStatisticEntry OBJECT-TYPE
    SYNTAX          SnL4RealServerStatisticEntry
    ACCESS          not-accessible
    DESCRIPTION     
            "An entry in the Real Server Statistic table."
    INDEX           { snL4RealServerStatisticRealIP }
    ::= { snL4RealServerStatisticTable 1 }

SnL4RealServerStatisticEntry ::=
    SEQUENCE {
        snL4RealServerStatisticRealIP   IpAddress,
        snL4RealServerStatisticName     L4ServerName,
        snL4RealServerStatisticReceivePkts  Counter,
        snL4RealServerStatisticTransmitPkts   Counter,
        snL4RealServerStatisticCurConnections     INTEGER,
        snL4RealServerStatisticTotalConnections       Counter,
        snL4RealServerStatisticAge      INTEGER,
        snL4RealServerStatisticState    INTEGER,
        snL4RealServerStatisticReassignments    INTEGER,
        snL4RealServerStatisticReassignmentLimit        INTEGER,
        snL4RealServerStatisticFailedPortExists       INTEGER,
        snL4RealServerStatisticFailTime INTEGER,
        snL4RealServerStatisticPeakConnections      INTEGER
    }

snL4RealServerStatisticRealIP OBJECT-TYPE
    SYNTAX          IpAddress
    ACCESS          read-only
    DESCRIPTION     
            ""
    ::= { snL4RealServerStatisticEntry 1 }

snL4RealServerStatisticName OBJECT-TYPE
    SYNTAX          L4ServerName
    ACCESS          read-only
    DESCRIPTION     
            ""
    ::= { snL4RealServerStatisticEntry 2 }

snL4RealServerStatisticReceivePkts OBJECT-TYPE
    SYNTAX          Counter
    ACCESS          read-only
    DESCRIPTION     
            ""
    ::= { snL4RealServerStatisticEntry 3 }

snL4RealServerStatisticTransmitPkts OBJECT-TYPE
    SYNTAX          Counter
    ACCESS          read-only
    DESCRIPTION     
            ""
    ::= { snL4RealServerStatisticEntry 4 }

snL4RealServerStatisticCurConnections OBJECT-TYPE
    SYNTAX          INTEGER
    ACCESS          read-only
    DESCRIPTION     
            ""
    ::= { snL4RealServerStatisticEntry 5 }

snL4RealServerStatisticTotalConnections OBJECT-TYPE
    SYNTAX          Counter
    ACCESS          read-only
    DESCRIPTION     
            ""
    ::= { snL4RealServerStatisticEntry 6 }

snL4RealServerStatisticAge OBJECT-TYPE
    SYNTAX          INTEGER
    ACCESS          read-only
    DESCRIPTION     
            ""
    ::= { snL4RealServerStatisticEntry 7 }

snL4RealServerStatisticState OBJECT-TYPE
    SYNTAX          INTEGER { serverdisabled(0), serverenabled(1), 
                        serverfailed(2), servertesting(3), 
                        serversuspect(4), servershutdown(5), 
                        serveractive(6) }
    ACCESS          read-only
    DESCRIPTION     
            ""
    ::= { snL4RealServerStatisticEntry 8 }

snL4RealServerStatisticReassignments OBJECT-TYPE
    SYNTAX          INTEGER
    ACCESS          read-only
    DESCRIPTION     
            ""
    ::= { snL4RealServerStatisticEntry 9 }

snL4RealServerStatisticReassignmentLimit OBJECT-TYPE
    SYNTAX          INTEGER
    ACCESS          read-only
    DESCRIPTION     
            ""
    ::= { snL4RealServerStatisticEntry 10 }

snL4RealServerStatisticFailedPortExists OBJECT-TYPE
    SYNTAX          INTEGER
    ACCESS          read-only
    DESCRIPTION     
            ""
    ::= { snL4RealServerStatisticEntry 11 }

snL4RealServerStatisticFailTime OBJECT-TYPE
    SYNTAX          INTEGER
    ACCESS          read-only
    DESCRIPTION     
            ""
    ::= { snL4RealServerStatisticEntry 12 }

snL4RealServerStatisticPeakConnections OBJECT-TYPE
    SYNTAX          INTEGER
    ACCESS          read-only
    DESCRIPTION     
            ""
    ::= { snL4RealServerStatisticEntry 13 }

snL4RealServerPortStatistic OBJECT IDENTIFIER
    ::= { snL4 24 }

snL4RealServerPortStatisticTable OBJECT-TYPE
    SYNTAX          SEQUENCE OF SnL4RealServerPortStatisticEntry
    ACCESS          not-accessible
    DESCRIPTION     
            "Real Server Port Statistic table."
    ::= { snL4RealServerPortStatistic 1 }

snL4RealServerPortStatisticEntry OBJECT-TYPE
    SYNTAX          SnL4RealServerPortStatisticEntry
    ACCESS          not-accessible
    DESCRIPTION     
            "An entry in the Real Server Port Statistic table."
    INDEX           { snL4RealServerPortStatisticIP, 
                      snL4RealServerPortStatisticPort }
    ::= { snL4RealServerPortStatisticTable 1 }

SnL4RealServerPortStatisticEntry ::=
    SEQUENCE {
        snL4RealServerPortStatisticIP   IpAddress,
        snL4RealServerPortStatisticPort INTEGER,
        snL4RealServerPortStatisticServerName     L4ServerName,
        snL4RealServerPortStatisticReassignCount        INTEGER,
        snL4RealServerPortStatisticState INTEGER,
        snL4RealServerPortStatisticFailTime   INTEGER,
        snL4RealServerPortStatisticCurrentConnection            INTEGER,
        snL4RealServerPortStatisticTotalConnection          Counter,
        snL4RealServerPortStatisticRxPkts Counter,
        snL4RealServerPortStatisticTxPkts Counter,
        snL4RealServerPortStatisticRxBytes  Counter,
        snL4RealServerPortStatisticTxBytes  Counter,
        snL4RealServerPortStatisticPeakConnection         INTEGER
    }

snL4RealServerPortStatisticIP OBJECT-TYPE
    SYNTAX          IpAddress
    ACCESS          read-only
    DESCRIPTION     
            "The index for Real Server Port Statistic entry."
    ::= { snL4RealServerPortStatisticEntry 1 }

snL4RealServerPortStatisticPort OBJECT-TYPE
    SYNTAX          INTEGER
    ACCESS          read-only
    DESCRIPTION     
            ""
    ::= { snL4RealServerPortStatisticEntry 2 }

snL4RealServerPortStatisticServerName OBJECT-TYPE
    SYNTAX          L4ServerName
    ACCESS          read-only
    DESCRIPTION     
            ""
    ::= { snL4RealServerPortStatisticEntry 3 }

snL4RealServerPortStatisticReassignCount OBJECT-TYPE
    SYNTAX          INTEGER
    ACCESS          read-only
    DESCRIPTION     
            ""
    ::= { snL4RealServerPortStatisticEntry 4 }

snL4RealServerPortStatisticState OBJECT-TYPE
    SYNTAX          INTEGER { disabled(0), enabled(1), failed(2), 
                        testing(3), suspect(4), shutdown(5), active(6) }
    ACCESS          read-only
    DESCRIPTION     
            "Real server port state"
    ::= { snL4RealServerPortStatisticEntry 5 }

snL4RealServerPortStatisticFailTime OBJECT-TYPE
    SYNTAX          INTEGER
    ACCESS          read-only
    DESCRIPTION     
            "Only useful, if real server port state is failed.
             Indicating how seconds has been elapsed from the last retry."
    ::= { snL4RealServerPortStatisticEntry 6 }

snL4RealServerPortStatisticCurrentConnection OBJECT-TYPE
    SYNTAX          INTEGER
    ACCESS          read-only
    DESCRIPTION     
            "Real server port current connection"
    ::= { snL4RealServerPortStatisticEntry 7 }

snL4RealServerPortStatisticTotalConnection OBJECT-TYPE
    SYNTAX          Counter
    ACCESS          read-only
    DESCRIPTION     
            "Real server port total connection"
    ::= { snL4RealServerPortStatisticEntry 8 }

snL4RealServerPortStatisticRxPkts OBJECT-TYPE
    SYNTAX          Counter
    ACCESS          read-only
    DESCRIPTION     
            "Real server port receive packets."
    ::= { snL4RealServerPortStatisticEntry 9 }

snL4RealServerPortStatisticTxPkts OBJECT-TYPE
    SYNTAX          Counter
    ACCESS          read-only
    DESCRIPTION     
            "Real server port transmit packets."
    ::= { snL4RealServerPortStatisticEntry 10 }

snL4RealServerPortStatisticRxBytes OBJECT-TYPE
    SYNTAX          Counter
    ACCESS          read-only
    DESCRIPTION     
            "Real server port receive bytes."
    ::= { snL4RealServerPortStatisticEntry 11 }

snL4RealServerPortStatisticTxBytes OBJECT-TYPE
    SYNTAX          Counter
    ACCESS          read-only
    DESCRIPTION     
            "Real server port transmit bytes."
    ::= { snL4RealServerPortStatisticEntry 12 }

snL4RealServerPortStatisticPeakConnection OBJECT-TYPE
    SYNTAX          INTEGER
    ACCESS          read-only
    DESCRIPTION     
            "peak connection for real server port."
    ::= { snL4RealServerPortStatisticEntry 13 }

snL4VirtualServerStatistic OBJECT IDENTIFIER
    ::= { snL4 25 }

snL4VirtualServerStatisticTable OBJECT-TYPE
    SYNTAX          SEQUENCE OF SnL4VirtualServerStatisticEntry
    ACCESS          not-accessible
    DESCRIPTION     
            "Virtual Server Statistic table."
    ::= { snL4VirtualServerStatistic 1 }

snL4VirtualServerStatisticEntry OBJECT-TYPE
    SYNTAX          SnL4VirtualServerStatisticEntry
    ACCESS          not-accessible
    DESCRIPTION     
            "An entry in L4 Virtual Server Statistic table."
    INDEX           { snL4VirtualServerStatisticIP }
    ::= { snL4VirtualServerStatisticTable 1 }

SnL4VirtualServerStatisticEntry ::=
    SEQUENCE {
        snL4VirtualServerStatisticIP    IpAddress,
        snL4VirtualServerStatisticName  L4ServerName,
        snL4VirtualServerStatisticReceivePkts     Counter,
        snL4VirtualServerStatisticTransmitPkts      Counter,
        snL4VirtualServerStatisticTotalConnections          Counter
--         snL4VirtualServerStatisticReceiveBytes      Counter64,
--         snL4VirtualServerStatisticTransmitBytes       Counter64
    }

snL4VirtualServerStatisticIP OBJECT-TYPE
    SYNTAX          IpAddress
    ACCESS          read-only
    DESCRIPTION     
            "The table index for a Virtual Server  Statistic entry."
    ::= { snL4VirtualServerStatisticEntry 1 }

snL4VirtualServerStatisticName OBJECT-TYPE
    SYNTAX          L4ServerName
    ACCESS          read-only
    DESCRIPTION     
            "Virtual server name."
    ::= { snL4VirtualServerStatisticEntry 2 }

snL4VirtualServerStatisticReceivePkts OBJECT-TYPE
    SYNTAX          Counter
    ACCESS          read-only
    DESCRIPTION     
            ""
    ::= { snL4VirtualServerStatisticEntry 3 }

snL4VirtualServerStatisticTransmitPkts OBJECT-TYPE
    SYNTAX          Counter
    ACCESS          read-only
    DESCRIPTION     
            ""
    ::= { snL4VirtualServerStatisticEntry 4 }

snL4VirtualServerStatisticTotalConnections OBJECT-TYPE
    SYNTAX          Counter
    ACCESS          read-only
    DESCRIPTION     
            ""
    ::= { snL4VirtualServerStatisticEntry 5 }

-- snL4VirtualServerStatisticReceiveBytes OBJECT-TYPE
--     SYNTAX          Counter64
--     ACCESS          read-only
--     DESCRIPTION     
--             ""
--     ::= { snL4VirtualServerStatisticEntry 6 }

-- snL4VirtualServerStatisticTransmitBytes OBJECT-TYPE
--     SYNTAX          Counter64
--     ACCESS          read-only
--     DESCRIPTION     
--             ""
--     ::= { snL4VirtualServerStatisticEntry 7 }

snL4VirtualServerPortStatistic OBJECT IDENTIFIER
    ::= { snL4 26 }

snL4VirtualServerPortStatisticTable OBJECT-TYPE
    SYNTAX          SEQUENCE OF SnL4VirtualServerPortStatisticEntry
    ACCESS          not-accessible
    DESCRIPTION     
            "Virtual Server Port Statistic table."
    ::= { snL4VirtualServerPortStatistic 1 }

snL4VirtualServerPortStatisticEntry OBJECT-TYPE
    SYNTAX          SnL4VirtualServerPortStatisticEntry
    ACCESS          not-accessible
    DESCRIPTION     
            "An entry in the Virtual Server Port Statistic table."
    INDEX           { snL4VirtualServerPortStatisticIP, 
                      snL4VirtualServerPortStatisticPort }
    ::= { snL4VirtualServerPortStatisticTable 1 }

SnL4VirtualServerPortStatisticEntry ::=
    SEQUENCE {
        snL4VirtualServerPortStatisticIP IpAddress,
        snL4VirtualServerPortStatisticPort  INTEGER,
        snL4VirtualServerPortStatisticServerName        L4ServerName,
        snL4VirtualServerPortStatisticCurrentConnection               INTEGER,
        snL4VirtualServerPortStatisticTotalConnection             Counter,
        snL4VirtualServerPortStatisticPeakConnection            INTEGER
    }

snL4VirtualServerPortStatisticIP OBJECT-TYPE
    SYNTAX          IpAddress
    ACCESS          read-only
    DESCRIPTION     
            "The index for Virtual Server Port Statistic entry."
    ::= { snL4VirtualServerPortStatisticEntry 1 }

snL4VirtualServerPortStatisticPort OBJECT-TYPE
    SYNTAX          INTEGER (1..2048)
    ACCESS          read-only
    DESCRIPTION     
            ""
    ::= { snL4VirtualServerPortStatisticEntry 2 }

snL4VirtualServerPortStatisticServerName OBJECT-TYPE
    SYNTAX          L4ServerName
    ACCESS          read-only
    DESCRIPTION     
            ""
    ::= { snL4VirtualServerPortStatisticEntry 3 }

snL4VirtualServerPortStatisticCurrentConnection OBJECT-TYPE
    SYNTAX          INTEGER
    ACCESS          read-only
    DESCRIPTION     
            ""
    ::= { snL4VirtualServerPortStatisticEntry 4 }

snL4VirtualServerPortStatisticTotalConnection OBJECT-TYPE
    SYNTAX          Counter
    ACCESS          read-only
    DESCRIPTION     
            ""
    ::= { snL4VirtualServerPortStatisticEntry 5 }

snL4VirtualServerPortStatisticPeakConnection OBJECT-TYPE
    SYNTAX          INTEGER
    ACCESS          read-only
    DESCRIPTION     
            ""
    ::= { snL4VirtualServerPortStatisticEntry 6 }

snL4GslbSiteRemoteServerIrons OBJECT IDENTIFIER
    ::= { snL4 27 }

snL4GslbSiteRemoteServerIronTable OBJECT-TYPE
    SYNTAX          SEQUENCE OF SnL4GslbSiteRemoteServerIronEntry
    ACCESS          not-accessible
    DESCRIPTION     
            "GSLB remote ServerIron configuration table."
    ::= { snL4GslbSiteRemoteServerIrons 1 }

snL4GslbSiteRemoteServerIronEntry OBJECT-TYPE
    SYNTAX          SnL4GslbSiteRemoteServerIronEntry
    ACCESS          not-accessible
    DESCRIPTION     
            "An entry of a GSLB remote ServerIron configuration."
    INDEX           { snL4GslbSiteRemoteServerIronIP }
    ::= { snL4GslbSiteRemoteServerIronTable 1 }

SnL4GslbSiteRemoteServerIronEntry ::=
    SEQUENCE {
        snL4GslbSiteRemoteServerIronIP  IpAddress,
        snL4GslbSiteRemoteServerIronPreference      INTEGER
    }

snL4GslbSiteRemoteServerIronIP OBJECT-TYPE
    SYNTAX          IpAddress
    ACCESS          read-only
    DESCRIPTION     
            "The index for each remote ServerIron in a site."
    ::= { snL4GslbSiteRemoteServerIronEntry 1 }

snL4GslbSiteRemoteServerIronPreference OBJECT-TYPE
    SYNTAX          INTEGER (0..255)
    ACCESS          read-write
    DESCRIPTION     
            "The preference of a remote ServerIron. The default value is 128."
    DEFVAL          { 128 }
    ::= { snL4GslbSiteRemoteServerIronEntry 2 }

END -- end of module FOUNDRY-SN-SW-L4-SWITCH-GROUP-MIB.
