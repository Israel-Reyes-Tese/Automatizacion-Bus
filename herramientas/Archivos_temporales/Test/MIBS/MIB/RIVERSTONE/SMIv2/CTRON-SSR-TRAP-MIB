--
-- This SMIv2 module has been generated by smidump 0.2-cvs. Do not edit.
--

CTRON-SSR-TRAP-MIB DEFINITIONS ::= BEGIN

IMPORTS
    sysHwFan, sysHwModuleSlotNumber, sysHwPowerSupply, sysHwTemperature
        FROM CTRON-SSR-HARDWARE-MIB
    ssrMibs, ssrTraps
        FROM CTRON-SSR-SMI-MIB
    MODULE-COMPLIANCE, NOTIFICATION-GROUP
        FROM SNMPv2-CONF
    MODULE-IDENTITY, NOTIFICATION-TYPE
        FROM SNMPv2-SMI;

ssrTrapsMIB MODULE-IDENTITY
    LAST-UPDATED    "197001010000Z"
    ORGANIZATION    
            "Cabletron Systems, Inc."
    CONTACT-INFO    
            "Cabletron Systems, Inc.
             35 Industrial Way, P.O. Box 5005
             Rochester, NH 03867-0505
             (603) 332-9400
             support@ctron.com
             http://www.ctron.com"
    DESCRIPTION     
            "This module describes the traps specific to the Smart Switch Router."
    ::= { ssrMibs 300 }


ssrTrapsConformance OBJECT IDENTIFIER
    ::= { ssrTrapsMIB 2 }

ssrTrapsCompliances OBJECT IDENTIFIER
    ::= { ssrTrapsConformance 1 }

ssrTrapsGroups OBJECT IDENTIFIER
    ::= { ssrTrapsConformance 2 }

trapControl OBJECT IDENTIFIER
    ::= { ssrTraps 1 }

envTrapGroup OBJECT IDENTIFIER
    ::= { ssrTraps 2 }

envPowerSupplyFailed NOTIFICATION-TYPE
    OBJECTS         { sysHwPowerSupply }
    STATUS          current
    DESCRIPTION     
            "A power supply on the sending device has failed. The 
             sysHwPowerSupply object identifies the failed supply."
    ::= { envTrapGroup 1 }

envPowerSupplyRecovered NOTIFICATION-TYPE
    OBJECTS         { sysHwPowerSupply }
    STATUS          current
    DESCRIPTION     
            "A power supply on the sending device has recovered 
             after failure. The sysHwPowerSupply object identifies 
             the recovered supply."
    ::= { envTrapGroup 2 }

envFanFailed NOTIFICATION-TYPE
    OBJECTS         { sysHwFan }
    STATUS          current
    DESCRIPTION     
            "A Fan tray on the sending device has failed. The
             sysHwFan object identifies the failed fan tray."
    ::= { envTrapGroup 3 }

envFanRecovered NOTIFICATION-TYPE
    OBJECTS         { sysHwFan }
    STATUS          current
    DESCRIPTION     
            "A Fan tray on the sending device has recovered
             after failure. The sysHwFan object identifies
             the recovered Fan tray."
    ::= { envTrapGroup 4 }

envTempExceeded NOTIFICATION-TYPE
    OBJECTS         { sysHwTemperature }
    STATUS          current
    DESCRIPTION     
            "A temperature inside the chassis on the sending device has exceeded
             normal operating temperature. The sysHwTemperature object
             identifies the current status."
    ::= { envTrapGroup 5 }

envTempNormal NOTIFICATION-TYPE
    OBJECTS         { sysHwTemperature }
    STATUS          current
    DESCRIPTION     
            "A temperature inside the chassis on the sending device has returned
             to normal operating temperature. The sysHwTemperature
             object identifies the current status."
    ::= { envTrapGroup 6 }

envHotSwapIn NOTIFICATION-TYPE
    OBJECTS         { sysHwModuleSlotNumber }
    STATUS          current
    DESCRIPTION     
            "A module has been inserted into the chassis.
             sysHwModuleSlotNumber identifies the slot the module was inserted into."
    ::= { envTrapGroup 7 }

envHotSwapOut NOTIFICATION-TYPE
    OBJECTS         { sysHwModuleSlotNumber }
    STATUS          current
    DESCRIPTION     
            "A module has been turned off or removed from the chassis.
             sysHwModuleSlotNumber identifies the slot the module was removed from."
    ::= { envTrapGroup 8 }

ssrTrapsConfGroupV10 NOTIFICATION-GROUP
    NOTIFICATIONS   { envPowerSupplyFailed, envPowerSupplyRecovered }
    STATUS          obsolete
    DESCRIPTION     
            "A set of managed objects that make up version 1.0 of the SSR Trap mib."
    ::= { ssrTrapsGroups 1 }

ssrTrapsConfGroupV20 NOTIFICATION-GROUP
    NOTIFICATIONS   { envPowerSupplyFailed, envPowerSupplyRecovered, 
                      envFanFailed, envFanRecovered, envTempExceeded, 
                      envTempNormal }
    STATUS          deprecated
    DESCRIPTION     
            "A set of managed objects that make up version 2.0 of the SSR Trap mib."
    ::= { ssrTrapsGroups 2 }

ssrTrapsConfGroupV30 NOTIFICATION-GROUP
    NOTIFICATIONS   { envPowerSupplyFailed, envPowerSupplyRecovered, 
                      envFanFailed, envFanRecovered, envTempExceeded, 
                      envTempNormal, envHotSwapIn, envHotSwapOut }
    STATUS          current
    DESCRIPTION     
            "A set of managed objects that make up version 3.0 of the SSR Trap mib."
    ::= { ssrTrapsGroups 3 }

ssrTrapsComplianceV10 MODULE-COMPLIANCE
    STATUS          obsolete
    DESCRIPTION     
            "The compliance statement for the CTRON-SSR-TRAPS-MIB."

    MODULE          -- this module

        MANDATORY-GROUPS    { ssrTrapsConfGroupV10 }

    ::= { ssrTrapsConfGroupV10 1 }

ssrTrapsComplianceV20 MODULE-COMPLIANCE
    STATUS          deprecated
    DESCRIPTION     
            "The compliance statement for the CTRON-SSR-TRAPS-MIB."

    MODULE          -- this module

        MANDATORY-GROUPS    { ssrTrapsConfGroupV20 }

    ::= { ssrTrapsConfGroupV20 1 }

ssrTrapsComplianceV30 MODULE-COMPLIANCE
    STATUS          current
    DESCRIPTION     
            "The compliance statement for the CTRON-SSR-TRAPS-MIB."

    MODULE          -- this module

        MANDATORY-GROUPS    { ssrTrapsConfGroupV30 }

    ::= { ssrTrapsConfGroupV30 1 }

END -- end of module CTRON-SSR-TRAP-MIB.
