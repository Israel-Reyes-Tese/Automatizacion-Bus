--
-- This SMIv1 module has been generated by smidump 0.2-cvs. Do not edit.
--

SONUS-PATHCHECK-MIB DEFINITIONS ::= BEGIN

IMPORTS
    Ipv6Address
        FROM IPV6-TC
    OBJECT-TYPE
        FROM RFC-1212
    IpAddress
        FROM RFC1155-SMI
    RowStatus
        FROM SNMPv2-TC
    sonusEventClass, sonusEventDescription, sonusEventLevel, 
    sonusEventTime, sonusSequenceId, sonusShelfIndex, sonusSlotIndex
        FROM SONUS-COMMON-MIB
    sonusServicesMIBs
        FROM SONUS-SMI
    SonusAdminState, SonusName, SonusNameReference
        FROM SONUS-TC;

sonusPathcheckMIB OBJECT IDENTIFIER
    ::= { sonusServicesMIBs 32 }

-- sonusPathcheckMIB MODULE-IDENTITY
--     LAST-UPDATED    "201110050000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for PATHCHECK Management."
--     ::= { sonusServicesMIBs 32 }


sonusPathcheckMIBObjects OBJECT IDENTIFIER
    ::= { sonusPathcheckMIB 1 }

sonusPingPath OBJECT IDENTIFIER
    ::= { sonusPathcheckMIBObjects 1 }

sonusPingPathNextIndex OBJECT-TYPE
    SYNTAX          INTEGER
    ACCESS          read-only
    STATUS          mandatory
    DESCRIPTION     
            "The next valid index to use when creating an entry in
             the sonusPingPathTable."
    ::= { sonusPingPath 1 }

sonusPingPathTable OBJECT-TYPE
    SYNTAX          SEQUENCE OF SonusPingPathEntry
    ACCESS          not-accessible
    STATUS          mandatory
    DESCRIPTION     
            "This table contains PATHCHECK PATH for the node."
    ::= { sonusPingPath 2 }

sonusPingPathEntry OBJECT-TYPE
    SYNTAX          SonusPingPathEntry
    ACCESS          not-accessible
    STATUS          mandatory
    DESCRIPTION     
            ""
    INDEX           { sonusPingPathIndex }
    ::= { sonusPingPathTable 1 }

SonusPingPathEntry ::=
    SEQUENCE {
        sonusPingPathIndex              INTEGER,
        sonusPingPathState              INTEGER,
        sonusPingPathName               SonusName,
        sonusPingPathSourceIpAddress    IpAddress,
        sonusPingPathTargetIpAddress    IpAddress,
        sonusPingPathNifIndex           INTEGER,
        sonusPingPathSifIndex           INTEGER,
        sonusPingPathPingProfileIndex   INTEGER,
        sonusPingPathReportSignalAddress IpAddress,
        sonusPingPathZoneName           SonusNameReference,
        sonusPingPathRowStatus          RowStatus,
        sonusPingPathOperState          INTEGER,
        sonusPingPathSourceIpv6Address  Ipv6Address,
        sonusPingPathTargetIpv6Address  Ipv6Address,
        sonusPingPathReportSignalIpv6Address    Ipv6Address,
        sonusPingPathSourceIpVersion    INTEGER,
        sonusPingPathTargetIpVersion    INTEGER,
        sonusPingPathRemoteIpVersion    INTEGER,
        sonusPingPathTargetPort         INTEGER,
        sonusPingPathErrorResponseBehavior  SonusAdminState
    }

sonusPingPathIndex OBJECT-TYPE
    SYNTAX          INTEGER
    ACCESS          read-only
    STATUS          mandatory
    DESCRIPTION     
            "Identifies the Ping Path entry."
    ::= { sonusPingPathEntry 1 }

sonusPingPathState OBJECT-TYPE
    SYNTAX          INTEGER { disabled(1), enabled(2) }
    ACCESS          read-write
    STATUS          mandatory
    DESCRIPTION     
            "The administrative state of this path entry."
    DEFVAL          { disabled }
    ::= { sonusPingPathEntry 2 }

sonusPingPathName OBJECT-TYPE
    SYNTAX          SonusName
    ACCESS          read-write
    STATUS          mandatory
    DESCRIPTION     
            "The user name of this Ping Path."
    ::= { sonusPingPathEntry 3 }

sonusPingPathSourceIpAddress OBJECT-TYPE
    SYNTAX          IpAddress
    ACCESS          read-write
    STATUS          mandatory
    DESCRIPTION     
            "IPv4 Address of the ping source address - optional parameter"
    ::= { sonusPingPathEntry 4 }

sonusPingPathTargetIpAddress OBJECT-TYPE
    SYNTAX          IpAddress
    ACCESS          read-write
    STATUS          mandatory
    DESCRIPTION     
            "IPv4 Address of the remote ping address - mandatory parameter"
    ::= { sonusPingPathEntry 5 }

sonusPingPathNifIndex OBJECT-TYPE
    SYNTAX          INTEGER
    ACCESS          read-write
    STATUS          mandatory
    DESCRIPTION     
            "The network interface index."
    ::= { sonusPingPathEntry 6 }

sonusPingPathSifIndex OBJECT-TYPE
    SYNTAX          INTEGER
    ACCESS          read-write
    STATUS          mandatory
    DESCRIPTION     
            "The sub-network interface index."
    ::= { sonusPingPathEntry 7 }

sonusPingPathPingProfileIndex OBJECT-TYPE
    SYNTAX          INTEGER
    ACCESS          read-write
    STATUS          mandatory
    DESCRIPTION     
            "The ping profile's index."
    ::= { sonusPingPathEntry 8 }

sonusPingPathReportSignalAddress OBJECT-TYPE
    SYNTAX          IpAddress
    ACCESS          read-write
    STATUS          mandatory
    DESCRIPTION     
            "IPv4 Address of the reporting remote signaling address"
    ::= { sonusPingPathEntry 9 }

sonusPingPathZoneName OBJECT-TYPE
    SYNTAX          SonusNameReference
    ACCESS          read-write
    STATUS          mandatory
    DESCRIPTION     
            "The Signaling Zone that this reporting SIP signaling port belongs to."
    ::= { sonusPingPathEntry 10 }

sonusPingPathRowStatus OBJECT-TYPE
    SYNTAX          RowStatus
    ACCESS          read-write
    STATUS          mandatory
    DESCRIPTION     
            ""
    ::= { sonusPingPathEntry 11 }

sonusPingPathOperState OBJECT-TYPE
    SYNTAX          INTEGER { inactive(1), active(2), down(3), up(4) }
    ACCESS          read-only
    STATUS          mandatory
    DESCRIPTION     
            "Operational state of the ping path."
    DEFVAL          { inactive }
    ::= { sonusPingPathEntry 12 }

sonusPingPathSourceIpv6Address OBJECT-TYPE
    SYNTAX          Ipv6Address
    ACCESS          read-write
    STATUS          mandatory
    DESCRIPTION     
            "IPv6 Address of the ping source address - optional parameter"
    ::= { sonusPingPathEntry 13 }

sonusPingPathTargetIpv6Address OBJECT-TYPE
    SYNTAX          Ipv6Address
    ACCESS          read-write
    STATUS          mandatory
    DESCRIPTION     
            "IPv6 Address of the remote ping address - mandatory parameter"
    ::= { sonusPingPathEntry 14 }

sonusPingPathReportSignalIpv6Address OBJECT-TYPE
    SYNTAX          Ipv6Address
    ACCESS          read-write
    STATUS          mandatory
    DESCRIPTION     
            "IPv6 Address of the reporting remote signaling address"
    ::= { sonusPingPathEntry 15 }

sonusPingPathSourceIpVersion OBJECT-TYPE
    SYNTAX          INTEGER { afInet(2), afInet6(24) }
    ACCESS          read-only
    STATUS          mandatory
    DESCRIPTION     
            "IP Address Type"
    ::= { sonusPingPathEntry 16 }

sonusPingPathTargetIpVersion OBJECT-TYPE
    SYNTAX          INTEGER { afInet(2), afInet6(24) }
    ACCESS          read-only
    STATUS          mandatory
    DESCRIPTION     
            "IP Address Type"
    ::= { sonusPingPathEntry 17 }

sonusPingPathRemoteIpVersion OBJECT-TYPE
    SYNTAX          INTEGER { afInet(2), afInet6(24) }
    ACCESS          read-only
    STATUS          mandatory
    DESCRIPTION     
            "IP Address Type"
    ::= { sonusPingPathEntry 18 }

sonusPingPathTargetPort OBJECT-TYPE
    SYNTAX          INTEGER (1..65535)
    ACCESS          read-write
    STATUS          mandatory
    DESCRIPTION     
            "Destination endpoint's UDP port number."
    ::= { sonusPingPathEntry 19 }

sonusPingPathErrorResponseBehavior OBJECT-TYPE
    SYNTAX          SonusAdminState
    ACCESS          read-write
    STATUS          mandatory
    DESCRIPTION     
            "Error response handling for OPTIONS request"
    DEFVAL          { disabled }
    ::= { sonusPingPathEntry 20 }

sonusPingProfile OBJECT IDENTIFIER
    ::= { sonusPathcheckMIBObjects 2 }

sonusPingProfileNextIndex OBJECT-TYPE
    SYNTAX          INTEGER
    ACCESS          read-only
    STATUS          mandatory
    DESCRIPTION     
            "The next valid index to use when creating an entry in
             the sonusPingProfileTable."
    ::= { sonusPingProfile 1 }

sonusPingProfileTable OBJECT-TYPE
    SYNTAX          SEQUENCE OF SonusPingProfileEntry
    ACCESS          not-accessible
    STATUS          mandatory
    DESCRIPTION     
            "This table contains ping profiles for the node."
    ::= { sonusPingProfile 2 }

sonusPingProfileEntry OBJECT-TYPE
    SYNTAX          SonusPingProfileEntry
    ACCESS          not-accessible
    STATUS          mandatory
    DESCRIPTION     
            ""
    INDEX           { sonusPingProfileIndex }
    ::= { sonusPingProfileTable 1 }

SonusPingProfileEntry ::=
    SEQUENCE {
        sonusPingProfileIndex           INTEGER,
        sonusPingProfileState           INTEGER,
        sonusPingProfileName            SonusName,
        sonusPingProfileProtocol        INTEGER,
        sonusPingProfileSendInterval    Gauge,
        sonusPingProfileReplyTimeout    Gauge,
        sonusPingProfileVerifyInterval  Gauge,
        sonusPingProfileTimeoutNumber   Gauge,
        sonusPingProfileRecoveryNumber  Gauge,
        sonusPingProfileRowStatus       RowStatus
    }

sonusPingProfileIndex OBJECT-TYPE
    SYNTAX          INTEGER
    ACCESS          read-only
    STATUS          mandatory
    DESCRIPTION     
            "Identifies the ping profile entry."
    ::= { sonusPingProfileEntry 1 }

sonusPingProfileState OBJECT-TYPE
    SYNTAX          INTEGER { disabled(1), enabled(2) }
    ACCESS          read-write
    STATUS          mandatory
    DESCRIPTION     
            "The administrative state of this ping profile entry."
    DEFVAL          { disabled }
    ::= { sonusPingProfileEntry 2 }

sonusPingProfileName OBJECT-TYPE
    SYNTAX          SonusName
    ACCESS          read-write
    STATUS          mandatory
    DESCRIPTION     
            "The user name of this ping profile."
    ::= { sonusPingProfileEntry 3 }

sonusPingProfileProtocol OBJECT-TYPE
    SYNTAX          INTEGER { icmp(1), bfd(2), sipOpt(3) }
    ACCESS          read-write
    STATUS          mandatory
    DESCRIPTION     
            "Specifies ping protocol type used"
    DEFVAL          { icmp }
    ::= { sonusPingProfileEntry 4 }

sonusPingProfileSendInterval OBJECT-TYPE
    SYNTAX          Gauge (500..3600000)
    ACCESS          read-write
    STATUS          mandatory
    DESCRIPTION     
            "Specifies ping packet sending interval"
    DEFVAL          { 1010 }
    ::= { sonusPingProfileEntry 5 }

sonusPingProfileReplyTimeout OBJECT-TYPE
    SYNTAX          Gauge (0..10000)
    ACCESS          read-write
    STATUS          mandatory
    DESCRIPTION     
            "ping echo packet reply timeout to "
    DEFVAL          { 1000 }
    ::= { sonusPingProfileEntry 6 }

sonusPingProfileVerifyInterval OBJECT-TYPE
    SYNTAX          Gauge (0..10000)
    ACCESS          read-write
    STATUS          mandatory
    DESCRIPTION     
            "Ping verification interval period used to determine the status of ping session"
    DEFVAL          { 6000 }
    ::= { sonusPingProfileEntry 7 }

sonusPingProfileTimeoutNumber OBJECT-TYPE
    SYNTAX          Gauge (1..32)
    ACCESS          read-write
    STATUS          mandatory
    DESCRIPTION     
            "The number of ping reply timeout in a verification interval period for a ping session"
    DEFVAL          { 6 }
    ::= { sonusPingProfileEntry 8 }

sonusPingProfileRecoveryNumber OBJECT-TYPE
    SYNTAX          Gauge (1..32)
    ACCESS          read-write
    STATUS          mandatory
    DESCRIPTION     
            "The number of consecutive responses recieved for a ping session"
    DEFVAL          { 3 }
    ::= { sonusPingProfileEntry 9 }

sonusPingProfileRowStatus OBJECT-TYPE
    SYNTAX          RowStatus
    ACCESS          read-write
    STATUS          mandatory
    DESCRIPTION     
            ""
    ::= { sonusPingProfileEntry 10 }

END -- end of module SONUS-PATHCHECK-MIB.
