--
-- This SMIv1 module has been generated by smidump 0.2-cvs. Do not edit.
--

SNMP-RESEARCH-MIB DEFINITIONS ::= BEGIN

IMPORTS
    enterprises
        FROM SNMPv2-SMI;

snmpResearch OBJECT IDENTIFIER
    ::= { enterprises 99 }

snmpResearchNode OBJECT IDENTIFIER
    ::= { snmpResearch 1 }

snmpResearchAgent OBJECT IDENTIFIER
    ::= { snmpResearchNode 1 }

snmpResearchUNIXAgent OBJECT IDENTIFIER
    ::= { snmpResearchAgent 1 }

snmpResearchSnmpd OBJECT IDENTIFIER
    ::= { snmpResearchUNIXAgent 1 }

snmpResearchProxyAgent OBJECT IDENTIFIER
    ::= { snmpResearchAgent 2 }

snmpResearchLb100Proxy OBJECT IDENTIFIER
    ::= { snmpResearchProxyAgent 1 }

snmpResearchEMANATEMasterAgent OBJECT IDENTIFIER
    ::= { snmpResearchAgent 3 }

solarisEMANATEMasterAgent OBJECT IDENTIFIER
    ::= { snmpResearchEMANATEMasterAgent 1 }

solarisTCPEMANATEMasterAgent OBJECT IDENTIFIER
    ::= { snmpResearchEMANATEMasterAgent 2 }

solarisx86TCPEMANATEMasterAgent OBJECT IDENTIFIER
    ::= { snmpResearchEMANATEMasterAgent 3 }

sunosEMANATEMasterAgent OBJECT IDENTIFIER
    ::= { snmpResearchEMANATEMasterAgent 4 }

dguxEMANATEMasterAgent OBJECT IDENTIFIER
    ::= { snmpResearchEMANATEMasterAgent 5 }

hpuxEMANATEMasterAgent OBJECT IDENTIFIER
    ::= { snmpResearchEMANATEMasterAgent 6 }

vxworksEMANATEMasterAgent OBJECT IDENTIFIER
    ::= { snmpResearchEMANATEMasterAgent 7 }

hprtEMANATEMasterAgent OBJECT IDENTIFIER
    ::= { snmpResearchEMANATEMasterAgent 8 }

aixEMANATEMasterAgent OBJECT IDENTIFIER
    ::= { snmpResearchEMANATEMasterAgent 9 }

sco3EMANATEMasterAgent OBJECT IDENTIFIER
    ::= { snmpResearchEMANATEMasterAgent 10 }

ntEMANATEMasterAgent OBJECT IDENTIFIER
    ::= { snmpResearchEMANATEMasterAgent 11 }

win31EMANATEMasterAgent OBJECT IDENTIFIER
    ::= { snmpResearchEMANATEMasterAgent 12 }

dynixEMANATEMasterAgent OBJECT IDENTIFIER
    ::= { snmpResearchEMANATEMasterAgent 13 }

osf1EMANATEMasterAgent OBJECT IDENTIFIER
    ::= { snmpResearchEMANATEMasterAgent 14 }

ncrEMANATEMasterAgent OBJECT IDENTIFIER
    ::= { snmpResearchEMANATEMasterAgent 15 }

sco5EMANATEMasterAgent OBJECT IDENTIFIER
    ::= { snmpResearchEMANATEMasterAgent 16 }

solarisx86EMANATEMasterAgent OBJECT IDENTIFIER
    ::= { snmpResearchEMANATEMasterAgent 17 }

freebsdEMANATEMasterAgent OBJECT IDENTIFIER
    ::= { snmpResearchEMANATEMasterAgent 18 }

irixEMANATEMasterAgent OBJECT IDENTIFIER
    ::= { snmpResearchEMANATEMasterAgent 19 }

os2EMANATEMasterAgent OBJECT IDENTIFIER
    ::= { snmpResearchEMANATEMasterAgent 20 }

unixwareEMANATEMasterAgent OBJECT IDENTIFIER
    ::= { snmpResearchEMANATEMasterAgent 21 }

bsdiEMANATEMasterAgent OBJECT IDENTIFIER
    ::= { snmpResearchEMANATEMasterAgent 22 }

sinixEMANATEMasterAgent OBJECT IDENTIFIER
    ::= { snmpResearchEMANATEMasterAgent 23 }

ftxEMANATEMasterAgent OBJECT IDENTIFIER
    ::= { snmpResearchEMANATEMasterAgent 24 }

hpux10EMANATEMasterAgent OBJECT IDENTIFIER
    ::= { snmpResearchEMANATEMasterAgent 25 }

dguxx86EMANATEMasterAgent OBJECT IDENTIFIER
    ::= { snmpResearchEMANATEMasterAgent 26 }

unixware21EMANATEMasterAgent OBJECT IDENTIFIER
    ::= { snmpResearchEMANATEMasterAgent 27 }

linuxEMANATEMasterAgent OBJECT IDENTIFIER
    ::= { snmpResearchEMANATEMasterAgent 28 }

osf4EMANATEMasterAgent OBJECT IDENTIFIER
    ::= { snmpResearchEMANATEMasterAgent 29 }

hpux11EMANATEMasterAgent OBJECT IDENTIFIER
    ::= { snmpResearchEMANATEMasterAgent 30 }

nextEMANATEMasterAgent OBJECT IDENTIFIER
    ::= { snmpResearchEMANATEMasterAgent 31 }

netbsdEMANATEMasterAgent OBJECT IDENTIFIER
    ::= { snmpResearchEMANATEMasterAgent 32 }

openvmsEMANATEMasterAgent OBJECT IDENTIFIER
    ::= { snmpResearchEMANATEMasterAgent 33 }

snmpResearchLTxxxAgent OBJECT IDENTIFIER
    ::= { snmpResearchAgent 4 }

snmpResearchLT301Agent OBJECT IDENTIFIER
    ::= { snmpResearchLTxxxAgent 1 }

snmpResearchVarVersion OBJECT IDENTIFIER
    ::= { snmpResearch 2 }

snmpResearchMIBs OBJECT IDENTIFIER
    ::= { snmpResearch 12 }

psMIB OBJECT IDENTIFIER
    ::= { snmpResearchMIBs 2 }

testMIB OBJECT IDENTIFIER
    ::= { snmpResearchMIBs 3 }

snmpResearchload OBJECT IDENTIFIER
    ::= { snmpResearchMIBs 4 }

oldExamples OBJECT IDENTIFIER
    ::= { snmpResearchMIBs 5 }

dmiTestMIB OBJECT IDENTIFIER
    ::= { snmpResearchMIBs 6 }

emacs2 OBJECT IDENTIFIER
    ::= { snmpResearchMIBs 7 }

sample OBJECT IDENTIFIER
    ::= { snmpResearchMIBs 8 }

etc OBJECT IDENTIFIER
    ::= { snmpResearchMIBs 9 }

spakes OBJECT IDENTIFIER
    ::= { snmpResearchMIBs 10 }

demo OBJECT IDENTIFIER
    ::= { snmpResearchMIBs 12 }

newV2ip OBJECT IDENTIFIER
    ::= { snmpResearchMIBs 13 }

newV2udp OBJECT IDENTIFIER
    ::= { snmpResearchMIBs 14 }

newV2tcp OBJECT IDENTIFIER
    ::= { snmpResearchMIBs 15 }

clusterMIB OBJECT IDENTIFIER
    ::= { snmpResearchMIBs 16 }

instanceRep OBJECT IDENTIFIER
    ::= { snmpResearchMIBs 17 }

brassMIB OBJECT IDENTIFIER
    ::= { snmpResearchMIBs 18 }

srExamples OBJECT IDENTIFIER
    ::= { snmpResearchMIBs 19 }

srBasics OBJECT IDENTIFIER
    ::= { srExamples 1 }

srProductFeatures OBJECT IDENTIFIER
    ::= { srExamples 2 }

latin OBJECT IDENTIFIER
    ::= { snmpResearchMIBs 21 }

processControl OBJECT IDENTIFIER
    ::= { snmpResearchMIBs 23 }

ltHardware OBJECT IDENTIFIER
    ::= { snmpResearchMIBs 25 }

alias OBJECT IDENTIFIER
    ::= { snmpResearchMIBs 27 }

softTrap OBJECT IDENTIFIER
    ::= { snmpResearchMIBs 28 }

critApp OBJECT IDENTIFIER
    ::= { snmpResearchMIBs 29 }

htmlpage OBJECT IDENTIFIER
    ::= { snmpResearchMIBs 30 }

phoneSwitch OBJECT IDENTIFIER
    ::= { snmpResearchMIBs 31 }

httpToSnmpAuthMappingMIB OBJECT IDENTIFIER
    ::= { snmpResearchMIBs 32 }

srCommunityMIB OBJECT IDENTIFIER
    ::= { snmpResearchMIBs 33 }

srAgtTest OBJECT IDENTIFIER
    ::= { snmpResearchMIBs 34 }

usmTargetTagMIB OBJECT IDENTIFIER
    ::= { snmpResearchMIBs 35 }

tgtAddressMaskMIB OBJECT IDENTIFIER
    ::= { snmpResearchMIBs 36 }

siServiceMIB OBJECT IDENTIFIER
    ::= { snmpResearchMIBs 38 }

siFsMonitor OBJECT IDENTIFIER
    ::= { snmpResearchMIBs 39 }

siLog OBJECT IDENTIFIER
    ::= { snmpResearchMIBs 40 }

smExtensionMIB OBJECT IDENTIFIER
    ::= { snmpResearchMIBs 41 }

siCIAgentEval OBJECT IDENTIFIER
    ::= { snmpResearchMIBs 42 }

siCIAgentEvalExpiredMsg OBJECT IDENTIFIER
    ::= { siCIAgentEval 1 }

siCIAgentEvalExpiredTrap OBJECT IDENTIFIER
    ::= { siCIAgentEval 10 }

srPrograms OBJECT IDENTIFIER
    ::= { snmpResearch 13 }

srExperimental OBJECT IDENTIFIER
    ::= { snmpResearch 15 }

srExperimentalMIBs OBJECT IDENTIFIER
    ::= { srExperimental 1 }

httpSecurityMIB OBJECT IDENTIFIER
    ::= { srExperimentalMIBs 1 }

reconfigMIB OBJECT IDENTIFIER
    ::= { srExperimentalMIBs 2 }

reconfigAgent OBJECT IDENTIFIER
    ::= { reconfigMIB 1 }

loadSubagent OBJECT IDENTIFIER
    ::= { reconfigMIB 2 }

srSmExt OBJECT IDENTIFIER
    ::= { srExperimentalMIBs 3 }

eventMIB OBJECT IDENTIFIER
    ::= { srExperimentalMIBs 5 }

srExperimentalDomains OBJECT IDENTIFIER
    ::= { srExperimental 2 }

httpTCPIPDomain OBJECT IDENTIFIER
    ::= { srExperimentalDomains 1 }

secureIntelligence OBJECT IDENTIFIER
    ::= { snmpResearch 16 }

enterpol OBJECT IDENTIFIER
    ::= { secureIntelligence 1 }

enterpolEvents OBJECT IDENTIFIER
    ::= { enterpol 1 }

enterpolStatusEvents OBJECT IDENTIFIER
    ::= { enterpolEvents 1 }

enterpolPingFailed OBJECT IDENTIFIER
    ::= { enterpolStatusEvents 1 }

mlmMIB OBJECT IDENTIFIER
    ::= { snmpResearch 42 }

END -- end of module SNMP-RESEARCH-MIB.
