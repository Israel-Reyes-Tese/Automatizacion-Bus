MIB-EMSPLUS-IPASOLINK-MPLS-MIB DEFINITIONS ::= BEGIN
    
    IMPORTS
        InetAddress, InetAddressType
            FROM INET-ADDRESS-MIB
        Gauge
            FROM RFC1155-SMI
        OBJECT-TYPE
            FROM RFC-1212
        enterprises
            FROM SNMPv2-SMI
        TruthValue
            FROM SNMPv2-TC;
    
    EnableDisableValue ::=
        INTEGER { invalid(0), disable(1), enable(2) }
    
    
    IpeMplsIndex ::=
        Gauge (0..4095)
    
    
    IpeMplsLabel ::=
        Gauge (16..1048575)
    
    
    IpeMplsTpOamIndex ::=
        INTEGER (0..256)
    
    
    IpeMplsTpOamMegID ::=
        OCTET STRING (SIZE(0..44))
    
    
    IpeMplsTpPathStatus ::=
        INTEGER { invalid(0), forceSwitched(1), signalFail(2),
                        signalDegraded(3), manualSwitched(4), noRequested(5),
                        lockout(6), forceSwitchedByRemote(7),
                        signalFailOnRemote(8), signalDegradeOnRemote(9),
                        manualSwitchedByRemote(10), lockoutByRemote(11),
                        waitToRestore(12) }
    
    
    IpeStatsInfo ::=
        INTEGER { invalid(0), validNoMaint(1), validMaint(2),
                        invalidNoMaint(3), invalidMaint(4) }
    
    
    IpeVlanIdOrAnyOrNone ::=
        INTEGER (0..4095)
    
    
    OffOnValue ::=
        INTEGER { invalid(0), off(1), on(2) }
    
    
    SeverityValue ::=
        INTEGER { cleared(1), indetermine(2), critical(3), major(4),
                        minor(5), warning(6), notReport(7) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.213
    commonPnmsPlus OBJECT IDENTIFIER
        ::= { radioEquipment 213 }
    
    -- 1.3.6.1.4.1.119.2.3.69.213.502
    ipasolink OBJECT IDENTIFIER
        ::= { commonPnmsPlus 502 }
    
    -- 1.3.6.1.4.1.119.2.3.69.213.502.501
    pasoNeoIpe-common OBJECT IDENTIFIER
        ::= { ipasolink 501 }
    
    -- 1.3.6.1.4.1.119.2.3.69.213.502.501.3
    alarmStatusGroup OBJECT IDENTIFIER
        ::= { pasoNeoIpe-common 3 }
    
    -- 1.3.6.1.4.1.119.2.3.69.213.502.501.3.43
    asMplsGroup OBJECT IDENTIFIER
        ::= { alarmStatusGroup 43 }
    
    -- 1.3.6.1.4.1.119.2.3.69.213.502.501.3.43.22
    asMplsTpOamGroup OBJECT IDENTIFIER
        ::= { asMplsGroup 22 }
    
    -- 1.3.6.1.4.1.119.2.3.69.213.502.501.3.43.22.1
    asMplsTpOamMepTable OBJECT-TYPE
        SYNTAX      SEQUENCE OF AsMplsTpOamMepEntry
        ACCESS      not-accessible
        STATUS      mandatory
        DESCRIPTION
            "This table contains alarm and status information related to MEP
             entry."
        ::= { asMplsTpOamGroup 1 }
    
    -- 1.3.6.1.4.1.119.2.3.69.213.502.501.3.43.22.1.1
    asMplsTpOamMepEntry OBJECT-TYPE
        SYNTAX      AsMplsTpOamMepEntry
        ACCESS      not-accessible
        STATUS      mandatory
        DESCRIPTION
            ""
        INDEX       { asMplsTpOamMepNEAddressAddrType, asMplsTpOamMepNEAddress, asMplsTpOamMepIndex }
        ::= { asMplsTpOamMepTable 1 }
    
    AsMplsTpOamMepEntry ::= SEQUENCE {
        asMplsTpOamMepIndex                 IpeMplsTpOamIndex,
        asMplsTpOamMepNEAddress             InetAddress,
        asMplsTpOamMepLOC                   SeverityValue,
        asMplsTpOamMepRdiReceived           SeverityValue,
        asMplsTpOamMepNEAddressAddrType     InetAddressType
    }
    
    -- 1.3.6.1.4.1.119.2.3.69.213.502.501.3.43.22.1.1.1
    asMplsTpOamMepIndex OBJECT-TYPE
        SYNTAX      IpeMplsTpOamIndex
        ACCESS      not-accessible
        STATUS      mandatory
        DESCRIPTION
            "Index of this table."
        ::= { asMplsTpOamMepEntry 1 }
    
    -- 1.3.6.1.4.1.119.2.3.69.213.502.501.3.43.22.1.1.2
    asMplsTpOamMepNEAddress OBJECT-TYPE
        SYNTAX      InetAddress
        ACCESS      not-accessible
        STATUS      mandatory
        DESCRIPTION
            "reserved."
        ::= { asMplsTpOamMepEntry 2 }
    
    -- 1.3.6.1.4.1.119.2.3.69.213.502.501.3.43.22.1.1.3
    asMplsTpOamMepLOC OBJECT-TYPE
        SYNTAX      SeverityValue
        ACCESS      read-only
        STATUS      mandatory
        DESCRIPTION
            "This alarm will be asserted when the MEP does not receive proper
             CCM frames."
        ::= { asMplsTpOamMepEntry 3 }
    
    -- 1.3.6.1.4.1.119.2.3.69.213.502.501.3.43.22.1.1.4
    asMplsTpOamMepRdiReceived OBJECT-TYPE
        SYNTAX      SeverityValue
        ACCESS      read-only
        STATUS      mandatory
        DESCRIPTION
            "this alarm will be asserted when the MEP received CCM frames
             with RDI information."
        ::= { asMplsTpOamMepEntry 4 }
    
    -- 1.3.6.1.4.1.119.2.3.69.213.502.501.3.43.22.1.1.1001
    asMplsTpOamMepNEAddressAddrType OBJECT-TYPE
        SYNTAX      InetAddressType
        ACCESS      not-accessible
        STATUS      mandatory
        DESCRIPTION
            "Represents the IP address type of NE address index.
             Only ipv4(1) and ipv6(2) are supported."
        ::= { asMplsTpOamMepEntry 1001 }
    
    -- 1.3.6.1.4.1.119.2.3.69.213.502.501.3.43.22.2
    asMplsTpOamPeerMepTable OBJECT-TYPE
        SYNTAX      SEQUENCE OF AsMplsTpOamPeerMepEntry
        ACCESS      not-accessible
        STATUS      mandatory
        DESCRIPTION
            "This table contains alarm and status information per peer MEP."
        ::= { asMplsTpOamGroup 2 }
    
    -- 1.3.6.1.4.1.119.2.3.69.213.502.501.3.43.22.2.1
    asMplsTpOamPeerMepEntry OBJECT-TYPE
        SYNTAX      AsMplsTpOamPeerMepEntry
        ACCESS      not-accessible
        STATUS      mandatory
        DESCRIPTION
            ""
        INDEX       { asMplsTpOamPeerNEAddressAddrType, asMplsTpOamPeerNEAddress, asMplsTpOamPeerIndex }
        ::= { asMplsTpOamPeerMepTable 1 }
    
    AsMplsTpOamPeerMepEntry ::= SEQUENCE {
        asMplsTpOamPeerIndex                INTEGER,
        asMplsTpOamPeerNEAddress            InetAddress,
        asMplsTpOamLocalMepIndex            IpeMplsTpOamIndex,
        asMplsTpOamPeerMepId                INTEGER,
        asMplsTpOamPeerLOC                  TruthValue,
        asMplsTpOamPeerRdiReceived          TruthValue,
        asMplsTpOamPeerNEAddressAddrType    InetAddressType
    }
    
    -- 1.3.6.1.4.1.119.2.3.69.213.502.501.3.43.22.2.1.1
    asMplsTpOamPeerIndex OBJECT-TYPE
        SYNTAX      INTEGER (1..256)
        ACCESS      not-accessible
        STATUS      mandatory
        DESCRIPTION
            "Index of this table."
        ::= { asMplsTpOamPeerMepEntry 1 }
    
    -- 1.3.6.1.4.1.119.2.3.69.213.502.501.3.43.22.2.1.2
    asMplsTpOamPeerNEAddress OBJECT-TYPE
        SYNTAX      InetAddress
        ACCESS      not-accessible
        STATUS      mandatory
        DESCRIPTION
            "reserved."
        ::= { asMplsTpOamPeerMepEntry 2 }
    
    -- 1.3.6.1.4.1.119.2.3.69.213.502.501.3.43.22.2.1.3
    asMplsTpOamLocalMepIndex OBJECT-TYPE
        SYNTAX      IpeMplsTpOamIndex
        ACCESS      read-only
        STATUS      mandatory
        DESCRIPTION
            "This object indicates local MEP index that assigns Peer MEP."
        ::= { asMplsTpOamPeerMepEntry 3 }
    
    -- 1.3.6.1.4.1.119.2.3.69.213.502.501.3.43.22.2.1.4
    asMplsTpOamPeerMepId OBJECT-TYPE
        SYNTAX      INTEGER (1..8191)
        ACCESS      not-accessible
        STATUS      mandatory
        DESCRIPTION
            "this object indicates peer MEP ID in protocol sense."
        ::= { asMplsTpOamPeerMepEntry 4 }
    
    -- 1.3.6.1.4.1.119.2.3.69.213.502.501.3.43.22.2.1.5
    asMplsTpOamPeerLOC OBJECT-TYPE
        SYNTAX      TruthValue
        ACCESS      read-only
        STATUS      mandatory
        DESCRIPTION
            "This alarm will be asserted when the proper CCM frames are not
             received between local MEP and peer MEP which is specified by
             asMplsTpOamPeerMepId."
        ::= { asMplsTpOamPeerMepEntry 5 }
    
    -- 1.3.6.1.4.1.119.2.3.69.213.502.501.3.43.22.2.1.6
    asMplsTpOamPeerRdiReceived OBJECT-TYPE
        SYNTAX      TruthValue
        ACCESS      read-only
        STATUS      mandatory
        DESCRIPTION
            "this alarm will be asserted when the local MEP received CCM
             frames with RDI information from peer MEP which is specified by
             asMplsTpOamPeerMepId"
        ::= { asMplsTpOamPeerMepEntry 6 }
    
    -- 1.3.6.1.4.1.119.2.3.69.213.502.501.3.43.22.2.1.1001
    asMplsTpOamPeerNEAddressAddrType OBJECT-TYPE
        SYNTAX      InetAddressType
        ACCESS      not-accessible
        STATUS      mandatory
        DESCRIPTION
            "Represents the IP address type of NE address index.
             Only ipv4(1) and ipv6(2) are supported."
        ::= { asMplsTpOamPeerMepEntry 1001 }
    
    -- 1.3.6.1.4.1.119.2.3.69.213.502.501.3.43.22.3
    asMplsTpOamMegTable OBJECT-TYPE
        SYNTAX      SEQUENCE OF AsMplsTpOamMegEntry
        ACCESS      not-accessible
        STATUS      mandatory
        DESCRIPTION
            "This table contains alarm and status information releated to MEG
             instance."
        ::= { asMplsTpOamGroup 3 }
    
    -- 1.3.6.1.4.1.119.2.3.69.213.502.501.3.43.22.3.1
    asMplsTpOamMegEntry OBJECT-TYPE
        SYNTAX      AsMplsTpOamMegEntry
        ACCESS      not-accessible
        STATUS      mandatory
        DESCRIPTION
            ""
        INDEX       { asMplsTpOamMegNEAddressAddrType, asMplsTpOamMegNEAddress, asMplsTpOamMegIndex }
        ::= { asMplsTpOamMegTable 1 }
    
    AsMplsTpOamMegEntry ::= SEQUENCE {
        asMplsTpOamMegIndex                 INTEGER,
        asMplsTpOamMegNEAddress             InetAddress,
        asMplsTpOamMegMismerge              SeverityValue,
        asMplsTpOamMegUnexpectedMep         SeverityValue,
        asMplsTpOamMegNEAddressAddrType     InetAddressType
    }
    
    -- 1.3.6.1.4.1.119.2.3.69.213.502.501.3.43.22.3.1.1
    asMplsTpOamMegIndex OBJECT-TYPE
        SYNTAX      INTEGER (1..128)
        ACCESS      not-accessible
        STATUS      mandatory
        DESCRIPTION
            "Index of this table."
        ::= { asMplsTpOamMegEntry 1 }
    
    -- 1.3.6.1.4.1.119.2.3.69.213.502.501.3.43.22.3.1.2
    asMplsTpOamMegNEAddress OBJECT-TYPE
        SYNTAX      InetAddress
        ACCESS      not-accessible
        STATUS      mandatory
        DESCRIPTION
            "reserved."
        ::= { asMplsTpOamMegEntry 2 }
    
    -- 1.3.6.1.4.1.119.2.3.69.213.502.501.3.43.22.3.1.3
    asMplsTpOamMegMismerge OBJECT-TYPE
        SYNTAX      SeverityValue
        ACCESS      read-only
        STATUS      mandatory
        DESCRIPTION
            "This alarm will be asserted when the MEG ID contained in
             received CCM frames does not match local MEG ID."
        ::= { asMplsTpOamMegEntry 3 }
    
    -- 1.3.6.1.4.1.119.2.3.69.213.502.501.3.43.22.3.1.4
    asMplsTpOamMegUnexpectedMep OBJECT-TYPE
        SYNTAX      SeverityValue
        ACCESS      read-only
        STATUS      mandatory
        DESCRIPTION
            "This alarm will be asserted when the CCM interval or MEP ID
             contained in received CCM frames does not match local
             configuration."
        ::= { asMplsTpOamMegEntry 4 }
    
    -- 1.3.6.1.4.1.119.2.3.69.213.502.501.3.43.22.3.1.1001
    asMplsTpOamMegNEAddressAddrType OBJECT-TYPE
        SYNTAX      InetAddressType
        ACCESS      not-accessible
        STATUS      mandatory
        DESCRIPTION
            "Represents the IP address type of NE address index.
             Only ipv4(1) and ipv6(2) are supported."
        ::= { asMplsTpOamMegEntry 1001 }
    
    -- 1.3.6.1.4.1.119.2.3.69.213.502.501.3.43.23
    asMplsTpLpsGroup OBJECT IDENTIFIER
        ::= { asMplsGroup 23 }
    
    -- 1.3.6.1.4.1.119.2.3.69.213.502.501.3.43.23.1
    asMplsTpLpsTable OBJECT-TYPE
        SYNTAX      SEQUENCE OF AsMplsTpLpsEntry
        ACCESS      not-accessible
        STATUS      mandatory
        DESCRIPTION
            "This table contains MPLS-TP Linear Protection Group status."
        ::= { asMplsTpLpsGroup 1 }
    
    -- 1.3.6.1.4.1.119.2.3.69.213.502.501.3.43.23.1.1
    asMplsTpLpsEntry OBJECT-TYPE
        SYNTAX      AsMplsTpLpsEntry
        ACCESS      not-accessible
        STATUS      mandatory
        DESCRIPTION
            ""
        INDEX       { asMplsTpLpsNEAddressAddrType, asMplsTpLpsNEAddress, asMplsTpLpsGroupIndex }
        ::= { asMplsTpLpsTable 1 }
    
    AsMplsTpLpsEntry ::= SEQUENCE {
        asMplsTpLpsGroupIndex               INTEGER,
        asMplsTpLpsNEAddress                InetAddress,
        asMplsTpWorkingPathStatus           IpeMplsTpPathStatus,
        asMplsTpProtectionPathStatus        IpeMplsTpPathStatus,
        asMplsTpLpsOnlinePath               INTEGER,
        asMplsTpLpsLockout                  INTEGER,
        asMplsTpLpsProtocolError            SeverityValue,
        asMplsTpWorkingPathLocalAlarm       OffOnValue,
        asMplsTpProtectionPathLocalAlarm    OffOnValue,
        asMplsTpLpsNEAddressAddrType        InetAddressType
    }
    
    -- 1.3.6.1.4.1.119.2.3.69.213.502.501.3.43.23.1.1.1
    asMplsTpLpsGroupIndex OBJECT-TYPE
        SYNTAX      INTEGER (1..128)
        ACCESS      not-accessible
        STATUS      mandatory
        DESCRIPTION
            "Index of this table."
        ::= { asMplsTpLpsEntry 1 }
    
    -- 1.3.6.1.4.1.119.2.3.69.213.502.501.3.43.23.1.1.2
    asMplsTpLpsNEAddress OBJECT-TYPE
        SYNTAX      InetAddress
        ACCESS      not-accessible
        STATUS      mandatory
        DESCRIPTION
            "reserved."
        ::= { asMplsTpLpsEntry 2 }
    
    -- 1.3.6.1.4.1.119.2.3.69.213.502.501.3.43.23.1.1.3
    asMplsTpWorkingPathStatus OBJECT-TYPE
        SYNTAX      IpeMplsTpPathStatus
        ACCESS      read-only
        STATUS      mandatory
        DESCRIPTION
            "This object indicates working path status."
        ::= { asMplsTpLpsEntry 3 }
    
    -- 1.3.6.1.4.1.119.2.3.69.213.502.501.3.43.23.1.1.4
    asMplsTpProtectionPathStatus OBJECT-TYPE
        SYNTAX      IpeMplsTpPathStatus
        ACCESS      read-only
        STATUS      mandatory
        DESCRIPTION
            "this object indicates protection path status."
        ::= { asMplsTpLpsEntry 4 }
    
    -- 1.3.6.1.4.1.119.2.3.69.213.502.501.3.43.23.1.1.5
    asMplsTpLpsOnlinePath OBJECT-TYPE
        SYNTAX      INTEGER { invalid(0), work(1), protection(2) }
        ACCESS      read-only
        STATUS      mandatory
        DESCRIPTION
            "this object indicates online path information. The user traffic
             is send and received on the path which is specified by this
             object."
        ::= { asMplsTpLpsEntry 5 }
    
    -- 1.3.6.1.4.1.119.2.3.69.213.502.501.3.43.23.1.1.6
    asMplsTpLpsLockout OBJECT-TYPE
        SYNTAX      INTEGER { invalid(0), normal(1), lockout(2) }
        ACCESS      read-only
        STATUS      mandatory
        DESCRIPTION
            "this object indicates lockout status. If this object returns
             lockout, then the protection path is locked-out."
        ::= { asMplsTpLpsEntry 6 }
    
    -- 1.3.6.1.4.1.119.2.3.69.213.502.501.3.43.23.1.1.7
    asMplsTpLpsProtocolError OBJECT-TYPE
        SYNTAX      SeverityValue
        ACCESS      read-only
        STATUS      mandatory
        DESCRIPTION
            "this object indicates the alarm for MPLS-TP APS protocol
             communication."
        ::= { asMplsTpLpsEntry 7 }
    
    -- 1.3.6.1.4.1.119.2.3.69.213.502.501.3.43.23.1.1.8
    asMplsTpWorkingPathLocalAlarm OBJECT-TYPE
        SYNTAX      OffOnValue
        ACCESS      read-only
        STATUS      mandatory
        DESCRIPTION
            "This object indicates if working path has any alarms which
             become the switching factor.
             ON shows that such alarms are available."
        ::= { asMplsTpLpsEntry 8 }
    
    -- 1.3.6.1.4.1.119.2.3.69.213.502.501.3.43.23.1.1.9
    asMplsTpProtectionPathLocalAlarm OBJECT-TYPE
        SYNTAX      OffOnValue
        ACCESS      read-only
        STATUS      mandatory
        DESCRIPTION
            "This object indicates if protection path has any alarms which
             become the switching factor.
             ON shows that such alarms are available."
        ::= { asMplsTpLpsEntry 9 }
    
    -- 1.3.6.1.4.1.119.2.3.69.213.502.501.3.43.23.1.1.1001
    asMplsTpLpsNEAddressAddrType OBJECT-TYPE
        SYNTAX      InetAddressType
        ACCESS      not-accessible
        STATUS      mandatory
        DESCRIPTION
            "Represents the IP address type of NE address index.
             Only ipv4(1) and ipv6(2) are supported."
        ::= { asMplsTpLpsEntry 1001 }
    
    -- 1.3.6.1.4.1.119.2.3.69.213.502.501.11
    rmonGroup OBJECT IDENTIFIER
        ::= { pasoNeoIpe-common 11 }
    
    -- 1.3.6.1.4.1.119.2.3.69.213.502.501.11.43
    rmonMplsGroup OBJECT IDENTIFIER
        ::= { rmonGroup 43 }
    
    -- 1.3.6.1.4.1.119.2.3.69.213.502.501.11.43.1
    rmon15minMplsSegmentCounterGroup OBJECT IDENTIFIER
        ::= { rmonMplsGroup 1 }
    
    -- 1.3.6.1.4.1.119.2.3.69.213.502.501.11.43.1.1
    rmon15minMplsSegmentCounterTable OBJECT-TYPE
        SYNTAX      SEQUENCE OF Rmon15minMplsSegmentCounterEntry
        ACCESS      not-accessible
        STATUS      mandatory
        DESCRIPTION
            "This table contains 15 minutes MPLS segment counter. The counted
             value is reset every 15 minutes."
        ::= { rmon15minMplsSegmentCounterGroup 1 }
    
    -- 1.3.6.1.4.1.119.2.3.69.213.502.501.11.43.1.1.1
    rmon15minMplsSegmentCounterEntry OBJECT-TYPE
        SYNTAX      Rmon15minMplsSegmentCounterEntry
        ACCESS      not-accessible
        STATUS      mandatory
        DESCRIPTION
            ""
        INDEX       { rmon15minMplsSegmentCounterNEAddressAddrType, rmon15minMplsSegmentCounterNEAddress, rmon15minMplsSegmentCounterIndex }
        ::= { rmon15minMplsSegmentCounterTable 1 }
    
    Rmon15minMplsSegmentCounterEntry ::= SEQUENCE {
        rmon15minMplsSegmentCounterIndex                INTEGER,
        rmon15minMplsSegmentCounterNEAddress            InetAddress,
        rmon15minMplsSegmentCounterHCRxFrameStatus      IpeStatsInfo,
        rmon15minMplsSegmentCounterHCTxFrameStatus      IpeStatsInfo,
        rmon15minMplsSegmentCounterHCRxDiscardStatus    IpeStatsInfo,
        rmon15minMplsSegmentCounterHCRxOctetStatus      IpeStatsInfo,
        rmon15minMplsSegmentCounterHCTxOctetStatus      IpeStatsInfo,
        rmon15minMplsSegmentCounterNEAddressAddrType    InetAddressType
    }
    
    -- 1.3.6.1.4.1.119.2.3.69.213.502.501.11.43.1.1.1.1
    rmon15minMplsSegmentCounterIndex OBJECT-TYPE
        SYNTAX      INTEGER (1..256)
        ACCESS      not-accessible
        STATUS      mandatory
        DESCRIPTION
            "Index of this table."
        ::= { rmon15minMplsSegmentCounterEntry 1 }
    
    -- 1.3.6.1.4.1.119.2.3.69.213.502.501.11.43.1.1.1.2
    rmon15minMplsSegmentCounterNEAddress OBJECT-TYPE
        SYNTAX      InetAddress
        ACCESS      not-accessible
        STATUS      mandatory
        DESCRIPTION
            "reserved"
        ::= { rmon15minMplsSegmentCounterEntry 2 }
    
    -- 1.3.6.1.4.1.119.2.3.69.213.502.501.11.43.1.1.1.4
    rmon15minMplsSegmentCounterHCRxFrameStatus OBJECT-TYPE
        SYNTAX      IpeStatsInfo
        ACCESS      read-only
        STATUS      mandatory
        DESCRIPTION
            "RMON 15 minutes RX Frames Status."
        ::= { rmon15minMplsSegmentCounterEntry 4 }
    
    -- 1.3.6.1.4.1.119.2.3.69.213.502.501.11.43.1.1.1.6
    rmon15minMplsSegmentCounterHCTxFrameStatus OBJECT-TYPE
        SYNTAX      IpeStatsInfo
        ACCESS      read-only
        STATUS      mandatory
        DESCRIPTION
            "RMON 15 minutes TX Frames Status."
        ::= { rmon15minMplsSegmentCounterEntry 6 }
    
    -- 1.3.6.1.4.1.119.2.3.69.213.502.501.11.43.1.1.1.8
    rmon15minMplsSegmentCounterHCRxDiscardStatus OBJECT-TYPE
        SYNTAX      IpeStatsInfo
        ACCESS      read-only
        STATUS      mandatory
        DESCRIPTION
            "RMON 15 minutes RX Discarded Frames Status."
        ::= { rmon15minMplsSegmentCounterEntry 8 }
    
    -- 1.3.6.1.4.1.119.2.3.69.213.502.501.11.43.1.1.1.10
    rmon15minMplsSegmentCounterHCRxOctetStatus OBJECT-TYPE
        SYNTAX      IpeStatsInfo
        ACCESS      read-only
        STATUS      mandatory
        DESCRIPTION
            "RMON 15 minutes RX Octets Status."
        ::= { rmon15minMplsSegmentCounterEntry 10 }
    
    -- 1.3.6.1.4.1.119.2.3.69.213.502.501.11.43.1.1.1.12
    rmon15minMplsSegmentCounterHCTxOctetStatus OBJECT-TYPE
        SYNTAX      IpeStatsInfo
        ACCESS      read-only
        STATUS      mandatory
        DESCRIPTION
            "RMON 15 minutes TX Octets Status."
        ::= { rmon15minMplsSegmentCounterEntry 12 }
    
    -- 1.3.6.1.4.1.119.2.3.69.213.502.501.11.43.1.1.1.1001
    rmon15minMplsSegmentCounterNEAddressAddrType OBJECT-TYPE
        SYNTAX      InetAddressType
        ACCESS      not-accessible
        STATUS      mandatory
        DESCRIPTION
            "Represents the IP address type of NE address index.
             Only ipv4(1) and ipv6(2) are supported."
        ::= { rmon15minMplsSegmentCounterEntry 1001 }
    
    -- 1.3.6.1.4.1.119.2.3.69.213.502.501.11.43.1.2
    rmon15minMplsSegmentCounterMapTable OBJECT-TYPE
        SYNTAX      SEQUENCE OF Rmon15minMplsSegmentCounterMapEntry
        ACCESS      not-accessible
        STATUS      mandatory
        DESCRIPTION
            "This table contains MPLS Segment Counter mapping information. If
             the MPLS Segment Counter is enabled on this segment, this object
             will show the corresponding MPLS Segment Counter Index."
        ::= { rmon15minMplsSegmentCounterGroup 2 }
    
    -- 1.3.6.1.4.1.119.2.3.69.213.502.501.11.43.1.2.1
    rmon15minMplsSegmentCounterMapEntry OBJECT-TYPE
        SYNTAX      Rmon15minMplsSegmentCounterMapEntry
        ACCESS      not-accessible
        STATUS      mandatory
        DESCRIPTION
            ""
        INDEX       { rmon15minMplsSegmentCounterMapNEAddressAddrType, rmon15minMplsSegmentCounterMapNEAddress, rmon15minMplsSegmentCounterMapBiDirSegment }
        ::= { rmon15minMplsSegmentCounterMapTable 1 }
    
    Rmon15minMplsSegmentCounterMapEntry ::= SEQUENCE {
        rmon15minMplsSegmentCounterMapBiDirSegment          IpeMplsIndex,
        rmon15minMplsSegmentCounterMapNEAddress             InetAddress,
        rmon15minMplsSegmentCounterMapCounterIndex          INTEGER,
        rmon15minMplsSegmentCounterMapNEAddressAddrType     InetAddressType
    }
    
    -- 1.3.6.1.4.1.119.2.3.69.213.502.501.11.43.1.2.1.1
    rmon15minMplsSegmentCounterMapBiDirSegment OBJECT-TYPE
        SYNTAX      IpeMplsIndex
        ACCESS      not-accessible
        STATUS      mandatory
        DESCRIPTION
            "Index of this table."
        ::= { rmon15minMplsSegmentCounterMapEntry 1 }
    
    -- 1.3.6.1.4.1.119.2.3.69.213.502.501.11.43.1.2.1.2
    rmon15minMplsSegmentCounterMapNEAddress OBJECT-TYPE
        SYNTAX      InetAddress
        ACCESS      not-accessible
        STATUS      mandatory
        DESCRIPTION
            "reserved."
        ::= { rmon15minMplsSegmentCounterMapEntry 2 }
    
    -- 1.3.6.1.4.1.119.2.3.69.213.502.501.11.43.1.2.1.3
    rmon15minMplsSegmentCounterMapCounterIndex OBJECT-TYPE
        SYNTAX      INTEGER (0..256)
        ACCESS      read-only
        STATUS      mandatory
        DESCRIPTION
            "MPLS Segment Counter Index which is assigned to the segment. '0'
             means no counter is assigned."
        ::= { rmon15minMplsSegmentCounterMapEntry 3 }
    
    -- 1.3.6.1.4.1.119.2.3.69.213.502.501.11.43.1.2.1.1001
    rmon15minMplsSegmentCounterMapNEAddressAddrType OBJECT-TYPE
        SYNTAX      InetAddressType
        ACCESS      not-accessible
        STATUS      mandatory
        DESCRIPTION
            "Represents the IP address type of NE address index.
             Only ipv4(1) and ipv6(2) are supported."
        ::= { rmon15minMplsSegmentCounterMapEntry 1001 }
    
    -- 1.3.6.1.4.1.119.2.3.69.213.502.501.11.43.2
    rmon1dayMplsSegmentCounterGroup OBJECT IDENTIFIER
        ::= { rmonMplsGroup 2 }
    
    -- 1.3.6.1.4.1.119.2.3.69.213.502.501.11.43.2.1
    rmon1dayMplsSegmentCounterTable OBJECT-TYPE
        SYNTAX      SEQUENCE OF Rmon1dayMplsSegmentCounterEntry
        ACCESS      not-accessible
        STATUS      mandatory
        DESCRIPTION
            "This table contains 1 day MPLS segment counter. The counted
             value is reset everyday."
        ::= { rmon1dayMplsSegmentCounterGroup 1 }
    
    -- 1.3.6.1.4.1.119.2.3.69.213.502.501.11.43.2.1.1
    rmon1dayMplsSegmentCounterEntry OBJECT-TYPE
        SYNTAX      Rmon1dayMplsSegmentCounterEntry
        ACCESS      not-accessible
        STATUS      mandatory
        DESCRIPTION
            ""
        INDEX       { rmon1dayMplsSegmentCounterNEAddressAddrType, rmon1dayMplsSegmentCounterNEAddress, rmon1dayMplsSegmentCounterIndex }
        ::= { rmon1dayMplsSegmentCounterTable 1 }
    
    Rmon1dayMplsSegmentCounterEntry ::= SEQUENCE {
        rmon1dayMplsSegmentCounterIndex                 INTEGER,
        rmon1dayMplsSegmentCounterNEAddress             InetAddress,
        rmon1dayMplsSegmentCounterHCRxFrameStatus       IpeStatsInfo,
        rmon1dayMplsSegmentCounterHCTxFrameStatus       IpeStatsInfo,
        rmon1dayMplsSegmentCounterHCRxDiscardStatus     IpeStatsInfo,
        rmon1dayMplsSegmentCounterHCRxOctetStatus       IpeStatsInfo,
        rmon1dayMplsSegmentCounterHCTxOctetStatus       IpeStatsInfo,
        rmon1dayMplsSegmentCounterNEAddressAddrType     InetAddressType
    }
    
    -- 1.3.6.1.4.1.119.2.3.69.213.502.501.11.43.2.1.1.1
    rmon1dayMplsSegmentCounterIndex OBJECT-TYPE
        SYNTAX      INTEGER (1..256)
        ACCESS      not-accessible
        STATUS      mandatory
        DESCRIPTION
            "Index of this table."
        ::= { rmon1dayMplsSegmentCounterEntry 1 }
    
    -- 1.3.6.1.4.1.119.2.3.69.213.502.501.11.43.2.1.1.2
    rmon1dayMplsSegmentCounterNEAddress OBJECT-TYPE
        SYNTAX      InetAddress
        ACCESS      not-accessible
        STATUS      mandatory
        DESCRIPTION
            "reserved."
        ::= { rmon1dayMplsSegmentCounterEntry 2 }
    
    -- 1.3.6.1.4.1.119.2.3.69.213.502.501.11.43.2.1.1.4
    rmon1dayMplsSegmentCounterHCRxFrameStatus OBJECT-TYPE
        SYNTAX      IpeStatsInfo
        ACCESS      read-only
        STATUS      mandatory
        DESCRIPTION
            "RMON 1 day RX Frames Status."
        ::= { rmon1dayMplsSegmentCounterEntry 4 }
    
    -- 1.3.6.1.4.1.119.2.3.69.213.502.501.11.43.2.1.1.6
    rmon1dayMplsSegmentCounterHCTxFrameStatus OBJECT-TYPE
        SYNTAX      IpeStatsInfo
        ACCESS      read-only
        STATUS      mandatory
        DESCRIPTION
            "RMON 1 day TX Frames Status."
        ::= { rmon1dayMplsSegmentCounterEntry 6 }
    
    -- 1.3.6.1.4.1.119.2.3.69.213.502.501.11.43.2.1.1.8
    rmon1dayMplsSegmentCounterHCRxDiscardStatus OBJECT-TYPE
        SYNTAX      IpeStatsInfo
        ACCESS      read-only
        STATUS      mandatory
        DESCRIPTION
            "RMON 1 day RX Discarded Frames Status."
        ::= { rmon1dayMplsSegmentCounterEntry 8 }
    
    -- 1.3.6.1.4.1.119.2.3.69.213.502.501.11.43.2.1.1.10
    rmon1dayMplsSegmentCounterHCRxOctetStatus OBJECT-TYPE
        SYNTAX      IpeStatsInfo
        ACCESS      read-only
        STATUS      mandatory
        DESCRIPTION
            "RMON 1 day RX Octets Status."
        ::= { rmon1dayMplsSegmentCounterEntry 10 }
    
    -- 1.3.6.1.4.1.119.2.3.69.213.502.501.11.43.2.1.1.12
    rmon1dayMplsSegmentCounterHCTxOctetStatus OBJECT-TYPE
        SYNTAX      IpeStatsInfo
        ACCESS      read-only
        STATUS      mandatory
        DESCRIPTION
            "RMON 1 day TX Octets Status."
        ::= { rmon1dayMplsSegmentCounterEntry 12 }
    
    -- 1.3.6.1.4.1.119.2.3.69.213.502.501.11.43.2.1.1.1001
    rmon1dayMplsSegmentCounterNEAddressAddrType OBJECT-TYPE
        SYNTAX      InetAddressType
        ACCESS      not-accessible
        STATUS      mandatory
        DESCRIPTION
            "Represents the IP address type of NE address index.
             Only ipv4(1) and ipv6(2) are supported."
        ::= { rmon1dayMplsSegmentCounterEntry 1001 }
    
    -- 1.3.6.1.4.1.119.2.3.69.213.502.501.11.43.2.2
    rmon1dayMplsSegmentCounterMapTable OBJECT-TYPE
        SYNTAX      SEQUENCE OF Rmon1dayMplsSegmentCounterMapEntry
        ACCESS      not-accessible
        STATUS      mandatory
        DESCRIPTION
            "This table contains MPLS Segment Counter mapping information. If
             the MPLS Segment Counter is enabled on this segment, this object
             will show the corresponding MPLS Segment Counter Index."
        ::= { rmon1dayMplsSegmentCounterGroup 2 }
    
    -- 1.3.6.1.4.1.119.2.3.69.213.502.501.11.43.2.2.1
    rmon1dayMplsSegmentCounterMapEntry OBJECT-TYPE
        SYNTAX      Rmon1dayMplsSegmentCounterMapEntry
        ACCESS      not-accessible
        STATUS      mandatory
        DESCRIPTION
            ""
        INDEX       { rmon1dayMplsSegmentCounterMapNEAddressAddrType, rmon1dayMplsSegmentCounterMapNEAddress, rmon1dayMplsSegmentCounterMapBiDirSegment }
        ::= { rmon1dayMplsSegmentCounterMapTable 1 }
    
    Rmon1dayMplsSegmentCounterMapEntry ::= SEQUENCE {
        rmon1dayMplsSegmentCounterMapBiDirSegment       IpeMplsIndex,
        rmon1dayMplsSegmentCounterMapNEAddress          InetAddress,
        rmon1dayMplsSegmentCounterMapCounterIndex       INTEGER,
        rmon1dayMplsSegmentCounterMapNEAddressAddrType  InetAddressType
    }
    
    -- 1.3.6.1.4.1.119.2.3.69.213.502.501.11.43.2.2.1.1
    rmon1dayMplsSegmentCounterMapBiDirSegment OBJECT-TYPE
        SYNTAX      IpeMplsIndex
        ACCESS      not-accessible
        STATUS      mandatory
        DESCRIPTION
            "Index of this table."
        ::= { rmon1dayMplsSegmentCounterMapEntry 1 }
    
    -- 1.3.6.1.4.1.119.2.3.69.213.502.501.11.43.2.2.1.2
    rmon1dayMplsSegmentCounterMapNEAddress OBJECT-TYPE
        SYNTAX      InetAddress
        ACCESS      not-accessible
        STATUS      mandatory
        DESCRIPTION
            "reserved."
        ::= { rmon1dayMplsSegmentCounterMapEntry 2 }
    
    -- 1.3.6.1.4.1.119.2.3.69.213.502.501.11.43.2.2.1.3
    rmon1dayMplsSegmentCounterMapCounterIndex OBJECT-TYPE
        SYNTAX      INTEGER (0..256)
        ACCESS      read-only
        STATUS      mandatory
        DESCRIPTION
            "MPLS Segment Counter Index which is assigned to the segment. '0'
             means no counter is assigned."
        ::= { rmon1dayMplsSegmentCounterMapEntry 3 }
    
    -- 1.3.6.1.4.1.119.2.3.69.213.502.501.11.43.2.2.1.1001
    rmon1dayMplsSegmentCounterMapNEAddressAddrType OBJECT-TYPE
        SYNTAX      InetAddressType
        ACCESS      not-accessible
        STATUS      mandatory
        DESCRIPTION
            "Represents the IP address type of NE address index.
             Only ipv4(1) and ipv6(2) are supported."
        ::= { rmon1dayMplsSegmentCounterMapEntry 1001 }
    
END -- end of module MIB-EMSPLUS-IPASOLINK-MPLS-MIB.
