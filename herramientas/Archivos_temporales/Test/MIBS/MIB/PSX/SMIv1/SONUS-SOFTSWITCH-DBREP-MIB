--
-- This SMIv1 module has been generated by smidump 0.2-cvs. Do not edit.
--

SONUS-SOFTSWITCH-DBREP-MIB DEFINITIONS ::= BEGIN

IMPORTS
    InetAddress, InetAddressType
        FROM INET-ADDRESS-MIB
    OBJECT-TYPE
        FROM RFC-1212
    TRAP-TYPE
        FROM RFC-1215
    IpAddress
        FROM RFC1155-SMI
    sonusEventClass, sonusEventDescription, sonusEventLevel, 
    sonusEventTime
        FROM SONUS-COMMON-MIB
    sonusServicesMIBs
        FROM SONUS-SMI;

sonusSoftSwitchDbrepMIB OBJECT IDENTIFIER
    ::= { sonusServicesMIBs 16 }

-- sonusSoftSwitchDbrepMIB MODULE-IDENTITY
--     LAST-UPDATED    "200205030000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch Database Replication Management."
--     ::= { sonusServicesMIBs 16 }


sonusSoftSwitchDbrepMIBObjects OBJECT IDENTIFIER
    ::= { sonusSoftSwitchDbrepMIB 1 }

sonusSoftSwitchDbrepMIBNotifications OBJECT IDENTIFIER
    ::= { sonusSoftSwitchDbrepMIB 2 }

sonusSoftSwitchDbrepMIBNotificationsPrefix OBJECT IDENTIFIER
    ::= { sonusSoftSwitchDbrepMIBNotifications 0 }

sonusSoftSwitchDbrepMIBNotificationsObjects OBJECT IDENTIFIER
    ::= { sonusSoftSwitchDbrepMIBNotifications 1 }

sonusSoftSwitchDbrepPeerIp OBJECT-TYPE
    SYNTAX          IpAddress
    ACCESS          read-only
    STATUS          deprecated
    DESCRIPTION     
            "The IP address of the remote peer."
    ::= { sonusSoftSwitchDbrepMIBNotificationsObjects 1 }

sonusSoftSwitchDbrepPeerExtendedIpType OBJECT-TYPE
    SYNTAX          InetAddressType
    ACCESS          read-only
    STATUS          mandatory
    DESCRIPTION     
            "The IP address type of the remote peer."
    ::= { sonusSoftSwitchDbrepMIBNotificationsObjects 2 }

sonusSoftSwitchDbrepPeerExtendedIp OBJECT-TYPE
    SYNTAX          InetAddress
    ACCESS          read-only
    STATUS          mandatory
    DESCRIPTION     
            "The IP address of the remote peer."
    ::= { sonusSoftSwitchDbrepMIBNotificationsObjects 3 }

sonusSoftSwitchDbrepUpNotification TRAP-TYPE
    ENTERPRISE      sonusSoftSwitchDbrepMIBNotifications
    VARIABLES       { sonusEventDescription, sonusEventClass, 
                      sonusEventLevel, sonusEventTime }
--     STATUS          mandatory
    DESCRIPTION     
            "Dbrep daemon up"
    ::= 1

sonusSoftSwitchDbrepDownNotification TRAP-TYPE
    ENTERPRISE      sonusSoftSwitchDbrepMIBNotifications
    VARIABLES       { sonusEventDescription, sonusEventClass, 
                      sonusEventLevel, sonusEventTime }
--     STATUS          mandatory
    DESCRIPTION     
            "Dbrep daemon down"
    ::= 2

sonusSoftSwitchDbrepConnectionUpNotification TRAP-TYPE
    ENTERPRISE      sonusSoftSwitchDbrepMIBNotifications
    VARIABLES       { sonusEventDescription, sonusEventClass, 
                      sonusEventLevel, sonusEventTime, 
                      sonusSoftSwitchDbrepPeerIp }
--     STATUS          deprecated
    DESCRIPTION     
            "Dbrep connection establised"
    ::= 3

sonusSoftSwitchDbrepConnectionDownNotification TRAP-TYPE
    ENTERPRISE      sonusSoftSwitchDbrepMIBNotifications
    VARIABLES       { sonusEventDescription, sonusEventClass, 
                      sonusEventLevel, sonusEventTime, 
                      sonusSoftSwitchDbrepPeerIp }
--     STATUS          deprecated
    DESCRIPTION     
            "Dbrep connection severed"
    ::= 4

sonusSoftSwitchDbrepConnectionAttemptNotification TRAP-TYPE
    ENTERPRISE      sonusSoftSwitchDbrepMIBNotifications
    VARIABLES       { sonusEventDescription, sonusEventClass, 
                      sonusEventLevel, sonusEventTime, 
                      sonusSoftSwitchDbrepPeerIp }
--     STATUS          deprecated
    DESCRIPTION     
            "Dbrep attempt to connect to remote peer"
    ::= 5

sonusSoftSwitchDbrepDbErrorNotification TRAP-TYPE
    ENTERPRISE      sonusSoftSwitchDbrepMIBNotifications
    VARIABLES       { sonusEventDescription, sonusEventClass, 
                      sonusEventLevel, sonusEventTime }
--     STATUS          mandatory
    DESCRIPTION     
            "Dbrep failure while attempting a DB operation"
    ::= 6

sonusSoftSwitchDbrepLagThresholdExceededNotification TRAP-TYPE
    ENTERPRISE      sonusSoftSwitchDbrepMIBNotifications
    VARIABLES       { sonusEventDescription, sonusEventClass, 
                      sonusEventLevel, sonusEventTime, 
                      sonusSoftSwitchDbrepPeerIp }
--     STATUS          deprecated
    DESCRIPTION     
            "Dbrep Lag Threshold was exceeded"
    ::= 7

sonusExtendedSoftSwitchDbrepConnectionUpNotification TRAP-TYPE
    ENTERPRISE      sonusSoftSwitchDbrepMIBNotifications
    VARIABLES       { sonusEventDescription, sonusEventClass, 
                      sonusEventLevel, sonusEventTime, 
                      sonusSoftSwitchDbrepPeerExtendedIpType, 
                      sonusSoftSwitchDbrepPeerExtendedIp }
--     STATUS          mandatory
    DESCRIPTION     
            "Dbrep connection establised"
    ::= 8

sonusExtendedSoftSwitchDbrepConnectionDownNotification TRAP-TYPE
    ENTERPRISE      sonusSoftSwitchDbrepMIBNotifications
    VARIABLES       { sonusEventDescription, sonusEventClass, 
                      sonusEventLevel, sonusEventTime, 
                      sonusSoftSwitchDbrepPeerExtendedIpType, 
                      sonusSoftSwitchDbrepPeerExtendedIp }
--     STATUS          mandatory
    DESCRIPTION     
            "Dbrep connection severed"
    ::= 9

sonusExtendedSoftSwitchDbrepConnectionAttemptNotification TRAP-TYPE
    ENTERPRISE      sonusSoftSwitchDbrepMIBNotifications
    VARIABLES       { sonusEventDescription, sonusEventClass, 
                      sonusEventLevel, sonusEventTime, 
                      sonusSoftSwitchDbrepPeerExtendedIpType, 
                      sonusSoftSwitchDbrepPeerExtendedIp }
--     STATUS          mandatory
    DESCRIPTION     
            "Dbrep attempt to connect to remote peer"
    ::= 10

sonusExtendedSoftSwitchDbrepLagThresholdExceededNotification TRAP-TYPE
    ENTERPRISE      sonusSoftSwitchDbrepMIBNotifications
    VARIABLES       { sonusEventDescription, sonusEventClass, 
                      sonusEventLevel, sonusEventTime, 
                      sonusSoftSwitchDbrepPeerExtendedIpType, 
                      sonusSoftSwitchDbrepPeerExtendedIp }
--     STATUS          mandatory
    DESCRIPTION     
            "Dbrep Lag Threshold was exceeded"
    ::= 11

END -- end of module SONUS-SOFTSWITCH-DBREP-MIB.
