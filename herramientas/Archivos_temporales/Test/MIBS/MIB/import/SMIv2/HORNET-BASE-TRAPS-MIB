--
-- This SMIv2 module has been generated by smidump 0.2-cvs. Do not edit.
--

HORNET-BASE-TRAPS-MIB DEFINITIONS ::= BEGIN

IMPORTS
    Integer32, MODULE-IDENTITY, NOTIFICATION-TYPE, OBJECT-TYPE
        FROM SNMPv2-SMI
    DisplayString, TEXTUAL-CONVENTION
        FROM SNMPv2-TC
    sonusAlarmDescription, sonusAlarmLevel, sonusAlarmNodeID, 
    sonusAlarmSequenceId, sonusAlarmTime, sonusServerID
        FROM SONUS-COMMON-TRAP-MIB
    sonusEventLogTypeAdminFileCount, sonusEventLogTypeAdminFileSize, 
    sonusEventLogTypeAdminFilterLevel, 
    sonusEventLogTypeAdminMaxEventMemorySize, 
    sonusEventLogTypeAdminMessageQueueSize, sonusEventLogTypeAdminSaveTo, 
    sonusEventLogTypeStatusCurrentFile
        FROM SONUS-GEN2-EVENT-LOG-MIB
    sonusCspsNotificationMIBs
        FROM SONUS-SMI
    sonusSystemSoftwareUpgradeStatusReason
        FROM SONUS-SYSTEM-MIB;

sonusCpBaseTrapsMIB MODULE-IDENTITY
    LAST-UPDATED    "200807110000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Base Hornet Traps."
    REVISION        "200807110000Z"
    DESCRIPTION     
            "Last revision."
    ::= { sonusCspsNotificationMIBs 2 }


InetAddressIP ::= TEXTUAL-CONVENTION
    STATUS          current
    DESCRIPTION     
            "confd:inetAddressIP"
    SYNTAX          OCTET STRING (SIZE(4 | 16))

sonusCpBaseTraps OBJECT IDENTIFIER
    ::= { sonusCpBaseTrapsMIB 1 }

sonusCpNtpServicesMIBNotifications OBJECT IDENTIFIER
    ::= { sonusCpBaseTraps 1 }

sonusCpNtpServicesMIBNotificationsPrefix OBJECT IDENTIFIER
    ::= { sonusCpNtpServicesMIBNotifications 0 }

sonusCpNtpServicesMIBNotificationsObjects OBJECT IDENTIFIER
    ::= { sonusCpNtpServicesMIBNotifications 1 }

sonusCpNtpServerOutOfServiceReason OBJECT-TYPE
    SYNTAX          INTEGER { ntpServerDisabled(1), 
                        ntpServerOutOfSync(2) }
    MAX-ACCESS      read-only
    STATUS          current
    DESCRIPTION     
            "The reason why this Network Timing Protocol Server is out of service."
    ::= { sonusCpNtpServicesMIBNotificationsObjects 1 }

sonusCpNtpDownReason OBJECT-TYPE
    SYNTAX          INTEGER { noNtpServerConfigured(1), 
                        allNtpServersOutOfSync(2) }
    MAX-ACCESS      read-only
    STATUS          current
    DESCRIPTION     
            "The reason why the Network Timing Protocol is down for this system."
    ::= { sonusCpNtpServicesMIBNotificationsObjects 2 }

sonusCpNtpIpAddress OBJECT-TYPE
    SYNTAX          InetAddressIP
    MAX-ACCESS      read-only
    STATUS          current
    DESCRIPTION     
            "
             The IP address of this NTP Peer. 
             "
    ::= { sonusCpNtpServicesMIBNotificationsObjects 3 }

sonusCpRedundancyServicesMIBNotifications OBJECT IDENTIFIER
    ::= { sonusCpBaseTraps 2 }

sonusCpRedundancyServicesMIBNotificationsPrefix OBJECT IDENTIFIER
    ::= { sonusCpRedundancyServicesMIBNotifications 0 }

sonusCpRedundancyServicesMIBNotificationsObjects OBJECT IDENTIFIER
    ::= { sonusCpRedundancyServicesMIBNotifications 1 }

sonusCpRedundPrevActiveServerName OBJECT-TYPE
    SYNTAX          DisplayString
    MAX-ACCESS      read-only
    STATUS          current
    DESCRIPTION     
            "The server identifier of the failed server module whose switchover
             generated this trap."
    ::= { sonusCpRedundancyServicesMIBNotificationsObjects 1 }

sonusCpRedundancyServicesGroupName OBJECT-TYPE
    SYNTAX          DisplayString
    MAX-ACCESS      read-only
    STATUS          current
    DESCRIPTION     
            "
             The name of this redundancy group instance.
             "
    ::= { sonusCpRedundancyServicesMIBNotificationsObjects 2 }

sonusCpSoftwareUpgradeServicesMIBNotifications OBJECT IDENTIFIER
    ::= { sonusCpBaseTraps 3 }

sonusCpSoftwareUpgradeServicesMIBNotificationsPrefix OBJECT IDENTIFIER
    ::= { sonusCpSoftwareUpgradeServicesMIBNotifications 0 }

sonusCpSoftwareUpgradeServicesMIBNotificationsObjects OBJECT IDENTIFIER
    ::= { sonusCpSoftwareUpgradeServicesMIBNotifications 1 }

sonusSystemSoftwareUpgradeOldRelease OBJECT-TYPE
    SYNTAX          DisplayString
    MAX-ACCESS      read-only
    STATUS          current
    DESCRIPTION     
            "
             Old software release.
             "
    ::= { sonusCpSoftwareUpgradeServicesMIBNotificationsObjects 1 }

sonusSystemSoftwareUpgradeNewRelease OBJECT-TYPE
    SYNTAX          DisplayString
    MAX-ACCESS      read-only
    STATUS          current
    DESCRIPTION     
            "
             New software release.
             "
    ::= { sonusCpSoftwareUpgradeServicesMIBNotificationsObjects 2 }

sonusCpEventLogMIBNotifications OBJECT IDENTIFIER
    ::= { sonusCpBaseTraps 4 }

sonusCpEventLogMIBNotificationsPrefix OBJECT IDENTIFIER
    ::= { sonusCpEventLogMIBNotifications 0 }

sonusCpEventLogMIBNotificationsObjects OBJECT IDENTIFIER
    ::= { sonusCpEventLogMIBNotifications 1 }

sonusCpEvLogAdminState OBJECT-TYPE
    SYNTAX          INTEGER { disabled(1), enabled(2), rollfile(3) }
    MAX-ACCESS      read-only
    STATUS          current
    DESCRIPTION     
            "The requested state of the given Event Log type.  Rollfile
             will close an enabled log file and reopen, incrementing the
             suffix.  If a file is disabled and rolled, the command is
             ignored."
    ::= { sonusCpEventLogMIBNotificationsObjects 1 }

sonusCpEvLogShutdownReason OBJECT-TYPE
    SYNTAX          INTEGER { fileWriteFailed(1), nfsError(2), 
                        createDirectoryFailed(3), 
                        maximumFileCountReached(4), fileRemoveFailed(5), 
                        fileOpenFailed(6), fileHeaderWriteFailed(7), 
                        memoryAllocationFailed(8), 
                        administrativeShutdown(9), 
                        localDiskUnavailable(10) }
    MAX-ACCESS      read-only
    STATUS          current
    DESCRIPTION     
            "The reason that event file logging has been shutdown."
    ::= { sonusCpEventLogMIBNotificationsObjects 2 }

sonusCpEvLogDirName OBJECT-TYPE
    SYNTAX          DisplayString
    MAX-ACCESS      read-only
    STATUS          current
    DESCRIPTION     
            "The event file log directory name."
    ::= { sonusCpEventLogMIBNotificationsObjects 3 }

sonusCpEvLogFilePercentage OBJECT-TYPE
    SYNTAX          Integer32
    MAX-ACCESS      read-only
    STATUS          current
    DESCRIPTION     
            "The percentage the event log directory is full based on file count."
    ::= { sonusCpEventLogMIBNotificationsObjects 4 }

sonusCpEvLogCurFileCount OBJECT-TYPE
    SYNTAX          Integer32
    MAX-ACCESS      read-only
    STATUS          current
    DESCRIPTION     
            "The current count of event files."
    ::= { sonusCpEventLogMIBNotificationsObjects 5 }

sonusCpEvLogErrorCode OBJECT-TYPE
    SYNTAX          Integer32
    MAX-ACCESS      read-only
    STATUS          current
    DESCRIPTION     
            "The evlog error code."
    ::= { sonusCpEventLogMIBNotificationsObjects 6 }

sonusEvLogTypeName OBJECT-TYPE
    SYNTAX          DisplayString
    MAX-ACCESS      read-only
    STATUS          current
    DESCRIPTION     
            "The event file log type."
    ::= { sonusCpEventLogMIBNotificationsObjects 7 }

sonusCpEventLogType OBJECT-TYPE
    SYNTAX          INTEGER { packet(7), audit(6), security(5), acct(4), 
                        trace(3), debug(2), system(1) }
    MAX-ACCESS      read-only
    STATUS          current
    DESCRIPTION     
            "
             The type of the event log.  Each type has separate
             configuration parameters and logs to a separate file.
             "
    ::= { sonusCpEventLogMIBNotificationsObjects 8 }

sonusAlarmMgrId OBJECT-TYPE
    SYNTAX          Integer32
    MAX-ACCESS      read-only
    STATUS          current
    DESCRIPTION     
            "
             The Alarm Manager Id.
             "
    ::= { sonusCpEventLogMIBNotificationsObjects 9 }

sonusEventLogRenameToFile OBJECT-TYPE
    SYNTAX          DisplayString
    MAX-ACCESS      read-only
    STATUS          current
    DESCRIPTION     
            "
             The rename to file name
             "
    ::= { sonusCpEventLogMIBNotificationsObjects 10 }

sonusCpSystemServicesMIBNotifications OBJECT IDENTIFIER
    ::= { sonusCpBaseTraps 5 }

sonusCpSystemServicesMIBNotificationsPrefix OBJECT IDENTIFIER
    ::= { sonusCpSystemServicesMIBNotifications 0 }

sonusCpSystemServicesMIBNotificationsObjects OBJECT IDENTIFIER
    ::= { sonusCpSystemServicesMIBNotifications 1 }

sonusCpSystemServerName OBJECT-TYPE
    SYNTAX          DisplayString
    MAX-ACCESS      read-only
    STATUS          current
    DESCRIPTION     
            "
             The unique identifier assigned to this card or server.
             "
    ::= { sonusCpSystemServicesMIBNotificationsObjects 1 }

sonusCpSystemHardDiskNumber OBJECT-TYPE
    SYNTAX          Integer32
    MAX-ACCESS      read-only
    STATUS          current
    DESCRIPTION     
            "
             Hard disk number (typically 0 through 3)
             "
    ::= { sonusCpSystemServicesMIBNotificationsObjects 2 }

sonusCpSystemPowerSupplyId OBJECT-TYPE
    SYNTAX          DisplayString
    MAX-ACCESS      read-only
    STATUS          current
    DESCRIPTION     
            "
             The name of the power supply (/SYS/VPS)
             "
    ::= { sonusCpSystemServicesMIBNotificationsObjects 3 }

sonusCpSystemFanId OBJECT-TYPE
    SYNTAX          DisplayString
    MAX-ACCESS      read-only
    STATUS          current
    DESCRIPTION     
            "
             The name of the fan (usually /FT0/F0/ /FT0/F1/ etc).
             
             "
    ::= { sonusCpSystemServicesMIBNotificationsObjects 4 }

sonusCpSystemCoredumpFile OBJECT-TYPE
    SYNTAX          DisplayString
    MAX-ACCESS      read-only
    STATUS          current
    DESCRIPTION     
            "
             File name of the coredump.
             "
    ::= { sonusCpSystemServicesMIBNotificationsObjects 5 }

sonusCpSystemCoredumpSpacePct OBJECT-TYPE
    SYNTAX          Integer32
    MAX-ACCESS      read-only
    STATUS          current
    DESCRIPTION     
            "
             Percentage of allowed coredump space occupied.
             "
    ::= { sonusCpSystemServicesMIBNotificationsObjects 6 }

sonusCpSystemServerTemperatureSensorId OBJECT-TYPE
    SYNTAX          DisplayString
    MAX-ACCESS      read-only
    STATUS          current
    DESCRIPTION     
            "
             Id of the temperature sensor, MB/T_AMB0, MB/T_AMB1 etc.
             
             "
    ::= { sonusCpSystemServicesMIBNotificationsObjects 7 }

sonusCpSystemServerTemperature OBJECT-TYPE
    SYNTAX          Integer32
    MAX-ACCESS      read-only
    STATUS          current
    DESCRIPTION     
            "
             Temperature (in Degrees C)
             "
    ::= { sonusCpSystemServicesMIBNotificationsObjects 8 }

sonusCpSystemAdminName OBJECT-TYPE
    SYNTAX          DisplayString
    MAX-ACCESS      read-only
    STATUS          current
    DESCRIPTION     
            "
             Name of the system
             "
    ::= { sonusCpSystemServicesMIBNotificationsObjects 9 }

sonusCpSystemDiskPartition OBJECT-TYPE
    SYNTAX          DisplayString
    MAX-ACCESS      read-only
    STATUS          current
    DESCRIPTION     
            "
             Partition on the disk
             "
    ::= { sonusCpSystemServicesMIBNotificationsObjects 10 }

sonusCpSystemDiskSpaceUsedPct OBJECT-TYPE
    SYNTAX          Integer32
    MAX-ACCESS      read-only
    STATUS          current
    DESCRIPTION     
            "
             Percentage of the disk space used.
             "
    ::= { sonusCpSystemServicesMIBNotificationsObjects 11 }

sonusCpSystemPortName OBJECT-TYPE
    SYNTAX          DisplayString
    MAX-ACCESS      read-only
    STATUS          current
    DESCRIPTION     
            "
             The name of the port.
             "
    ::= { sonusCpSystemServicesMIBNotificationsObjects 12 }

sonusCpSystemConfigFileName OBJECT-TYPE
    SYNTAX          DisplayString
    MAX-ACCESS      read-only
    STATUS          current
    DESCRIPTION     
            "
             File name of the configuration file.
             "
    ::= { sonusCpSystemServicesMIBNotificationsObjects 13 }

sonusCpSelfBaseMacAddress OBJECT-TYPE
    SYNTAX          DisplayString
    MAX-ACCESS      read-only
    STATUS          current
    DESCRIPTION     
            "
             Local base MAC addresss.
             "
    ::= { sonusCpSystemServicesMIBNotificationsObjects 14 }

sonusCpPeerBaseMacAddress OBJECT-TYPE
    SYNTAX          DisplayString
    MAX-ACCESS      read-only
    STATUS          current
    DESCRIPTION     
            "
             Peer base MAC addresss.
             "
    ::= { sonusCpSystemServicesMIBNotificationsObjects 15 }

sonusCpActiveBaseMacAddress OBJECT-TYPE
    SYNTAX          DisplayString
    MAX-ACCESS      read-only
    STATUS          current
    DESCRIPTION     
            "
             Active MAC addresss of the system.
             "
    ::= { sonusCpSystemServicesMIBNotificationsObjects 16 }

sonusNodeOverloadType OBJECT-TYPE
    SYNTAX          DisplayString (SIZE(0..3))
    MAX-ACCESS      read-only
    STATUS          current
    DESCRIPTION     
            "Overload Resource Type"
    ::= { sonusCpSystemServicesMIBNotificationsObjects 17 }

sonusNodeOverloadLevel OBJECT-TYPE
    SYNTAX          Integer32 (0..3)
    MAX-ACCESS      read-only
    STATUS          current
    DESCRIPTION     
            "The Overload Level"
    ::= { sonusCpSystemServicesMIBNotificationsObjects 18 }

sonusNodeOverloadThresholdCurrent OBJECT-TYPE
    SYNTAX          Integer32 (0..100)
    MAX-ACCESS      read-only
    STATUS          current
    DESCRIPTION     
            "The current calculated value of this resource"
    ::= { sonusCpSystemServicesMIBNotificationsObjects 19 }

sonusNodeOverloadThresholdConfigured OBJECT-TYPE
    SYNTAX          Integer32 (0..100)
    MAX-ACCESS      read-only
    STATUS          current
    DESCRIPTION     
            "The configured threshold level for this resource"
    ::= { sonusCpSystemServicesMIBNotificationsObjects 20 }

sonusCpProductCapabilityName OBJECT-TYPE
    SYNTAX          DisplayString
    MAX-ACCESS      read-only
    STATUS          current
    DESCRIPTION     
            "
             Product capability type.
             "
    ::= { sonusCpSystemServicesMIBNotificationsObjects 21 }

sonusCpProductCapabilityValue OBJECT-TYPE
    SYNTAX          DisplayString
    MAX-ACCESS      read-only
    STATUS          current
    DESCRIPTION     
            "
             Product Capability value of local server.
             "
    ::= { sonusCpSystemServicesMIBNotificationsObjects 22 }

sonusCpProductPeerCapabilityValue OBJECT-TYPE
    SYNTAX          DisplayString
    MAX-ACCESS      read-only
    STATUS          current
    DESCRIPTION     
            "
             Product Capability value of peer server.
             "
    ::= { sonusCpSystemServicesMIBNotificationsObjects 23 }

sonusCpSystemHardDiskName OBJECT-TYPE
    SYNTAX          DisplayString
    MAX-ACCESS      read-only
    STATUS          current
    DESCRIPTION     
            "
             Name of a disk device on the system.
             "
    ::= { sonusCpSystemServicesMIBNotificationsObjects 24 }

sonusCpSystemHardDiskError OBJECT-TYPE
    SYNTAX          DisplayString
    MAX-ACCESS      read-only
    STATUS          current
    DESCRIPTION     
            "
             Error string reported by Self-Monitoring, Analysis and Reporting Technology (SMART).
             "
    ::= { sonusCpSystemServicesMIBNotificationsObjects 25 }

sonusCpSystemLifeAvailAttrib OBJECT-TYPE
    SYNTAX          DisplayString
    MAX-ACCESS      read-only
    STATUS          current
    DESCRIPTION     
            "
             Value representing the percentage of disk life remaining reported by Self-Monitoring, Analysis and Reporting Technology (SMART) or N/A if not supported.
             "
    ::= { sonusCpSystemServicesMIBNotificationsObjects 26 }

sonusCpSystemMemoryUsage OBJECT-TYPE
    SYNTAX          Integer32
    MAX-ACCESS      read-only
    STATUS          current
    DESCRIPTION     
            "
             Percentage of the system memory used.
             "
    ::= { sonusCpSystemServicesMIBNotificationsObjects 27 }

sonusCpSystemUserString OBJECT-TYPE
    SYNTAX          OCTET STRING (SIZE(0..255))
    MAX-ACCESS      read-only
    STATUS          current
    DESCRIPTION     
            "
             User provided information string.
             "
    ::= { sonusCpSystemServicesMIBNotificationsObjects 28 }

sonusCpNifMIBNotifications OBJECT IDENTIFIER
    ::= { sonusCpBaseTraps 6 }

sonusCpNifMIBNotificationsPrefix OBJECT IDENTIFIER
    ::= { sonusCpNifMIBNotifications 0 }

sonusCpNifMIBNotificationsObjects OBJECT IDENTIFIER
    ::= { sonusCpNifMIBNotifications 1 }

sonusCpNifCeName OBJECT-TYPE
    SYNTAX          DisplayString
    MAX-ACCESS      read-only
    STATUS          current
    DESCRIPTION     
            "
             The host name is this server.
             "
    ::= { sonusCpNifMIBNotificationsObjects 1 }

sonusCpNifType OBJECT-TYPE
    SYNTAX          INTEGER { externalSignaling(3), internalSignaling(2), 
                        management(1) }
    MAX-ACCESS      read-only
    STATUS          current
    DESCRIPTION     
            "
             The type of nif to which the port belongs, which is one of:
             management
             internalSignaling
             externalSignaling
             "
    ::= { sonusCpNifMIBNotificationsObjects 2 }

sonusCpNifUsage OBJECT-TYPE
    SYNTAX          INTEGER { secondary(2), primary(1) }
    MAX-ACCESS      read-only
    STATUS          current
    DESCRIPTION     
            "
             The way the port will be used, which is one of:
             primary
             secondary
             "
    ::= { sonusCpNifMIBNotificationsObjects 3 }

sonusCpRadiusAccountingMIBNotifications OBJECT IDENTIFIER
    ::= { sonusCpBaseTraps 7 }

sonusCpRadiusAccountingMIBNotificationsPrefix OBJECT IDENTIFIER
    ::= { sonusCpRadiusAccountingMIBNotifications 0 }

sonusCpRadiusAccountingMIBNotificationsObjects OBJECT IDENTIFIER
    ::= { sonusCpRadiusAccountingMIBNotifications 1 }

sonusCpRadiusServerName OBJECT-TYPE
    SYNTAX          DisplayString
    MAX-ACCESS      read-only
    STATUS          current
    DESCRIPTION     
            "
             The host name of the radius server
             "
    ::= { sonusCpRadiusAccountingMIBNotificationsObjects 1 }

sonusCpRadiusFlushedPackets OBJECT-TYPE
    SYNTAX          Integer32
    MAX-ACCESS      read-only
    STATUS          current
    DESCRIPTION     
            "
             The number of Radius packets flushed to disk
             "
    ::= { sonusCpRadiusAccountingMIBNotificationsObjects 2 }

sonusCpRadiusFlushedPacketsFile OBJECT-TYPE
    SYNTAX          DisplayString
    MAX-ACCESS      read-only
    STATUS          current
    DESCRIPTION     
            "
             The filename of the file containing the flushed Radius packets
             "
    ::= { sonusCpRadiusAccountingMIBNotificationsObjects 3 }

sonusCpLicenseMIBNotifications OBJECT IDENTIFIER
    ::= { sonusCpBaseTraps 8 }

sonusCpLicenseMIBNotificationsPrefix OBJECT IDENTIFIER
    ::= { sonusCpLicenseMIBNotifications 0 }

sonusCpLicenseMIBNotificationsObjects OBJECT IDENTIFIER
    ::= { sonusCpLicenseMIBNotifications 1 }

sonusCpLicenseViolationDescString OBJECT-TYPE
    SYNTAX          DisplayString
    MAX-ACCESS      read-only
    STATUS          current
    DESCRIPTION     
            "This string describes details of any attempted violation of license integrity"
    ::= { sonusCpLicenseMIBNotificationsObjects 1 }

sonusCpLicenseId OBJECT-TYPE
    SYNTAX          DisplayString
    MAX-ACCESS      read-only
    STATUS          current
    DESCRIPTION     
            "The license Id"
    ::= { sonusCpLicenseMIBNotificationsObjects 2 }

sonusCpLicenseFeatureName OBJECT-TYPE
    SYNTAX          DisplayString
    MAX-ACCESS      read-only
    STATUS          current
    DESCRIPTION     
            "The license feature string"
    ::= { sonusCpLicenseMIBNotificationsObjects 3 }

sonusSessConfigLicenses OBJECT-TYPE
    SYNTAX          Integer32
    MAX-ACCESS      read-only
    STATUS          current
    DESCRIPTION     
            "
             The number of configured licenses
             "
    ::= { sonusCpLicenseMIBNotificationsObjects 4 }

sonusSessSystemLimit OBJECT-TYPE
    SYNTAX          Integer32
    MAX-ACCESS      read-only
    STATUS          current
    DESCRIPTION     
            "
             The system limit of maximum sessions
             "
    ::= { sonusCpLicenseMIBNotificationsObjects 5 }

sonusCpCdrServerMIBNotifications OBJECT IDENTIFIER
    ::= { sonusCpBaseTraps 9 }

sonusCpCdrServerMIBNotificationsPrefix OBJECT IDENTIFIER
    ::= { sonusCpCdrServerMIBNotifications 0 }

sonusCpCdrServerMIBNotificationsObjects OBJECT IDENTIFIER
    ::= { sonusCpCdrServerMIBNotifications 1 }

sonusCpCdrServerType OBJECT-TYPE
    SYNTAX          DisplayString
    MAX-ACCESS      read-only
    STATUS          current
    DESCRIPTION     
            "The CDR server that is currently active (primary or secondary)."
    ::= { sonusCpCdrServerMIBNotificationsObjects 1 }

sonusCpCdrServerIpAddress OBJECT-TYPE
    SYNTAX          DisplayString
    MAX-ACCESS      read-only
    STATUS          current
    DESCRIPTION     
            "The IP address of this NTP Peer."
    ::= { sonusCpCdrServerMIBNotificationsObjects 2 }

sonusCpNtpServerInServiceNotification NOTIFICATION-TYPE
    OBJECTS         { sonusAlarmNodeID, sonusAlarmLevel, 
                      sonusAlarmSequenceId, sonusAlarmTime, 
                      sonusAlarmDescription, sonusCpSystemServerName, 
                      sonusCpNtpIpAddress }
    STATUS          current
    DESCRIPTION     
            "This trap indicates that a Network Timing Protocol Server is in service."
    ::= { sonusCpNtpServicesMIBNotificationsPrefix 1 }

sonusCpNtpServerOutOfServiceNotification NOTIFICATION-TYPE
    OBJECTS         { sonusAlarmNodeID, sonusAlarmLevel, 
                      sonusAlarmSequenceId, sonusAlarmTime, 
                      sonusAlarmDescription, sonusCpSystemServerName, 
                      sonusCpNtpIpAddress, 
                      sonusCpNtpServerOutOfServiceReason }
    STATUS          current
    DESCRIPTION     
            "This trap indicates that a Network Timing Protocol Server is out of service."
    ::= { sonusCpNtpServicesMIBNotificationsPrefix 2 }

sonusCpNtpUpNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that Network Timing Protocol Server is Up."
    ::= { sonusCpNtpServicesMIBNotificationsPrefix 3 }

sonusCpNtpDownNotification NOTIFICATION-TYPE
    OBJECTS         { sonusAlarmNodeID, sonusAlarmLevel, 
                      sonusAlarmSequenceId, sonusAlarmTime, 
                      sonusAlarmDescription, sonusCpSystemServerName, 
                      sonusCpNtpDownReason }
    STATUS          current
    DESCRIPTION     
            "This trap indicates that Network Timing Protocol is down."
    ::= { sonusCpNtpServicesMIBNotificationsPrefix 4 }

sonusCpNtpAllServersOutOfSyncNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that all Network Timing Protocol Servers are Out of Sync."
    ::= { sonusCpNtpServicesMIBNotificationsPrefix 5 }

sonusCpNtpServerOutOfSyncNotification NOTIFICATION-TYPE
    OBJECTS         { sonusAlarmNodeID, sonusAlarmLevel, 
                      sonusAlarmSequenceId, sonusAlarmTime, 
                      sonusAlarmDescription, sonusCpSystemServerName, 
                      sonusCpNtpIpAddress }
    STATUS          current
    DESCRIPTION     
            "This trap indicates that a Network Timing Protocol Server is out of Sync."
    ::= { sonusCpNtpServicesMIBNotificationsPrefix 6 }

sonusCpNtpServerInSyncNotification NOTIFICATION-TYPE
    OBJECTS         { sonusAlarmNodeID, sonusAlarmLevel, 
                      sonusAlarmSequenceId, sonusAlarmTime, 
                      sonusAlarmDescription, sonusCpSystemServerName, 
                      sonusCpNtpIpAddress }
    STATUS          current
    DESCRIPTION     
            "This trap indicates that a Network Timing Protocol Server is in Sync."
    ::= { sonusCpNtpServicesMIBNotificationsPrefix 7 }

sonusCpNtpServerReachableNotification NOTIFICATION-TYPE
    OBJECTS         { sonusAlarmNodeID, sonusAlarmLevel, 
                      sonusAlarmSequenceId, sonusAlarmTime, 
                      sonusAlarmDescription, sonusCpSystemServerName, 
                      sonusCpNtpIpAddress }
    STATUS          current
    DESCRIPTION     
            "This trap indicates that a Network Timing Protocol Server is Reachable."
    ::= { sonusCpNtpServicesMIBNotificationsPrefix 8 }

sonusCpRedundGroupSwitchOverNotification NOTIFICATION-TYPE
    OBJECTS         { sonusAlarmNodeID, sonusAlarmLevel, 
                      sonusAlarmSequenceId, sonusAlarmTime, 
                      sonusAlarmDescription, sonusCpSystemServerName, 
                      sonusCpRedundPrevActiveServerName, 
                      sonusCpRedundancyServicesGroupName }
    STATUS          current
    DESCRIPTION     
            "This trap indicates a server module redundancy switchover has occurred.
             The standby server module has become active.  
             The previous active server module, and group
             information are included.  For 1+1 the redundancy model, there
             is no group name."
    ::= { sonusCpRedundancyServicesMIBNotificationsPrefix 1 }

sonusCpRedundGroupNoRedundancyNotification NOTIFICATION-TYPE
    OBJECTS         { sonusAlarmNodeID, sonusAlarmLevel, 
                      sonusAlarmSequenceId, sonusAlarmTime, 
                      sonusAlarmDescription, 
                      sonusCpRedundancyServicesGroupName }
    STATUS          current
    DESCRIPTION     
            "This trap indicates that the specified redundancy group has
             no redundancy protection."
    ::= { sonusCpRedundancyServicesMIBNotificationsPrefix 2 }

sonusCpRedundGroupFullRedundancyNotification NOTIFICATION-TYPE
    OBJECTS         { sonusAlarmNodeID, sonusAlarmLevel, 
                      sonusAlarmSequenceId, sonusAlarmTime, 
                      sonusAlarmDescription, 
                      sonusCpRedundancyServicesGroupName }
    STATUS          current
    DESCRIPTION     
            "This trap indicates that the specified redundancy group has
             full redundancy protection."
    ::= { sonusCpRedundancyServicesMIBNotificationsPrefix 3 }

sonusCpSoftwareUpgradeInitiatedNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that a software upgrade 
             has been initiated."
    ::= { sonusCpSoftwareUpgradeServicesMIBNotificationsPrefix 1 }

sonusCpSoftwareUpgradeTerminatedNotification NOTIFICATION-TYPE
    OBJECTS         { sonusAlarmNodeID, sonusAlarmLevel, 
                      sonusAlarmSequenceId, sonusAlarmTime, 
                      sonusAlarmDescription, 
                      sonusSystemSoftwareUpgradeStatusReason }
    STATUS          current
    DESCRIPTION     
            "This trap indicates that a software upgrade has terminated 
             for the specified reason."
    ::= { sonusCpSoftwareUpgradeServicesMIBNotificationsPrefix 2 }

sonusCpSoftwareUpgradeSucceededNotification NOTIFICATION-TYPE
    OBJECTS         { sonusAlarmNodeID, sonusAlarmLevel, 
                      sonusAlarmSequenceId, sonusAlarmTime, 
                      sonusAlarmDescription, 
                      sonusSystemSoftwareUpgradeStatusReason }
    STATUS          current
    DESCRIPTION     
            "This trap indicates that a software upgrade has succeeded
             for the specified reason."
    ::= { sonusCpSoftwareUpgradeServicesMIBNotificationsPrefix 3 }

sonusCpSoftwareUpgradeRevertNotification NOTIFICATION-TYPE
    OBJECTS         { sonusAlarmNodeID, sonusAlarmLevel, 
                      sonusAlarmSequenceId, sonusAlarmTime, 
                      sonusAlarmDescription }
    STATUS          current
    DESCRIPTION     
            "This trap indicates that a Live Software Upgrade
             revert to the previous release has occured."
    ::= { sonusCpSoftwareUpgradeServicesMIBNotificationsPrefix 4 }

sonusCpSoftwareUpgradeCommitRequiredNotification NOTIFICATION-TYPE
    OBJECTS         { sonusAlarmNodeID, sonusAlarmLevel, 
                      sonusAlarmSequenceId, sonusAlarmTime, 
                      sonusAlarmDescription, 
                      sonusSystemSoftwareUpgradeOldRelease, 
                      sonusSystemSoftwareUpgradeNewRelease }
    STATUS          current
    DESCRIPTION     
            "This trap indicates that Live Software Upgrade
             commit is pending. This trap is not applicable in the SGX4000."
    ::= { sonusCpSoftwareUpgradeServicesMIBNotificationsPrefix 5 }

sonusCpSoftwareUpgradeCommittedNotification NOTIFICATION-TYPE
    OBJECTS         { sonusAlarmNodeID, sonusAlarmLevel, 
                      sonusAlarmSequenceId, sonusAlarmTime, 
                      sonusAlarmDescription, 
                      sonusSystemSoftwareUpgradeOldRelease, 
                      sonusSystemSoftwareUpgradeNewRelease }
    STATUS          current
    DESCRIPTION     
            "This trap indicates that Live Software Upgrade is committed. This trap is not applicable in the SGX4000."
    ::= { sonusCpSoftwareUpgradeServicesMIBNotificationsPrefix 6 }

sonusCpEventLogFileStateNotification NOTIFICATION-TYPE
    OBJECTS         { sonusAlarmNodeID, sonusAlarmLevel, 
                      sonusAlarmSequenceId, sonusAlarmTime, 
                      sonusAlarmDescription, sonusCpEventLogType, 
                      sonusCpEvLogAdminState }
    STATUS          current
    DESCRIPTION     
            "This trap indicates the current state of event file logging."
    ::= { sonusCpEventLogMIBNotificationsPrefix 1 }

sonusCpEventLogFileCreatedNotification NOTIFICATION-TYPE
    OBJECTS         { sonusAlarmNodeID, sonusAlarmLevel, 
                      sonusAlarmSequenceId, sonusAlarmTime, 
                      sonusAlarmDescription, sonusCpEventLogType, 
                      sonusEventLogTypeStatusCurrentFile }
    STATUS          current
    DESCRIPTION     
            "This trap indicates the name of the event file which has been created for logging."
    ::= { sonusCpEventLogMIBNotificationsPrefix 2 }

sonusCpEventLogFileRestartNotification NOTIFICATION-TYPE
    OBJECTS         { sonusAlarmNodeID, sonusAlarmLevel, 
                      sonusAlarmSequenceId, sonusAlarmTime, 
                      sonusAlarmDescription, sonusCpEventLogType }
    STATUS          current
    DESCRIPTION     
            "This trap indicates that file event logging has been automatically restarted."
    ::= { sonusCpEventLogMIBNotificationsPrefix 3 }

sonusCpEventLogFileClosedNotification NOTIFICATION-TYPE
    OBJECTS         { sonusAlarmNodeID, sonusAlarmLevel, 
                      sonusAlarmSequenceId, sonusAlarmTime, 
                      sonusAlarmDescription, sonusCpEventLogType, 
                      sonusEventLogTypeStatusCurrentFile }
    STATUS          current
    DESCRIPTION     
            "This trap indicates the name of the event file which has been closed."
    ::= { sonusCpEventLogMIBNotificationsPrefix 4 }

sonusCpEventLogFileShutdownNotification NOTIFICATION-TYPE
    OBJECTS         { sonusAlarmNodeID, sonusAlarmLevel, 
                      sonusAlarmSequenceId, sonusAlarmTime, 
                      sonusAlarmDescription, sonusCpEventLogType, 
                      sonusCpEvLogShutdownReason, sonusCpEvLogAdminState }
    STATUS          current
    DESCRIPTION     
            "This trap indicates that a shutdown of file event logging has occurred."
    ::= { sonusCpEventLogMIBNotificationsPrefix 5 }

sonusCpEventLogFileCountNotification NOTIFICATION-TYPE
    OBJECTS         { sonusAlarmNodeID, sonusAlarmLevel, 
                      sonusAlarmSequenceId, sonusAlarmTime, 
                      sonusAlarmDescription, sonusEvLogTypeName, 
                      sonusCpEvLogFilePercentage, 
                      sonusCpEvLogCurFileCount, 
                      sonusEventLogTypeAdminFileCount }
    STATUS          current
    DESCRIPTION     
            "This trap indicates that the number of event log files is approaching the configured maximum."
    ::= { sonusCpEventLogMIBNotificationsPrefix 6 }

sonusCpEventLogFileCountChngNotification NOTIFICATION-TYPE
    OBJECTS         { sonusAlarmNodeID, sonusAlarmLevel, 
                      sonusAlarmSequenceId, sonusAlarmTime, 
                      sonusAlarmDescription, sonusCpEventLogType, 
                      sonusEventLogTypeAdminFileCount }
    STATUS          current
    DESCRIPTION     
            "This trap indicates the number of Event Log files that will be maintained for this event type is changed"
    ::= { sonusCpEventLogMIBNotificationsPrefix 7 }

sonusCpEventLogFileSizeChngNotification NOTIFICATION-TYPE
    OBJECTS         { sonusAlarmNodeID, sonusAlarmLevel, 
                      sonusAlarmSequenceId, sonusAlarmTime, 
                      sonusAlarmDescription, sonusCpEventLogType, 
                      sonusEventLogTypeAdminFileSize }
    STATUS          current
    DESCRIPTION     
            "This trap indicates that the maximum size of a single event log file has changed."
    ::= { sonusCpEventLogMIBNotificationsPrefix 8 }

sonusCpEventLogFileMsgQueueChngNotification NOTIFICATION-TYPE
    OBJECTS         { sonusAlarmNodeID, sonusAlarmLevel, 
                      sonusAlarmSequenceId, sonusAlarmTime, 
                      sonusAlarmDescription, sonusCpEventLogType, 
                      sonusEventLogTypeAdminMessageQueueSize }
    STATUS          current
    DESCRIPTION     
            "This trap indicates that the number event log message entries to the buffer changed"
    ::= { sonusCpEventLogMIBNotificationsPrefix 9 }

sonusCpEventLogSaveToChngNotification NOTIFICATION-TYPE
    OBJECTS         { sonusAlarmNodeID, sonusAlarmLevel, 
                      sonusAlarmSequenceId, sonusAlarmTime, 
                      sonusAlarmDescription, sonusCpEventLogType, 
                      sonusEventLogTypeAdminSaveTo }
    STATUS          current
    DESCRIPTION     
            "This Trap indicates that the location where events are saved is being changed "
    ::= { sonusCpEventLogMIBNotificationsPrefix 10 }

sonusCpEventLogFileMaxEventMemSizeChngNotification NOTIFICATION-TYPE
    OBJECTS         { sonusAlarmNodeID, sonusAlarmLevel, 
                      sonusAlarmSequenceId, sonusAlarmTime, 
                      sonusAlarmDescription, sonusCpEventLogType, 
                      sonusEventLogTypeAdminMaxEventMemorySize }
    STATUS          current
    DESCRIPTION     
            "This trap indicates that the maximum size of the memory event log buffer is changed"
    ::= { sonusCpEventLogMIBNotificationsPrefix 11 }

sonusCpEventLogFileFilterLevelChngNotification NOTIFICATION-TYPE
    OBJECTS         { sonusAlarmNodeID, sonusAlarmLevel, 
                      sonusAlarmSequenceId, sonusAlarmTime, 
                      sonusAlarmDescription, sonusCpEventLogType, 
                      sonusEventLogTypeAdminFilterLevel }
    STATUS          current
    DESCRIPTION     
            "This trap indicates that the level of event logging for this event type is changed"
    ::= { sonusCpEventLogMIBNotificationsPrefix 12 }

sonusCpEventLogDirectoryCreateErrorNotification NOTIFICATION-TYPE
    OBJECTS         { sonusAlarmNodeID, sonusAlarmLevel, 
                      sonusAlarmSequenceId, sonusAlarmTime, 
                      sonusAlarmDescription, sonusCpEventLogType, 
                      sonusCpEvLogDirName, sonusCpEvLogErrorCode }
    STATUS          current
    DESCRIPTION     
            "This trap indicates that the inability of the system to create a directory for event logging.
             This could also indicate an generic error with the NFS server."
    ::= { sonusCpEventLogMIBNotificationsPrefix 13 }

sonusCpEventLogRolloverScheduledNotification NOTIFICATION-TYPE
    OBJECTS         { sonusAlarmNodeID, sonusAlarmLevel, 
                      sonusAlarmSequenceId, sonusAlarmTime, 
                      sonusAlarmDescription, sonusCpEventLogType }
    STATUS          current
    DESCRIPTION     
            "This trap indicates that event log for this log type is scheduled to rollover."
    ::= { sonusCpEventLogMIBNotificationsPrefix 14 }

sonusCpEventLogRolloverStoppedNotification NOTIFICATION-TYPE
    OBJECTS         { sonusAlarmNodeID, sonusAlarmLevel, 
                      sonusAlarmSequenceId, sonusAlarmTime, 
                      sonusAlarmDescription, sonusCpEventLogType }
    STATUS          current
    DESCRIPTION     
            "This trap indicates that event log rollover for this log type is stopped."
    ::= { sonusCpEventLogMIBNotificationsPrefix 15 }

sonusCpEventLogRolloverFastNotification NOTIFICATION-TYPE
    OBJECTS         { sonusAlarmNodeID, sonusAlarmLevel, 
                      sonusAlarmSequenceId, sonusAlarmTime, 
                      sonusAlarmDescription, sonusEvLogTypeName }
    STATUS          current
    DESCRIPTION     
            "This trap indicates that event log rollover is occuring frequently."
    ::= { sonusCpEventLogMIBNotificationsPrefix 16 }

sonusCpEventLogFileCountClearedNotification NOTIFICATION-TYPE
    OBJECTS         { sonusAlarmNodeID, sonusAlarmLevel, 
                      sonusAlarmSequenceId, sonusAlarmTime, 
                      sonusAlarmDescription, sonusEvLogTypeName, 
                      sonusCpEvLogFilePercentage, 
                      sonusCpEvLogCurFileCount, 
                      sonusEventLogTypeAdminFileCount }
    STATUS          current
    DESCRIPTION     
            "This trap indicates that the number of event log files has dropped below the either the 100% or 75% threshold"
    ::= { sonusCpEventLogMIBNotificationsPrefix 17 }

sonusCpEventLogFileSkipped NOTIFICATION-TYPE
    OBJECTS         { sonusAlarmNodeID, sonusAlarmLevel, 
                      sonusAlarmSequenceId, sonusAlarmTime, 
                      sonusAlarmDescription, sonusCpEventLogType, 
                      sonusEventLogTypeStatusCurrentFile }
    STATUS          current
    DESCRIPTION     
            "This trap indicates the name of the event file which has been skipped because of file errors."
    ::= { sonusCpEventLogMIBNotificationsPrefix 18 }

sonusCpEventLogFileDeletedNotification NOTIFICATION-TYPE
    OBJECTS         { sonusAlarmNodeID, sonusAlarmLevel, 
                      sonusAlarmSequenceId, sonusAlarmTime, 
                      sonusAlarmDescription, sonusCpEventLogType, 
                      sonusEventLogTypeStatusCurrentFile }
    STATUS          current
    DESCRIPTION     
            "This trap indicates that an accountng file has been deleted because the maximum file count has been reached."
    ::= { sonusCpEventLogMIBNotificationsPrefix 19 }

sonusCpEventMgrAlarmManualClear NOTIFICATION-TYPE
    OBJECTS         { sonusAlarmNodeID, sonusAlarmLevel, 
                      sonusAlarmSequenceId, sonusAlarmTime, 
                      sonusAlarmDescription, sonusAlarmMgrId }
    STATUS          current
    DESCRIPTION     
            "This trap indicates that an alarm has been manually cleared. This trap is not applicable in the SGX4000."
    ::= { sonusCpEventLogMIBNotificationsPrefix 20 }

sonusCpEventLogFileRenamedNotification NOTIFICATION-TYPE
    OBJECTS         { sonusAlarmNodeID, sonusAlarmLevel, 
                      sonusAlarmSequenceId, sonusAlarmTime, 
                      sonusAlarmDescription, sonusCpEventLogType, 
                      sonusEventLogTypeStatusCurrentFile, 
                      sonusEventLogRenameToFile }
    STATUS          current
    DESCRIPTION     
            "This trap indicates that an accountng file has been renamed to remove the open file extension. This trap is not applicable in the SGX4000."
    ::= { sonusCpEventLogMIBNotificationsPrefix 21 }

sonusCpSystemBootNotification NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node boot is requested."
    ::= { sonusCpSystemServicesMIBNotificationsPrefix 1 }

sonusCpSystemBootActiveNotification NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node is active after a reboot."
    ::= { sonusCpSystemServicesMIBNotificationsPrefix 2 }

sonusCpSystemSoftBootNotification NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node soft boot is requested."
    ::= { sonusCpSystemServicesMIBNotificationsPrefix 3 }

sonusCpSystemSoftBootActiveNotification NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node is active after a soft reboot."
    ::= { sonusCpSystemServicesMIBNotificationsPrefix 4 }

sonusCpSystemLocalDiskAvailableNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that a hard disk of a server is available."
    ::= { sonusCpSystemServicesMIBNotificationsPrefix 5 }

sonusCpSystemLocalDiskBadVolumeNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that bad volume is detected on hard disk of a server. This trap is not applicable in the SGX4000."
    ::= { sonusCpSystemServicesMIBNotificationsPrefix 6 }

sonusCpSystemLocalDiskMisMatchNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that an incorrect hard disk is inserted on a server. This trap is not applicable in the SGX4000."
    ::= { sonusCpSystemServicesMIBNotificationsPrefix 7 }

sonusCpSystemLocalDiskSpaceOkNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
    STATUS          current
    DESCRIPTION     
            "This trap indicates that space on the hard disk in with in the limits of normal operation."
    ::= { sonusCpSystemServicesMIBNotificationsPrefix 8 }

sonusCpSystemLocalDiskSpaceReadOnlyNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that space on the hard disk is low and no more data can be written and operating in read only mode. This trap is not applicable in the SGX4000."
    ::= { sonusCpSystemServicesMIBNotificationsPrefix 9 }

sonusCpSystemLocalDiskSpaceWarningNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber, 
                      sonusCpSystemDiskPartition, 
                      sonusCpSystemDiskSpaceUsedPct }
    STATUS          current
    DESCRIPTION     
            "This trap indicates that space on the hard disk is low."
    ::= { sonusCpSystemServicesMIBNotificationsPrefix 10 }

sonusCpSystemLocalDiskTooManyFilesNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that there are too many files on the hard disk."
    ::= { sonusCpSystemServicesMIBNotificationsPrefix 11 }

sonusCpSystemLocalDiskUnavailableNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that a hard disk is unavailable on the indicated server."
    ::= { sonusCpSystemServicesMIBNotificationsPrefix 12 }

sonusCpSystemLocalDiskWritableNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that space on a hard disk is above normal limit and disk is now writable. This trap is not applicable in the SGX4000."
    ::= { sonusCpSystemServicesMIBNotificationsPrefix 13 }

sonusCpSystemLocalDiskSyncStartNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that a hard disk synchronization is started on a server."
    ::= { sonusCpSystemServicesMIBNotificationsPrefix 14 }

sonusCpSystemLocalDiskSyncCompleteNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that a hard disk synchronization is completed on a server."
    ::= { sonusCpSystemServicesMIBNotificationsPrefix 15 }

sonusCpSystemCEDisabledNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a Server is disabled. This trap is not applicable in the SGX4000."
    ::= { sonusCpSystemServicesMIBNotificationsPrefix 16 }

sonusCpSystemCEEnabledNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a Server is enabled. This trap is not applicable in the SGX4000."
    ::= { sonusCpSystemServicesMIBNotificationsPrefix 17 }

sonusCpSystemCEOperationalNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a Server is operational."
    ::= { sonusCpSystemServicesMIBNotificationsPrefix 18 }

sonusCpSystemCEBootNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the CE/server boot is requested."
    ::= { sonusCpSystemServicesMIBNotificationsPrefix 19 }

sonusCpSystemCEBootActiveNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the CE/server is active after a reboot."
    ::= { sonusCpSystemServicesMIBNotificationsPrefix 20 }

sonusCpSystemCESoftBootNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the CE/server soft boot is requested."
    ::= { sonusCpSystemServicesMIBNotificationsPrefix 21 }

sonusCpSystemCESoftBootActiveNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the CE/server is active after a soft reboot."
    ::= { sonusCpSystemServicesMIBNotificationsPrefix 22 }

sonusCpSystemCETempFailureNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
    STATUS          current
    DESCRIPTION     
            "This trap indicates that the CE/server temperature is higher than normal."
    ::= { sonusCpSystemServicesMIBNotificationsPrefix 23 }

sonusCpSystemCETempNormalNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
    STATUS          current
    DESCRIPTION     
            "This trap indicates that the CE/server temperature is normal."
    ::= { sonusCpSystemServicesMIBNotificationsPrefix 24 }

sonusCpSystemCETempWarningNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemServerTemperatureSensorId, 
                      sonusCpSystemServerTemperature }
    STATUS          current
    DESCRIPTION     
            "This trap indicates that the CE/server temperature is reaching critical level."
    ::= { sonusCpSystemServicesMIBNotificationsPrefix 25 }

sonusCpConfigCommitSucceedNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a configuration commit has suceeded."
    ::= { sonusCpSystemServicesMIBNotificationsPrefix 26 }

sonusCpConfigCommitFailNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a configuration commit has failed."
    ::= { sonusCpSystemServicesMIBNotificationsPrefix 27 }

sonusCpSystemAllHardDisksFailedNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that all the hard disks are unavailable on the indicated server."
    ::= { sonusCpSystemServicesMIBNotificationsPrefix 28 }

sonusCpSystemProcessCoredumpGeneratedNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemCoredumpFile }
    STATUS          current
    DESCRIPTION     
            "This trap indicates that a coredump is generated for a process running on the indicated server."
    ::= { sonusCpSystemServicesMIBNotificationsPrefix 36 }

sonusCpSystemCoredumpSpaceWarningNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemCoredumpSpacePct }
    STATUS          current
    DESCRIPTION     
            "This trap indicates that a system is running low on coredump space."
    ::= { sonusCpSystemServicesMIBNotificationsPrefix 37 }

sonusCpNodeStandbyDisabled NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node standby server is disabled. This trap is not applicable in the SGX4000."
    ::= { sonusCpSystemServicesMIBNotificationsPrefix 38 }

sonusCpNodeStandbyEnabled NOTIFICATION-TYPE
    OBJECTS         { sonusAlarmNodeID, sonusAlarmLevel, 
                      sonusAlarmSequenceId, sonusAlarmTime, 
                      sonusAlarmDescription, sonusCpSystemAdminName }
    STATUS          current
    DESCRIPTION     
            "This trap indicates that the node standby server is enabled. This trap is not applicable in the SGX4000."
    ::= { sonusCpSystemServicesMIBNotificationsPrefix 39 }

sonusCpNodeHaPortDownNotification NOTIFICATION-TYPE
    OBJECTS         { sonusAlarmNodeID, sonusAlarmLevel, 
                      sonusAlarmSequenceId, sonusAlarmTime, 
                      sonusAlarmDescription, sonusCpSystemServerName, 
                      sonusCpSystemPortName }
    STATUS          deprecated
    DESCRIPTION     
            "This trap indicates that a high availability port is down. This trap is not applicable in the SGX4000."
    ::= { sonusCpSystemServicesMIBNotificationsPrefix 40 }

sonusCpNodeHaPortUpNotification NOTIFICATION-TYPE
    OBJECTS         { sonusAlarmNodeID, sonusAlarmLevel, 
                      sonusAlarmSequenceId, sonusAlarmTime, 
                      sonusAlarmDescription, sonusCpSystemServerName, 
                      sonusCpSystemPortName }
    STATUS          current
    DESCRIPTION     
            "This trap indicates that a high availability port is up. This trap is not applicable in the SGX4000."
    ::= { sonusCpSystemServicesMIBNotificationsPrefix 41 }

sonusCpNodeBondingDeviceDownNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the bonding device is down. This trap is not applicable in the SGX4000."
    ::= { sonusCpSystemServicesMIBNotificationsPrefix 42 }

sonusCpNodeBondingDeviceUpNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the bonding device is up. This trap is not applicable in the SGX4000."
    ::= { sonusCpSystemServicesMIBNotificationsPrefix 43 }

sonusCpNodeHaPortDownNewNotification NOTIFICATION-TYPE
    OBJECTS         { sonusAlarmNodeID, sonusAlarmLevel, 
                      sonusAlarmSequenceId, sonusAlarmTime, 
                      sonusAlarmDescription, sonusCpSystemServerName, 
                      sonusCpSystemPortName }
    STATUS          current
    DESCRIPTION     
            "This trap indicates that a high availability port is down. This trap is not applicable in the SGX4000."
    ::= { sonusCpSystemServicesMIBNotificationsPrefix 44 }

sonusCpSystemLocalRaidArrayDegradedNotification NOTIFICATION-TYPE
    OBJECTS         { sonusAlarmNodeID, sonusAlarmLevel, 
                      sonusAlarmSequenceId, sonusAlarmTime, 
                      sonusAlarmDescription, sonusCpSystemAdminName, 
                      sonusCpSystemServerName, 
                      sonusCpSystemHardDiskNumber }
    STATUS          current
    DESCRIPTION     
            "This trap indicates that the RAID array has degraded due to a failure on the specified disk."
    ::= { sonusCpSystemServicesMIBNotificationsPrefix 45 }

sonusCpSystemRestoreConfigNotification NOTIFICATION-TYPE
    OBJECTS         { sonusAlarmNodeID, sonusAlarmLevel, 
                      sonusAlarmSequenceId, sonusAlarmTime, 
                      sonusAlarmDescription, sonusCpSystemAdminName, 
                      sonusCpSystemConfigFileName }
    STATUS          current
    DESCRIPTION     
            "This trap indicates that the configuration restoration from specified config file is in progress."
    ::= { sonusCpSystemServicesMIBNotificationsPrefix 46 }

sonusCpSystemNotMacAddressOwnerNotification NOTIFICATION-TYPE
    OBJECTS         { sonusAlarmNodeID, sonusAlarmLevel, 
                      sonusAlarmSequenceId, sonusAlarmTime, 
                      sonusAlarmDescription, sonusCpSelfBaseMacAddress, 
                      sonusCpPeerBaseMacAddress, 
                      sonusCpActiveBaseMacAddress }
    STATUS          current
    DESCRIPTION     
            "This trap indicates that the system is running with a set of MAC addresses that doesn't belog to this system. This is possible if a server is replaced. This trap is not applicable in the SGX4000."
    ::= { sonusCpSystemServicesMIBNotificationsPrefix 47 }

sonusSystemNodeResourceCongestionWarningNotification NOTIFICATION-TYPE
    OBJECTS         { sonusAlarmNodeID, sonusAlarmLevel, 
                      sonusAlarmSequenceId, sonusAlarmTime, 
                      sonusAlarmDescription, sonusNodeOverloadType, 
                      sonusNodeOverloadLevel, 
                      sonusNodeOverloadThresholdCurrent, 
                      sonusNodeOverloadThresholdConfigured }
    STATUS          current
    DESCRIPTION     
            "This trap indicates that the system is running out of memory and will soon reboot. This trap is not applicable in the SGX4000."
    ::= { sonusCpSystemServicesMIBNotificationsPrefix 48 }

sonusCpSystemProductCapabalityMismatch NOTIFICATION-TYPE
    OBJECTS         { sonusAlarmNodeID, sonusAlarmLevel, 
                      sonusAlarmSequenceId, sonusAlarmTime, 
                      sonusAlarmDescription, sonusCpSystemServerName, 
                      sonusCpProductCapabilityName, 
                      sonusCpProductCapabilityValue, 
                      sonusCpProductPeerCapabilityValue }
    STATUS          current
    DESCRIPTION     
            "This trap indicates that the specified server is running with a product capability that is not compatible with the peer capabilities. This trap is not applicable in the SGX4000."
    ::= { sonusCpSystemServicesMIBNotificationsPrefix 49 }

sonusSystemNodeResourceClearCongestionWarningNotification NOTIFICATION-TYPE
    OBJECTS         { sonusAlarmNodeID, sonusAlarmLevel, 
                      sonusAlarmSequenceId, sonusAlarmTime, 
                      sonusAlarmDescription, sonusNodeOverloadType, 
                      sonusNodeOverloadLevel, 
                      sonusNodeOverloadThresholdCurrent, 
                      sonusNodeOverloadThresholdConfigured }
    STATUS          current
    DESCRIPTION     
            "This trap indicates that the system has fallen below the memory threshold. This trap is not applicable in the SGX4000."
    ::= { sonusCpSystemServicesMIBNotificationsPrefix 50 }

sonusCpSystemLocalDiskHealthErrorNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemHardDiskName, 
                      sonusCpSystemHardDiskError, 
                      sonusCpSystemLifeAvailAttrib }
    STATUS          current
    DESCRIPTION     
            "This trap indicates that the system received an error from  Self-Monitoring, Analysis and Reporting Technology (SMART) which is built into many hard drives. Not applicable to SGX4000."
    ::= { sonusCpSystemServicesMIBNotificationsPrefix 51 }

sonusCpSystemLocalDiskHealthErrorClearNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemHardDiskName, 
                      sonusCpSystemLifeAvailAttrib }
    STATUS          current
    DESCRIPTION     
            "This trap indicates that the system cleared an error cleared from Self-Monitoring, Analysis and Reporting Technology (SMART) which is built into many hard drives. Not applicable to SGX4000."
    ::= { sonusCpSystemServicesMIBNotificationsPrefix 52 }

sonusCpSystemLocalDiskLifeAttribErrorNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemHardDiskName, 
                      sonusCpSystemHardDiskError, 
                      sonusCpSystemLifeAvailAttrib }
    STATUS          current
    DESCRIPTION     
            "This trap indicates that the system received a life remaining threshold exceeded event from  Self-Monitoring, Analysis and Reporting Technology (SMART) which is built into many hard drives. Not applicable to SGX4000."
    ::= { sonusCpSystemServicesMIBNotificationsPrefix 53 }

sonusCpSystemLocalDiskLifeAttribErrorClearNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemHardDiskName, 
                      sonusCpSystemLifeAvailAttrib }
    STATUS          current
    DESCRIPTION     
            "This trap indicates that the system cleared life remaining threshold alarm from Self-Monitoring, Analysis and Reporting Technology (SMART) which is built into many hard drives. Not applicable to SGX4000."
    ::= { sonusCpSystemServicesMIBNotificationsPrefix 54 }

sonusSystemServerLinksDryupNotification NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the links for the specified server has dried up. Applicable to SGX4000 only."
    ::= { sonusCpSystemServicesMIBNotificationsPrefix 55 }

sonusCpSystemMemoryUsageWarningNotification NOTIFICATION-TYPE
    OBJECTS         { sonusAlarmNodeID, sonusAlarmLevel, 
                      sonusAlarmSequenceId, sonusAlarmTime, 
                      sonusAlarmDescription, sonusCpSystemAdminName, 
                      sonusCpSystemServerName, sonusCpSystemMemoryUsage }
    STATUS          current
    DESCRIPTION     
            "This trap indicates that the system memory usage is high. Applicable to SGX4000 only"
    ::= { sonusCpSystemServicesMIBNotificationsPrefix 57 }

sonusCpSystemMemoryUsageOkNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the system memory usage is at a safe level. Applicable to SGX4000 only"
    ::= { sonusCpSystemServicesMIBNotificationsPrefix 58 }

sonusCpConfigHaSlaveDied NOTIFICATION-TYPE
    OBJECTS         { sonusAlarmNodeID, sonusAlarmLevel, 
                      sonusAlarmSequenceId, sonusAlarmTime, 
                      sonusAlarmDescription }
    STATUS          current
    DESCRIPTION     
            "This trap indicates that the management active CE is no longer able to communicate configuration changes to the standby. Applicable to SGX4000 only."
    ::= { sonusCpSystemServicesMIBNotificationsPrefix 59 }

sonusCpSystemMemoryModuleFaultNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          obsolete
    DESCRIPTION     
            "This trap indicates that a server memory module maybe faulty. Applicable to SGX4000 only."
    ::= { sonusCpSystemServicesMIBNotificationsPrefix 60 }

sonusCpSystemReadonlyFileSystemNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          obsolete
    DESCRIPTION     
            "This trap indicates that the file system has gone into a read only state and nothing can be written to disk. Applicable to SGX4000 only."
    ::= { sonusCpSystemServicesMIBNotificationsPrefix 61 }

sonusCpSystemFaultyHardDiskNotification NOTIFICATION-TYPE
    OBJECTS         { sonusAlarmNodeID, sonusAlarmLevel, 
                      sonusAlarmSequenceId, sonusAlarmTime, 
                      sonusAlarmDescription, sonusCpSystemAdminName, 
                      sonusCpSystemServerName }
    STATUS          obsolete
    DESCRIPTION     
            "This trap indicates that a hard disk maybe faulty. Applicable to SGX4000 only."
    ::= { sonusCpSystemServicesMIBNotificationsPrefix 62 }

sonusCpConfigHaInSync NOTIFICATION-TYPE
    OBJECTS         { sonusAlarmNodeID, sonusAlarmLevel, 
                      sonusAlarmSequenceId, sonusAlarmTime, 
                      sonusAlarmDescription }
    STATUS          obsolete
    DESCRIPTION     
            "This trap indicates that the management active CE is in sync with the standby for configuration changes."
    ::= { sonusCpSystemServicesMIBNotificationsPrefix 63 }

sonusCpSystemCriticalUserEvent NOTIFICATION-TYPE
    OBJECTS         { sonusAlarmNodeID, sonusAlarmLevel, 
                      sonusAlarmSequenceId, sonusAlarmTime, 
                      sonusAlarmDescription, sonusCpSystemUserString }
    STATUS          obsolete
    DESCRIPTION     
            "This trap is the user generated critical severity trap."
    ::= { sonusCpSystemServicesMIBNotificationsPrefix 64 }

sonusCpSystemMajorUserEvent NOTIFICATION-TYPE
    OBJECTS         { sonusAlarmNodeID, sonusAlarmLevel, 
                      sonusAlarmSequenceId, sonusAlarmTime, 
                      sonusAlarmDescription, sonusCpSystemUserString }
    STATUS          current
    DESCRIPTION     
            "This trap is the user generated major severity trap.This trap is only applicable for SGX4000."
    ::= { sonusCpSystemServicesMIBNotificationsPrefix 65 }

sonusCpSystemMinorUserEvent NOTIFICATION-TYPE
    OBJECTS         { sonusAlarmNodeID, sonusAlarmLevel, 
                      sonusAlarmSequenceId, sonusAlarmTime, 
                      sonusAlarmDescription, sonusCpSystemUserString }
    STATUS          current
    DESCRIPTION     
            "This trap is the user generated minor severity trap.This trap is only applicable for SGX4000."
    ::= { sonusCpSystemServicesMIBNotificationsPrefix 66 }

sonusCpSystemInfoUserEvent NOTIFICATION-TYPE
    OBJECTS         { sonusAlarmNodeID, sonusAlarmLevel, 
                      sonusAlarmSequenceId, sonusAlarmTime, 
                      sonusAlarmDescription, sonusCpSystemUserString }
    STATUS          current
    DESCRIPTION     
            "This trap is the user generated info severity trap.This trap is only applicable for SGX4000."
    ::= { sonusCpSystemServicesMIBNotificationsPrefix 67 }

sonusCpSystemServerDrbdReformatStartNotify NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the drbd partition is being resized and reformatted to match the peer partition, this trap is only applicable for SBX"
    ::= { sonusCpSystemServicesMIBNotificationsPrefix 68 }

sonusCpSystemServerDrbdReformatSwitchoverNotify NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the active server has requested the standby to become active, allowing the current active to reconfigure its drbd partition, this trap is only applicable for SBX"
    ::= { sonusCpSystemServicesMIBNotificationsPrefix 69 }

sonusCpSystemServerDrbdReformatErrorNotify NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the drbd process encountered an error during reconfiguration, this trap is only applicable for SBX"
    ::= { sonusCpSystemServicesMIBNotificationsPrefix 70 }

sonusCpSystemServerDrbdReformatBackupNotify NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the drbd process is backing up configuration and accounting files in preparation for a drbd partition reformat, this trap is only applicable for SBX"
    ::= { sonusCpSystemServicesMIBNotificationsPrefix 71 }

sonusCpSystemServerDrbdReformatCompletedNotify NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates drbd partition format has completed. A full disk sync will start, this trap is only applicable for SBX"
    ::= { sonusCpSystemServicesMIBNotificationsPrefix 72 }

sonusCpSystemMemoryModuleFaultNotify NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a server memory module maybe faulty, specific to SGX4000 only."
    ::= { sonusCpSystemServicesMIBNotificationsPrefix 73 }

sonusCpSystemReadonlyFileSystemNotify NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that the file system has gone into a read only state and nothing can be written to disk, specific to SGX4000 only."
    ::= { sonusCpSystemServicesMIBNotificationsPrefix 74 }

sonusCpSystemFaultyHardDiskNotify NOTIFICATION-TYPE
    OBJECTS         { sonusAlarmNodeID, sonusAlarmLevel, 
                      sonusAlarmSequenceId, sonusAlarmTime, 
                      sonusAlarmDescription, sonusCpSystemAdminName, 
                      sonusCpSystemServerName }
    STATUS          current
    DESCRIPTION     
            "This trap indicates that a hard disk maybe faulty,  specific to SGX4000 only."
    ::= { sonusCpSystemServicesMIBNotificationsPrefix 75 }

sonusCpConfigHaInSyncNotify NOTIFICATION-TYPE
    OBJECTS         { sonusAlarmNodeID, sonusAlarmLevel, 
                      sonusAlarmSequenceId, sonusAlarmTime, 
                      sonusAlarmDescription }
    STATUS          current
    DESCRIPTION     
            "This trap indicates that the management active CE is in sync with the standby for configuration changes, specific for SGX4000 only"
    ::= { sonusCpSystemServicesMIBNotificationsPrefix 76 }

sonusCpSystemCriticalUserEventNotify NOTIFICATION-TYPE
    OBJECTS         { sonusAlarmNodeID, sonusAlarmLevel, 
                      sonusAlarmSequenceId, sonusAlarmTime, 
                      sonusAlarmDescription, sonusCpSystemUserString }
    STATUS          obsolete
    DESCRIPTION     
            "This trap is the user generated critical severity trap, specific for SGX4000 only"
    ::= { sonusCpSystemServicesMIBNotificationsPrefix 77 }

sonusCpSystemCriticalUserEventNfy NOTIFICATION-TYPE
    OBJECTS         { sonusAlarmNodeID, sonusAlarmLevel, 
                      sonusAlarmSequenceId, sonusAlarmTime, 
                      sonusAlarmDescription, sonusCpSystemUserInfoString }
    STATUS          current
    DESCRIPTION     
            "This trap is the user generated critical severity trap. This trap is only applicable for SGX4000."
    ::= { sonusCpSystemServicesMIBNotificationsPrefix 81 }

sonusCpSystemMajorUserEventNfy NOTIFICATION-TYPE
    OBJECTS         { sonusAlarmNodeID, sonusAlarmLevel, 
                      sonusAlarmSequenceId, sonusAlarmTime, 
                      sonusAlarmDescription, sonusCpSystemUserInfoString }
    STATUS          current
    DESCRIPTION     
            "This trap is the user generated major severity trap. This trap is only applicable for SGX4000."
    ::= { sonusCpSystemServicesMIBNotificationsPrefix 82 }

sonusCpSystemMinorUserEventNfy NOTIFICATION-TYPE
    OBJECTS         { sonusAlarmNodeID, sonusAlarmLevel, 
                      sonusAlarmSequenceId, sonusAlarmTime, 
                      sonusAlarmDescription, sonusCpSystemUserInfoString }
    STATUS          current
    DESCRIPTION     
            "This trap is the user generated minor severity trap. This trap is only applicable for SGX4000."
    ::= { sonusCpSystemServicesMIBNotificationsPrefix 83 }

sonusCpSystemInfoUserEventNfy NOTIFICATION-TYPE
    OBJECTS         { sonusAlarmNodeID, sonusAlarmLevel, 
                      sonusAlarmSequenceId, sonusAlarmTime, 
                      sonusAlarmDescription, sonusCpSystemUserInfoString }
    STATUS          current
    DESCRIPTION     
            "This trap is the user generated info severity trap. This trap is only applicable for SGX4000."
    ::= { sonusCpSystemServicesMIBNotificationsPrefix 84 }

sonusCpSystemServiceRestartNotification NOTIFICATION-TYPE
    OBJECTS         { sonusAlarmNodeID, sonusAlarmLevel, 
                      sonusAlarmSequenceId, sonusAlarmTime, 
                      sonusAlarmDescription, sonusCpSystemServerName, 
                      sonusCpSystemApplicationRestartReason }
    STATUS          current
    DESCRIPTION     
            "This trap indicates the reason for the service restarting."
    ::= { sonusCpSystemServicesMIBNotificationsPrefix 85 }

sonusCpSystemSwitchoverIncompleteNotification NOTIFICATION-TYPE
    OBJECTS         { sonusAlarmNodeID, sonusAlarmLevel, 
                      sonusAlarmSequenceId, sonusAlarmTime, 
                      sonusAlarmDescription }
    STATUS          current
    DESCRIPTION     
            "This trap indicates indicates that this CE started to switchover but the process did not complete, leaving the system in an undefined state. This trap is only applicable for SGX4000."
    ::= { sonusCpSystemServicesMIBNotificationsPrefix 86 }

sonusCpNifCrcErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that CRC error rate has exceeded set threshold for the set duration. This trap is not applicable in the SGX4000."
    ::= { sonusCpNifMIBNotificationsPrefix 1 }

sonusCpNifCrcErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that CRC error rate gone below the clear threshold for the clear duration."
    ::= { sonusCpNifMIBNotificationsPrefix 2 }

sonusCpNifCodeViolationErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that code violation error rate has exceeded set threshold for the set duration. This trap is not applicable in the SGX4000."
    ::= { sonusCpNifMIBNotificationsPrefix 3 }

sonusCpNifCodeViolationErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that code violation error rate gone below the clear threshold for the clear duration. This trap is not applicable in the SGX4000."
    ::= { sonusCpNifMIBNotificationsPrefix 4 }

sonusCpMaxPacketLengthErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the maximum packet length error rate has exceeded set threshold for the set duration. This trap is not applicable in the SGX4000."
    ::= { sonusCpNifMIBNotificationsPrefix 5 }

sonusCpMaxPacketLengthErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the maximum packet length error rate gone below the clear threshold for the clear duration. This trap is not applicable in the SGX4000."
    ::= { sonusCpNifMIBNotificationsPrefix 6 }

sonusCpNifRcrDcfErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RCR DFC error rate has exceeded set threshold for the set duration. This trap is not applicable in the SGX4000."
    ::= { sonusCpNifMIBNotificationsPrefix 7 }

sonusCpfRcrDcfErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RCR DFC error rate gone below the clear threshold for the clear duration. This trap is not applicable in the SGX4000."
    ::= { sonusCpNifMIBNotificationsPrefix 8 }

sonusCpNifRcrErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RCR error rate has exceeded set threshold for the set duration. This trap is not applicable in the SGX4000."
    ::= { sonusCpNifMIBNotificationsPrefix 9 }

sonusCpNifRcrErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RCR error rate gone below the clear threshold for the clear duration. This trap is not applicable in the SGX4000."
    ::= { sonusCpNifMIBNotificationsPrefix 10 }

sonusCpNifResourceErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Resource Error rate has exceeded set threshold for the set duration. This trap is not applicable in the SGX4000."
    ::= { sonusCpNifMIBNotificationsPrefix 11 }

sonusCpNifResourceErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Resource Error rate gone below the clear threshold for the clear duration. This trap is not applicable in the SGX4000."
    ::= { sonusCpNifMIBNotificationsPrefix 12 }

sonusCpNifRingOverflowErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Overflow Error Rate rate has exceeded set threshold for the set duration. This trap is not applicable in the SGX4000."
    ::= { sonusCpNifMIBNotificationsPrefix 13 }

sonusCpNifRingOverflowErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Overflow Error Rate rate gone below the clear threshold for the clear duration. This trap is not applicable in the SGX4000."
    ::= { sonusCpNifMIBNotificationsPrefix 14 }

sonusCpNifDroppedPacketsRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Dropped Packets rate has exceeded set threshold for the set duration. This trap is not applicable in the SGX4000."
    ::= { sonusCpNifMIBNotificationsPrefix 15 }

sonusCpNifRateDroppedPacketsClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the Dropped Packets rate gone below the clear threshold for the clear duration. This trap is not applicable in the SGX4000."
    ::= { sonusCpNifMIBNotificationsPrefix 16 }

sonusCpNifRbrPrefetchEmptyErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RBR Prefetch Empty rate has exceeded set threshold for the set duration. This trap is not applicable in the SGX4000."
    ::= { sonusCpNifMIBNotificationsPrefix 17 }

sonusCpNifRbrPrefetchEmptyErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RBR Prefetch Empty rate gone below the clear threshold for the clear duration. This trap is not applicable in the SGX4000."
    ::= { sonusCpNifMIBNotificationsPrefix 18 }

sonusCpNifRbrEmptyErrorRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RBR Empty rate has exceeded set threshold for the set duration. This trap is not applicable in the SGX4000."
    ::= { sonusCpNifMIBNotificationsPrefix 19 }

sonusCpNifRbrEmptyErrorRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the RBR Empty rate gone below the clear threshold for the clear duration. This trap is not applicable in the SGX4000."
    ::= { sonusCpNifMIBNotificationsPrefix 20 }

sonusCpNifWredDroppedPacketsRateExceededNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the WRED Dropped Packets rate has exceeded set threshold for the set duration. This trap is not applicable in the SGX4000."
    ::= { sonusCpNifMIBNotificationsPrefix 21 }

sonusCpNifWredDroppedPacketsRateClearedNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates that the WRED Dropped Packets rate gone below the clear threshold for the clear duration. This trap is not applicable in the SGX4000."
    ::= { sonusCpNifMIBNotificationsPrefix 22 }

sonusCpNifMailBoxNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal mailbox error. This trap is not applicable in the SGX4000."
    ::= { sonusCpNifMIBNotificationsPrefix 23 }

sonusCpNifNackPacketReadErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal NACK Packet Read Error. This trap is not applicable in the SGX4000."
    ::= { sonusCpNifMIBNotificationsPrefix 24 }

sonusCpNifNackPrefetchErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal NACK Prefetch Error. This trap is not applicable in the SGX4000."
    ::= { sonusCpNifMIBNotificationsPrefix 25 }

sonusCpNifPacketSizeErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Packet Size Error. This trap is not applicable in the SGX4000."
    ::= { sonusCpNifMIBNotificationsPrefix 26 }

sonusCpNifPacketPointerErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Packet Pointer Error. This trap is not applicable in the SGX4000."
    ::= { sonusCpNifMIBNotificationsPrefix 27 }

sonusCpNifParityErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Parity Error. This trap is not applicable in the SGX4000."
    ::= { sonusCpNifMIBNotificationsPrefix 28 }

sonusCpNifPartitionErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Partition Error. This trap is not applicable in the SGX4000."
    ::= { sonusCpNifMIBNotificationsPrefix 29 }

sonusCpNifByteEnableBusErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Byte Enable Bus Error. This trap is not applicable in the SGX4000."
    ::= { sonusCpNifMIBNotificationsPrefix 30 }

sonusCpNifPageViolationErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Page Violation Error. This trap is not applicable in the SGX4000."
    ::= { sonusCpNifMIBNotificationsPrefix 31 }

sonusCpNifDataControlFifoErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Data or Control FIFO Error. This trap is not applicable in the SGX4000."
    ::= { sonusCpNifMIBNotificationsPrefix 32 }

sonusCpNifRcrShadowParityErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RCR Shadow Parity Error. This trap is not applicable in the SGX4000."
    ::= { sonusCpNifMIBNotificationsPrefix 33 }

sonusCpNifPrefetchParityErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Prefetch Parity Error. This trap is not applicable in the SGX4000."
    ::= { sonusCpNifMIBNotificationsPrefix 34 }

sonusCpNifRbrFullErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RBR Full Error. This trap is not applicable in the SGX4000."
    ::= { sonusCpNifMIBNotificationsPrefix 35 }

sonusCpNifRbrLogicalPageErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RBR Logical Page Error. This trap is not applicable in the SGX4000."
    ::= { sonusCpNifMIBNotificationsPrefix 36 }

sonusCpNifRbrTimeoutNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RBR Timeout. This trap is not applicable in the SGX4000."
    ::= { sonusCpNifMIBNotificationsPrefix 37 }

sonusCpNifRcrAckErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RCR Ack Error. This trap is not applicable in the SGX4000."
    ::= { sonusCpNifMIBNotificationsPrefix 38 }

sonusCpNifRcrInconsistencyErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RCR Inconsistancy Error. This trap is not applicable in the SGX4000."
    ::= { sonusCpNifMIBNotificationsPrefix 39 }

sonusCpNifRcrRingFullErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal RCR Ring Full Error. This trap is not applicable in the SGX4000."
    ::= { sonusCpNifMIBNotificationsPrefix 40 }

sonusCpNifResponseCountErrorNotification NOTIFICATION-TYPE
    OBJECTS         { sonusAlarmNodeID, sonusAlarmLevel, 
                      sonusAlarmSequenceId, sonusAlarmTime, 
                      sonusAlarmDescription, sonusCpNifCeName, 
                      sonusCpNifType, sonusCpNifUsage }
    STATUS          current
    DESCRIPTION     
            "This trap indicates a fatal Response Count Error. This trap is not applicable in the SGX4000."
    ::= { sonusCpNifMIBNotificationsPrefix 41 }

sonusCpRadiusServerFailedNotification NOTIFICATION-TYPE
    OBJECTS         { sonusAlarmNodeID, sonusAlarmLevel, 
                      sonusAlarmSequenceId, sonusAlarmTime, 
                      sonusAlarmDescription, sonusCpRadiusServerName }
    STATUS          current
    DESCRIPTION     
            "This trap indicates a radius accounting server has been marked failed. This trap is not applicable in the SGX4000."
    ::= { sonusCpRadiusAccountingMIBNotificationsPrefix 1 }

sonusCpRadiusServerPacketsFlushedNotification NOTIFICATION-TYPE
    OBJECTS         { sonusAlarmNodeID, sonusAlarmLevel, 
                      sonusAlarmSequenceId, sonusAlarmTime, 
                      sonusAlarmDescription, sonusCpRadiusFlushedPackets, 
                      sonusCpRadiusFlushedPacketsFile }
    STATUS          current
    DESCRIPTION     
            "This trap indicates that radius packets have been flushed because a radius server is not available. This trap is not applicable in the SGX4000."
    ::= { sonusCpRadiusAccountingMIBNotificationsPrefix 2 }

sonusCpLicenseIntegrityViolationNotification NOTIFICATION-TYPE
    OBJECTS         { sonusAlarmNodeID, sonusAlarmLevel, 
                      sonusAlarmSequenceId, sonusAlarmTime, 
                      sonusAlarmDescription, sonusCpLicenseId, 
                      sonusCpLicenseViolationDescString }
    STATUS          current
    DESCRIPTION     
            "This trap indicates any attempted violation of license integrity. This trap is not applicable in the SGX4000. "
    ::= { sonusCpLicenseMIBNotificationsPrefix 1 }

sonusCpLicenseBundleExpireWarningNotification NOTIFICATION-TYPE
    OBJECTS         { sonusAlarmNodeID, sonusAlarmLevel, 
                      sonusAlarmSequenceId, sonusAlarmTime, 
                      sonusAlarmDescription, sonusCpLicenseId, 
                      sonusCpLicenseFeatureName }
    STATUS          current
    DESCRIPTION     
            "This trap indicates that license budle will expire in 14 days. This trap is not applicable in the SGX4000."
    ::= { sonusCpLicenseMIBNotificationsPrefix 2 }

sonusCpLicenseBundleExpiredNotification NOTIFICATION-TYPE
    OBJECTS         { sonusAlarmNodeID, sonusAlarmLevel, 
                      sonusAlarmSequenceId, sonusAlarmTime, 
                      sonusAlarmDescription, sonusCpLicenseId, 
                      sonusCpLicenseFeatureName }
    STATUS          current
    DESCRIPTION     
            "This trap indicates that license budle is expired. This trap is not applicable in the SGX4000."
    ::= { sonusCpLicenseMIBNotificationsPrefix 3 }

sonusCpLicenseBundleRenewedNotification NOTIFICATION-TYPE
    OBJECTS         { sonusAlarmNodeID, sonusAlarmLevel, 
                      sonusAlarmSequenceId, sonusAlarmTime, 
                      sonusAlarmDescription, sonusCpLicenseId, 
                      sonusCpLicenseFeatureName }
    STATUS          current
    DESCRIPTION     
            "This trap indicates that license budle will is renewed. This trap is not applicable in the SGX4000."
    ::= { sonusCpLicenseMIBNotificationsPrefix 4 }

sonusCpLicenseHostSerialUnavailable NOTIFICATION-TYPE
    OBJECTS         { sonusAlarmNodeID, sonusAlarmLevel, 
                      sonusAlarmSequenceId, sonusAlarmTime, 
                      sonusAlarmDescription, sonusCpSystemServerName }
    STATUS          current
    DESCRIPTION     
            "This trap indicates that the host serial number could not be read from the hardware. This trap is not applicable in the SGX4000."
    ::= { sonusCpLicenseMIBNotificationsPrefix 5 }

sonusCpLicenseSerialMismatch NOTIFICATION-TYPE
    OBJECTS         { sonusAlarmNodeID, sonusAlarmLevel, 
                      sonusAlarmSequenceId, sonusAlarmTime, 
                      sonusAlarmDescription, sonusCpSystemServerName, 
                      sonusCpLicenseId }
    STATUS          current
    DESCRIPTION     
            "This trap indicates that the host serial number does not match that the serial number in the license. This trap is not applicable in the SGX4000."
    ::= { sonusCpLicenseMIBNotificationsPrefix 6 }

sonusCpLicensePeerSerialMismatch NOTIFICATION-TYPE
    OBJECTS         { sonusAlarmNodeID, sonusAlarmLevel, 
                      sonusAlarmSequenceId, sonusAlarmTime, 
                      sonusAlarmDescription, sonusCpSystemServerName, 
                      sonusCpLicenseId }
    STATUS          current
    DESCRIPTION     
            "This trap indicates that the peer host serial number does not match that the serial number in the license. This trap is not applicable in the SGX4000."
    ::= { sonusCpLicenseMIBNotificationsPrefix 7 }

sonusCpConfiguredExceedSystemLimit NOTIFICATION-TYPE
    OBJECTS         { sonusAlarmNodeID, sonusAlarmLevel, 
                      sonusAlarmSequenceId, sonusAlarmTime, 
                      sonusAlarmDescription, sonusSessConfigLicenses, 
                      sonusSessSystemLimit }
    STATUS          current
    DESCRIPTION     
            "This trap indicates that configured licensed sessions are more than system limit. This trap is not applicable in the SGX4000."
    ::= { sonusCpLicenseMIBNotificationsPrefix 8 }

sonusCpCdrServerTransferFailNotification NOTIFICATION-TYPE
    OBJECTS         { sonusAlarmNodeID, sonusAlarmLevel, 
                      sonusAlarmSequenceId, sonusAlarmTime, 
                      sonusAlarmDescription, sonusCpCdrServerType, 
                      sonusCpCdrServerIpAddress }
    STATUS          current
    DESCRIPTION     
            "CDR transfer failure. This notification is flow controlled and
             will not occur more often than once every ten seconds. This trap is not applicable in the SGX4000."
    ::= { sonusCpCdrServerMIBNotificationsPrefix 1 }

sonusCpCdrServerSwtichoverNotification NOTIFICATION-TYPE
    OBJECTS         { sonusAlarmNodeID, sonusAlarmLevel, 
                      sonusAlarmSequenceId, sonusAlarmTime, 
                      sonusAlarmDescription, sonusCpCdrServerType, 
                      sonusCpCdrServerIpAddress }
    STATUS          current
    DESCRIPTION     
            "CDR server is switching to alternate server. This notification is flow controlled
             and will not occur more often than once every ten seconds. This trap is not applicable in the SGX4000."
    ::= { sonusCpCdrServerMIBNotificationsPrefix 2 }

sonusCpCdrServerNewXferPendingNotification NOTIFICATION-TYPE
    OBJECTS         { sonusAlarmNodeID, sonusAlarmLevel, 
                      sonusAlarmSequenceId, sonusAlarmTime, 
                      sonusAlarmDescription, sonusCpCdrServerType, 
                      sonusCpCdrServerIpAddress }
    STATUS          current
    DESCRIPTION     
            "CDR transfer added to pending queue. This trap is not applicable in the SGX4000."
    ::= { sonusCpCdrServerMIBNotificationsPrefix 3 }

sonusCpCdrServerPendingQueueEmptiedNotification NOTIFICATION-TYPE
    OBJECTS         { sonusAlarmNodeID, sonusAlarmLevel, 
                      sonusAlarmSequenceId, sonusAlarmTime, 
                      sonusAlarmDescription, sonusCpCdrServerType, 
                      sonusCpCdrServerIpAddress }
    STATUS          current
    DESCRIPTION     
            "CDR server all pending transfers have completed. This trap is not applicable in the SGX4000."
    ::= { sonusCpCdrServerMIBNotificationsPrefix 4 }

END -- end of module HORNET-BASE-TRAPS-MIB.
