--
-- This SMIv2 module has been generated by smidump 0.2-cvs. Do not edit.
--

SONUS-RAID-DH-MIB DEFINITIONS ::= BEGIN

IMPORTS
    Counter64, Integer32, IpAddress, MODULE-IDENTITY, NOTIFICATION-TYPE, 
    OBJECT-TYPE
        FROM SNMPv2-SMI
    DisplayString
        FROM SNMPv2-TC
    sonusEventClass, sonusEventDescription, sonusEventLevel, 
    sonusEventTime
        FROM SONUS-COMMON-MIB
    sonusSystemMIBs
        FROM SONUS-SMI;

sonusRAIDDHMIB MODULE-IDENTITY
    LAST-UPDATED    "200403160000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The Sonus MIB Module for node-level management of the
             Dot Hill RAID Device."
    ::= { sonusSystemMIBs 13 }


sonusRAIDDHMIBObjects OBJECT IDENTIFIER
    ::= { sonusRAIDDHMIB 1 }

sonusRAIDDHMIBNotifications OBJECT IDENTIFIER
    ::= { sonusRAIDDHMIB 2 }

sonusRAIDDHMIBNotificationsPrefix OBJECT IDENTIFIER
    ::= { sonusRAIDDHMIBNotifications 0 }

sonusRAIDDHMIBNotificationsObjects OBJECT IDENTIFIER
    ::= { sonusRAIDDHMIBNotifications 1 }

sonusRAIDDHErrorCode OBJECT-TYPE
    SYNTAX          Integer32 (0..255)
    MAX-ACCESS      read-only
    STATUS          current
    DESCRIPTION     
            ""
    ::= { sonusRAIDDHMIBNotificationsObjects 1 }

sonusRAIDDHLastErrorTime OBJECT-TYPE
    SYNTAX          Counter64
    MAX-ACCESS      read-only
    STATUS          current
    DESCRIPTION     
            ""
    ::= { sonusRAIDDHMIBNotificationsObjects 2 }

sonusRAIDDHNumErrorsDetected OBJECT-TYPE
    SYNTAX          Counter64
    MAX-ACCESS      read-only
    STATUS          current
    DESCRIPTION     
            ""
    ::= { sonusRAIDDHMIBNotificationsObjects 3 }

sonusRAIDDHLogicalDriveId OBJECT-TYPE
    SYNTAX          Counter64
    MAX-ACCESS      read-only
    STATUS          current
    DESCRIPTION     
            ""
    ::= { sonusRAIDDHMIBNotificationsObjects 4 }

sonusRAIDDHScsiChannel OBJECT-TYPE
    SYNTAX          Integer32 (0..255)
    MAX-ACCESS      read-only
    STATUS          current
    DESCRIPTION     
            ""
    ::= { sonusRAIDDHMIBNotificationsObjects 5 }

sonusRAIDDHScsiId OBJECT-TYPE
    SYNTAX          Integer32 (0..255)
    MAX-ACCESS      read-only
    STATUS          current
    DESCRIPTION     
            ""
    ::= { sonusRAIDDHMIBNotificationsObjects 6 }

sonusRAIDDHScsiLUN OBJECT-TYPE
    SYNTAX          Integer32 (0..255)
    MAX-ACCESS      read-only
    STATUS          current
    DESCRIPTION     
            ""
    ::= { sonusRAIDDHMIBNotificationsObjects 7 }

sonusRAIDDHSectorNum OBJECT-TYPE
    SYNTAX          Counter64
    MAX-ACCESS      read-only
    STATUS          current
    DESCRIPTION     
            ""
    ::= { sonusRAIDDHMIBNotificationsObjects 8 }

sonusRAIDDHScsiStatus OBJECT-TYPE
    SYNTAX          Integer32 (0..255)
    MAX-ACCESS      read-only
    STATUS          current
    DESCRIPTION     
            ""
    ::= { sonusRAIDDHMIBNotificationsObjects 9 }

sonusRAIDDHSenseKey OBJECT-TYPE
    SYNTAX          Integer32 (0..255)
    MAX-ACCESS      read-only
    STATUS          current
    DESCRIPTION     
            ""
    ::= { sonusRAIDDHMIBNotificationsObjects 10 }

sonusRAIDDHSenseCode OBJECT-TYPE
    SYNTAX          Integer32 (0..255)
    MAX-ACCESS      read-only
    STATUS          current
    DESCRIPTION     
            ""
    ::= { sonusRAIDDHMIBNotificationsObjects 11 }

sonusRAIDDHSenseCdQIf OBJECT-TYPE
    SYNTAX          Integer32 (0..255)
    MAX-ACCESS      read-only
    STATUS          current
    DESCRIPTION     
            ""
    ::= { sonusRAIDDHMIBNotificationsObjects 12 }

sonusRAIDDHLUNDescription OBJECT-TYPE
    SYNTAX          Counter64
    MAX-ACCESS      read-only
    STATUS          current
    DESCRIPTION     
            ""
    ::= { sonusRAIDDHMIBNotificationsObjects 13 }

sonusRAIDDHDeviceDescription OBJECT-TYPE
    SYNTAX          Counter64
    MAX-ACCESS      read-only
    STATUS          current
    DESCRIPTION     
            ""
    ::= { sonusRAIDDHMIBNotificationsObjects 14 }

sonusRAIDDHLUNClass OBJECT-TYPE
    SYNTAX          Integer32
    MAX-ACCESS      read-only
    STATUS          current
    DESCRIPTION     
            ""
    ::= { sonusRAIDDHMIBNotificationsObjects 15 }

sonusRAIDDHDeviceType OBJECT-TYPE
    SYNTAX          Integer32 (0..65535)
    MAX-ACCESS      read-only
    STATUS          current
    DESCRIPTION     
            ""
    ::= { sonusRAIDDHMIBNotificationsObjects 16 }

sonusRAIDDHDeviceIndex OBJECT-TYPE
    SYNTAX          Integer32 (0..65535)
    MAX-ACCESS      read-only
    STATUS          current
    DESCRIPTION     
            ""
    ::= { sonusRAIDDHMIBNotificationsObjects 17 }

sonusRAIDDHControllerNotification NOTIFICATION-TYPE
    OBJECTS         { sonusRAIDDHErrorCode, sonusRAIDDHLastErrorTime, 
                      sonusRAIDDHNumErrorsDetected, 
                      sonusEventDescription, sonusEventClass, 
                      sonusEventLevel, sonusEventTime }
    STATUS          current
    DESCRIPTION     
            "This notification is raised in response to a RaidControllerEvent message from a dotHill RAID device."
    ::= { sonusRAIDDHMIBNotificationsPrefix 1 }

sonusRAIDDHLogDrvNotification NOTIFICATION-TYPE
    OBJECTS         { sonusRAIDDHErrorCode, sonusRAIDDHLogicalDriveId, 
                      sonusRAIDDHScsiChannel, sonusRAIDDHScsiId, 
                      sonusRAIDDHScsiLUN, sonusEventDescription, 
                      sonusEventClass, sonusEventLevel, sonusEventTime }
    STATUS          current
    DESCRIPTION     
            "This notification is raised in response to a RaidLogDriveEvent message from a dotHill RAID device."
    ::= { sonusRAIDDHMIBNotificationsPrefix 2 }

sonusRAIDDHHostChannelErrorNotification NOTIFICATION-TYPE
    OBJECTS         { sonusRAIDDHErrorCode, sonusRAIDDHLastErrorTime, 
                      sonusRAIDDHNumErrorsDetected, 
                      sonusRAIDDHScsiChannel, sonusRAIDDHScsiId, 
                      sonusRAIDDHScsiLUN, sonusEventDescription, 
                      sonusEventClass, sonusEventLevel, sonusEventTime }
    STATUS          current
    DESCRIPTION     
            "This notification is raised in response to a RaidHostChannelErrorEvent message from a dotHill RAID device."
    ::= { sonusRAIDDHMIBNotificationsPrefix 3 }

sonusRAIDDHDriveChannelErrorNotification NOTIFICATION-TYPE
    OBJECTS         { sonusRAIDDHErrorCode, sonusRAIDDHLastErrorTime, 
                      sonusRAIDDHNumErrorsDetected, 
                      sonusRAIDDHLogicalDriveId, sonusRAIDDHScsiChannel, 
                      sonusRAIDDHScsiId, sonusRAIDDHScsiLUN, 
                      sonusRAIDDHSectorNum, sonusRAIDDHScsiStatus, 
                      sonusRAIDDHSenseKey, sonusRAIDDHSenseCode, 
                      sonusRAIDDHSenseCdQIf, sonusEventDescription, 
                      sonusEventClass, sonusEventLevel, sonusEventTime }
    STATUS          current
    DESCRIPTION     
            "This notification is raised in response to a RaidDriveChannelErrorEvent message from a dotHill RAID device."
    ::= { sonusRAIDDHMIBNotificationsPrefix 4 }

sonusRAIDDHGeneralizedTargetNotification NOTIFICATION-TYPE
    OBJECTS         { sonusRAIDDHErrorCode, sonusRAIDDHLUNDescription, 
                      sonusRAIDDHDeviceDescription, sonusRAIDDHLUNClass, 
                      sonusRAIDDHDeviceType, sonusRAIDDHDeviceIndex, 
                      sonusRAIDDHScsiChannel, sonusRAIDDHScsiId, 
                      sonusRAIDDHScsiLUN, sonusEventDescription, 
                      sonusEventClass, sonusEventLevel, sonusEventTime }
    STATUS          current
    DESCRIPTION     
            "This notification is raised in response to a RaidGeneralizedTargetEvent message from a dotHill RAID device."
    ::= { sonusRAIDDHMIBNotificationsPrefix 5 }

END -- end of module SONUS-RAID-DH-MIB.
