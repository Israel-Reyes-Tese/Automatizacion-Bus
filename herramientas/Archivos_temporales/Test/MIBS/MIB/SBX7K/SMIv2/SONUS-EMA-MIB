--
-- This SMIv2 module has been generated by smidump 0.2-cvs. Do not edit.
--

SONUS-EMA-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusEmaMIB MODULE-IDENTITY
    LAST-UPDATED    "202007050000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            ""
    REVISION        "202007050000Z"
    DESCRIPTION     
            "Auto generated MIB."
    ::= { sonusCommonSoftwarePlatformServicesMIBs 20 }


String ::= TEXTUAL-CONVENTION
    DISPLAY-HINT    "1t"
    STATUS          current
    DESCRIPTION     
            "xs:string"
    SYNTAX          OCTET STRING

EmaClientAuthMethodType ::= TEXTUAL-CONVENTION
    STATUS          current
    DESCRIPTION     
            ""
    SYNTAX          INTEGER { usernamePasswordOnly(0), pkiCertOnly(1), 
                        usernamePasswordOrPkiCert(2) }

sonusEma OBJECT IDENTIFIER
    ::= { sonusEmaMIB 1 }

sonusEmaClientAuthMethod OBJECT-TYPE
    SYNTAX          EmaClientAuthMethodType
    MAX-ACCESS      read-write
    STATUS          obsolete
    DESCRIPTION     
            "
             EMA client authentication method
             "
    ::= { sonusEma 1 }

END -- end of module SONUS-EMA-MIB.
