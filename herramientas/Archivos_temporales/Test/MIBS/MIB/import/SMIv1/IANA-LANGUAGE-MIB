--
-- This SMIv1 module has been generated by smidump 0.2-cvs. Do not edit.
--

IANA-LANGUAGE-MIB DEFINITIONS ::= BEGIN

IMPORTS
    mib-2
        FROM RFC1213-MIB;

ianaLanguages OBJECT IDENTIFIER
    ::= { mib-2 73 }

-- ianaLanguages MODULE-IDENTITY
--     LAST-UPDATED    "199909090900Z"
--     ORGANIZATION    
--             "IANA"
--     CONTACT-INFO    
--             "Internet Assigned Numbers Authority (IANA)
--              
--              Postal: ICANN
--                      4676 Admiralty Way, Suite 330
--              	    Marina del Rey, CA 90292
--              
--              Tel:    +1 310 823 9358 x20
--              E-Mail: iana@iana.org"
--     DESCRIPTION     
--             "The MIB module registers object identifier values for
--              well-known programming and scripting languages. Every
--              language registration MUST describe the format used
--              when transferring scripts written in this language.
--              
--              Any additions or changes to the contents of this MIB
--              module require Designated Expert Review as defined in
--              the Guidelines for Writing IANA Considerations Section
--              document. The Designated Expert will be selected by
--              the IESG Area Director of the OPS Area.
--              
--              Note, this module does not have to register all possible
--              languages since languages are identified by object identifier
--              values. It is therefore possible to registered languages in
--              private OID trees.
--              
--              The references given below are not normative with regard to
--              the language version. Other references might be better suited
--              to describe some newer versions of this language. The
--              references are only provided as `a pointer into the right
--              direction'."
--     ::= { mib-2 73 }


ianaLangJavaByteCode OBJECT IDENTIFIER
    ::= { ianaLanguages 1 }

ianaLangTcl OBJECT IDENTIFIER
    ::= { ianaLanguages 2 }

ianaLangPerl OBJECT IDENTIFIER
    ::= { ianaLanguages 3 }

ianaLangScheme OBJECT IDENTIFIER
    ::= { ianaLanguages 4 }

ianaLangSRSL OBJECT IDENTIFIER
    ::= { ianaLanguages 5 }

ianaLangPSL OBJECT IDENTIFIER
    ::= { ianaLanguages 6 }

ianaLangSMSL OBJECT IDENTIFIER
    ::= { ianaLanguages 7 }

END -- end of module IANA-LANGUAGE-MIB.
