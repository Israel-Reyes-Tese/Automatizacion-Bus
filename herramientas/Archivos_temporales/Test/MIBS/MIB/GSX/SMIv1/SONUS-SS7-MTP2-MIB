--
-- This SMIv1 module has been generated by smidump 0.2-cvs. Do not edit.
--

SONUS-SS7-MTP2-MIB DEFINITIONS ::= BEGIN

IMPORTS
    OBJECT-TYPE
        FROM RFC-1212
    TRAP-TYPE
        FROM RFC-1215
    Counter
        FROM RFC1155-SMI
    RowStatus
        FROM SNMPv2-TC
    sonusEventClass, sonusEventDescription, sonusEventLevel, 
    sonusEventTime, sonusSequenceId
        FROM SONUS-COMMON-MIB
    sonusSs7ServicesMIBObjects
        FROM SONUS-SS7-SERVICES-MIB
    SonusAdminState, SonusName, SonusNameReference, SonusServiceState
        FROM SONUS-TC;

sonusSs7Mtp2MIB OBJECT IDENTIFIER
    ::= { sonusSs7ServicesMIBObjects 6 }

-- sonusSs7Mtp2MIB MODULE-IDENTITY
--     LAST-UPDATED    "201009070000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for SS7 MTP2 Management."
--     ::= { sonusSs7ServicesMIBObjects 6 }


sonusSs7Mtp2MIBNotifications OBJECT IDENTIFIER
    ::= { sonusSs7Mtp2MIB 2 }

sonusSs7Mtp2MIBNotificationsPrefix OBJECT IDENTIFIER
    ::= { sonusSs7Mtp2MIBNotifications 0 }

sonusSs7Mtp2MIBNotificationsObjects OBJECT IDENTIFIER
    ::= { sonusSs7Mtp2MIBNotifications 1 }

sonusSs7Mtp2Link OBJECT IDENTIFIER
    ::= { sonusSs7ServicesMIBObjects 7 }

sonusSs7Mtp2LinkNextIndex OBJECT-TYPE
    SYNTAX          INTEGER
    ACCESS          read-only
    STATUS          mandatory
    DESCRIPTION     
            "The next valid index to use when creating a new sonusSs7Mtp2LinkEntry"
    ::= { sonusSs7Mtp2Link 1 }

sonusSs7Mtp2LinkTable OBJECT-TYPE
    SYNTAX          SEQUENCE OF SonusSs7Mtp2LinkEntry
    ACCESS          not-accessible
    STATUS          mandatory
    DESCRIPTION     
            "This table contains information about each MTP2 Link.
             
             A management entity may create rows for Link that are
             anticipated to be supported in the future."
    ::= { sonusSs7Mtp2Link 2 }

sonusSs7Mtp2LinkEntry OBJECT-TYPE
    SYNTAX          SonusSs7Mtp2LinkEntry
    ACCESS          not-accessible
    STATUS          mandatory
    DESCRIPTION     
            "This table describes the MTP2 Links that are configured
             on the GSX switch."
    INDEX           { sonusSs7Mtp2LinkListIndex }
    ::= { sonusSs7Mtp2LinkTable 1 }

SonusSs7Mtp2LinkEntry ::=
    SEQUENCE {
        sonusSs7Mtp2LinkListIndex       INTEGER,
        sonusSs7Mtp2LinkName            SonusName,
        sonusSs7Mtp2LinkProfileName     DisplayString,
        sonusSs7Mtp2LinkInterfacePortName SonusNameReference,
        sonusSs7Mtp2LinkChannelTimeSlot INTEGER,
        sonusSs7Mtp2LinkProtocol        INTEGER,
        sonusSs7Mtp2LinkLinkspeed       INTEGER,
        sonusSs7Mtp2LinkBitrate         INTEGER,
        sonusSs7Mtp2LinkEcm             INTEGER,
        sonusSs7Mtp2LinkT1              INTEGER,
        sonusSs7Mtp2LinkT2              INTEGER,
        sonusSs7Mtp2LinkT3              INTEGER,
        sonusSs7Mtp2LinkT4n             INTEGER,
        sonusSs7Mtp2LinkT4e             INTEGER,
        sonusSs7Mtp2LinkT5              INTEGER,
        sonusSs7Mtp2LinkT6              INTEGER,
        sonusSs7Mtp2LinkT7              INTEGER,
        sonusSs7Mtp2LinkTs              INTEGER,
        sonusSs7Mtp2LinkTo              INTEGER,
        sonusSs7Mtp2LinkTa              INTEGER,
        sonusSs7Mtp2LinkTf              INTEGER,
        sonusSs7Mtp2LinkTfn             INTEGER,
        sonusSs7Mtp2LinkTfp             INTEGER,
        sonusSs7Mtp2LinkTe              INTEGER,
        sonusSs7Mtp2LinkAdminState      SonusAdminState,
        sonusSs7Mtp2LinkMode            SonusServiceState,
        sonusSs7Mtp2LinkRowStatus       RowStatus,
        sonusSs7Mtp2LinkLayerTrace      INTEGER
    }

sonusSs7Mtp2LinkListIndex OBJECT-TYPE
    SYNTAX          INTEGER
    ACCESS          read-only
    STATUS          mandatory
    DESCRIPTION     
            "The index of the MTP2 Link entry."
    ::= { sonusSs7Mtp2LinkEntry 1 }

sonusSs7Mtp2LinkName OBJECT-TYPE
    SYNTAX          SonusName
    ACCESS          read-write
    STATUS          mandatory
    DESCRIPTION     
            "The name of the MTP2 Link."
    ::= { sonusSs7Mtp2LinkEntry 2 }

sonusSs7Mtp2LinkProfileName OBJECT-TYPE
    SYNTAX          DisplayString (SIZE(0..23))
    ACCESS          read-write
    STATUS          mandatory
    DESCRIPTION     
            "The MTP2 Link profile name."
    ::= { sonusSs7Mtp2LinkEntry 3 }

sonusSs7Mtp2LinkInterfacePortName OBJECT-TYPE
    SYNTAX          SonusNameReference
    ACCESS          read-write
    STATUS          mandatory
    DESCRIPTION     
            "The name of the port that the MTP2 interface is on."
    ::= { sonusSs7Mtp2LinkEntry 4 }

sonusSs7Mtp2LinkChannelTimeSlot OBJECT-TYPE
    SYNTAX          INTEGER (1..31)
    ACCESS          read-write
    STATUS          mandatory
    DESCRIPTION     
            "The MTP2 Link channel time slot."
    DEFVAL          { 24 }
    ::= { sonusSs7Mtp2LinkEntry 5 }

sonusSs7Mtp2LinkProtocol OBJECT-TYPE
    SYNTAX          INTEGER { itu(1), ansi(2), jt(3) }
    ACCESS          read-write
    STATUS          mandatory
    DESCRIPTION     
            "The SS7 MTP2 stack type protocol variant."
    DEFVAL          { itu }
    ::= { sonusSs7Mtp2LinkEntry 6 }

sonusSs7Mtp2LinkLinkspeed OBJECT-TYPE
    SYNTAX          INTEGER { low(1), high(2) }
    ACCESS          read-write
    STATUS          mandatory
    DESCRIPTION     
            "The SS7 MTP2 linkspeed."
    DEFVAL          { high }
    ::= { sonusSs7Mtp2LinkEntry 7 }

sonusSs7Mtp2LinkBitrate OBJECT-TYPE
    SYNTAX          INTEGER { bitrate64(1), bitrate56(2), bitrate48(3) }
    ACCESS          read-write
    STATUS          mandatory
    DESCRIPTION     
            "The SS7 MTP2 bitrate in Kbps."
    DEFVAL          { bitrate64 }
    ::= { sonusSs7Mtp2LinkEntry 8 }

sonusSs7Mtp2LinkEcm OBJECT-TYPE
    SYNTAX          INTEGER { basic(1), pcr(2) }
    ACCESS          read-write
    STATUS          mandatory
    DESCRIPTION     
            "The SS7 MTP2 error correcton method."
    DEFVAL          { basic }
    ::= { sonusSs7Mtp2LinkEntry 9 }

sonusSs7Mtp2LinkT1 OBJECT-TYPE
    SYNTAX          INTEGER (40000..50000)
    ACCESS          read-write
    STATUS          mandatory
    DESCRIPTION     
            "T1 timer."
    DEFVAL          { 45000 }
    ::= { sonusSs7Mtp2LinkEntry 10 }

sonusSs7Mtp2LinkT2 OBJECT-TYPE
    SYNTAX          INTEGER (5000..150000)
    ACCESS          read-write
    STATUS          mandatory
    DESCRIPTION     
            "T2 timer."
    DEFVAL          { 118000 }
    ::= { sonusSs7Mtp2LinkEntry 11 }

sonusSs7Mtp2LinkT3 OBJECT-TYPE
    SYNTAX          INTEGER (1000..2000)
    ACCESS          read-write
    STATUS          mandatory
    DESCRIPTION     
            "T3 timer."
    DEFVAL          { 1200 }
    ::= { sonusSs7Mtp2LinkEntry 12 }

sonusSs7Mtp2LinkT4n OBJECT-TYPE
    SYNTAX          INTEGER (7500..9500)
    ACCESS          read-write
    STATUS          mandatory
    DESCRIPTION     
            "T4n timer."
    DEFVAL          { 8700 }
    ::= { sonusSs7Mtp2LinkEntry 13 }

sonusSs7Mtp2LinkT4e OBJECT-TYPE
    SYNTAX          INTEGER (400..600)
    ACCESS          read-write
    STATUS          mandatory
    DESCRIPTION     
            "T4e timer."
    DEFVAL          { 500 }
    ::= { sonusSs7Mtp2LinkEntry 14 }

sonusSs7Mtp2LinkT5 OBJECT-TYPE
    SYNTAX          INTEGER (80..120)
    ACCESS          read-write
    STATUS          mandatory
    DESCRIPTION     
            "T5 timer."
    DEFVAL          { 100 }
    ::= { sonusSs7Mtp2LinkEntry 15 }

sonusSs7Mtp2LinkT6 OBJECT-TYPE
    SYNTAX          INTEGER (3000..6000)
    ACCESS          read-write
    STATUS          mandatory
    DESCRIPTION     
            "T6 timer."
    DEFVAL          { 5000 }
    ::= { sonusSs7Mtp2LinkEntry 16 }

sonusSs7Mtp2LinkT7 OBJECT-TYPE
    SYNTAX          INTEGER (500..2000)
    ACCESS          read-write
    STATUS          mandatory
    DESCRIPTION     
            "T7 timer."
    DEFVAL          { 1000 }
    ::= { sonusSs7Mtp2LinkEntry 17 }

sonusSs7Mtp2LinkTs OBJECT-TYPE
    SYNTAX          INTEGER (0..65536)
    ACCESS          read-write
    STATUS          mandatory
    DESCRIPTION     
            "Ts timer (Japan only)."
    DEFVAL          { 1000 }
    ::= { sonusSs7Mtp2LinkEntry 18 }

sonusSs7Mtp2LinkTo OBJECT-TYPE
    SYNTAX          INTEGER (0..65536)
    ACCESS          read-write
    STATUS          mandatory
    DESCRIPTION     
            "To timer (Japan only)."
    DEFVAL          { 1000 }
    ::= { sonusSs7Mtp2LinkEntry 19 }

sonusSs7Mtp2LinkTa OBJECT-TYPE
    SYNTAX          INTEGER (0..65536)
    ACCESS          read-write
    STATUS          mandatory
    DESCRIPTION     
            "Ta timer (Japan only)."
    DEFVAL          { 1000 }
    ::= { sonusSs7Mtp2LinkEntry 20 }

sonusSs7Mtp2LinkTf OBJECT-TYPE
    SYNTAX          INTEGER (0..65536)
    ACCESS          read-write
    STATUS          mandatory
    DESCRIPTION     
            "Tf timer (Japan only)."
    DEFVAL          { 1000 }
    ::= { sonusSs7Mtp2LinkEntry 21 }

sonusSs7Mtp2LinkTfn OBJECT-TYPE
    SYNTAX          INTEGER (0..65536)
    ACCESS          read-write
    STATUS          mandatory
    DESCRIPTION     
            "Tfn timer (Japan only)."
    DEFVAL          { 1000 }
    ::= { sonusSs7Mtp2LinkEntry 22 }

sonusSs7Mtp2LinkTfp OBJECT-TYPE
    SYNTAX          INTEGER (0..65536)
    ACCESS          read-write
    STATUS          mandatory
    DESCRIPTION     
            "Tfp timer (Japan only)."
    DEFVAL          { 1000 }
    ::= { sonusSs7Mtp2LinkEntry 23 }

sonusSs7Mtp2LinkTe OBJECT-TYPE
    SYNTAX          INTEGER (0..65536)
    ACCESS          read-write
    STATUS          mandatory
    DESCRIPTION     
            "Te timer (Japan only)."
    DEFVAL          { 1000 }
    ::= { sonusSs7Mtp2LinkEntry 24 }

sonusSs7Mtp2LinkAdminState OBJECT-TYPE
    SYNTAX          SonusAdminState
    ACCESS          read-write
    STATUS          mandatory
    DESCRIPTION     
            "The admin state of the MTP2 Link."
    DEFVAL          { disabled }
    ::= { sonusSs7Mtp2LinkEntry 25 }

sonusSs7Mtp2LinkMode OBJECT-TYPE
    SYNTAX          SonusServiceState
    ACCESS          read-write
    STATUS          mandatory
    DESCRIPTION     
            "The mode of operation of link."
    DEFVAL          { inService }
    ::= { sonusSs7Mtp2LinkEntry 26 }

sonusSs7Mtp2LinkRowStatus OBJECT-TYPE
    SYNTAX          RowStatus
    ACCESS          read-write
    STATUS          mandatory
    DESCRIPTION     
            ""
    ::= { sonusSs7Mtp2LinkEntry 27 }

sonusSs7Mtp2LinkLayerTrace OBJECT-TYPE
    SYNTAX          INTEGER { none(1), layer2(2) }
    ACCESS          read-write
    STATUS          mandatory
    DESCRIPTION     
            "Controls logging of layer events to the trace event log file."
    DEFVAL          { none }
    ::= { sonusSs7Mtp2LinkEntry 28 }

sonusSs7Mtp2LinkStatTable OBJECT-TYPE
    SYNTAX          SEQUENCE OF SonusSs7Mtp2LinkStatEntry
    ACCESS          not-accessible
    STATUS          mandatory
    DESCRIPTION     
            "This table contains status information about each MTP2 link
             in the GSX switch node."
    ::= { sonusSs7ServicesMIBObjects 8 }

sonusSs7Mtp2LinkStatEntry OBJECT-TYPE
    SYNTAX          SonusSs7Mtp2LinkStatEntry
    ACCESS          not-accessible
    STATUS          mandatory
    DESCRIPTION     
            "This table describes the status of the links that are configured
             as SS7 nodes for the GSX Switch node."
    INDEX           { sonusSs7Mtp2LinkStatListIndex }
    ::= { sonusSs7Mtp2LinkStatTable 1 }

SonusSs7Mtp2LinkStatEntry ::=
    SEQUENCE {
        sonusSs7Mtp2LinkStatListIndex   INTEGER,
        sonusSs7Mtp2LinkStatState       INTEGER,
        sonusSs7Mtp2LinkStatInApiSu     Counter,
        sonusSs7Mtp2LinkStatOutApiSu    Counter,
        sonusSs7Mtp2LinkStatInApiLl     Counter,
        sonusSs7Mtp2LinkStatOutApiLl    Counter,
        sonusSs7Mtp2LinkStatInApiSm     Counter,
        sonusSs7Mtp2LinkStatOutApiSm    Counter,
        sonusSs7Mtp2LinkStatErrApiSu    Counter,
        sonusSs7Mtp2LinkStatErrApiLl    Counter,
        sonusSs7Mtp2LinkStatErrApiSm    Counter,
        sonusSs7Mtp2LinkStatErrOutApiLl Counter,
        sonusSs7Mtp2LinkStatErrApiMisc  Counter,
        sonusSs7Mtp2LinkStatLinkInServiceStartTime          INTEGER,
        sonusSs7Mtp2LinkStatSlFailureAllReason      Counter,
        sonusSs7Mtp2LinkStatSlFailureAbnormalFibBsnr            Counter,
        sonusSs7Mtp2LinkStatSlFailureT7Expiry     Counter,
        sonusSs7Mtp2LinkStatSlCongTooLong Counter,
        sonusSs7Mtp2LinkStatSlProvAlgnFailed    Counter,
        sonusSs7Mtp2LinkStatNumSuError  Counter,
        sonusSs7Mtp2LinkStatNumNegAck   Counter,
        sonusSs7Mtp2LinkStatNumSifSioOctetTx    Counter,
        sonusSs7Mtp2LinkStatNumOctetRtx Counter,
        sonusSs7Mtp2LinkStatNumMsuTx    Counter,
        sonusSs7Mtp2LinkStatNumSifSioOctetRx    Counter,
        sonusSs7Mtp2LinkStatNumMsuRx    Counter,
        sonusSs7Mtp2LinkStatErrApi      Counter,
        sonusSs7Mtp2LinkStatErrMsg      Counter,
        sonusSs7Mtp2LinkStatErrSys      Counter,
        sonusSs7Mtp2LinkStatErrSystemRes Counter
    }

sonusSs7Mtp2LinkStatListIndex OBJECT-TYPE
    SYNTAX          INTEGER
    ACCESS          read-only
    STATUS          mandatory
    DESCRIPTION     
            "The index of the SS7 MTP2 Link."
    ::= { sonusSs7Mtp2LinkStatEntry 1 }

sonusSs7Mtp2LinkStatState OBJECT-TYPE
    SYNTAX          INTEGER { outOfService(0), initialAlignment(1), 
                        allignedNotReady(2), proving(3), 
                        allignedReady(4), inService(5) }
    ACCESS          read-only
    STATUS          mandatory
    DESCRIPTION     
            "The state of the SS7 MTP2 Link."
    ::= { sonusSs7Mtp2LinkStatEntry 2 }

sonusSs7Mtp2LinkStatInApiSu OBJECT-TYPE
    SYNTAX          Counter
    ACCESS          read-only
    STATUS          mandatory
    DESCRIPTION     
            "Incoming API's from SU."
    ::= { sonusSs7Mtp2LinkStatEntry 3 }

sonusSs7Mtp2LinkStatOutApiSu OBJECT-TYPE
    SYNTAX          Counter
    ACCESS          read-only
    STATUS          mandatory
    DESCRIPTION     
            "Outgoing API's to SU."
    ::= { sonusSs7Mtp2LinkStatEntry 4 }

sonusSs7Mtp2LinkStatInApiLl OBJECT-TYPE
    SYNTAX          Counter
    ACCESS          read-only
    STATUS          mandatory
    DESCRIPTION     
            "Incoming API's from LL."
    ::= { sonusSs7Mtp2LinkStatEntry 5 }

sonusSs7Mtp2LinkStatOutApiLl OBJECT-TYPE
    SYNTAX          Counter
    ACCESS          read-only
    STATUS          mandatory
    DESCRIPTION     
            "Outgoing API's to LL."
    ::= { sonusSs7Mtp2LinkStatEntry 6 }

sonusSs7Mtp2LinkStatInApiSm OBJECT-TYPE
    SYNTAX          Counter
    ACCESS          read-only
    STATUS          mandatory
    DESCRIPTION     
            "Incoming API's from SM."
    ::= { sonusSs7Mtp2LinkStatEntry 7 }

sonusSs7Mtp2LinkStatOutApiSm OBJECT-TYPE
    SYNTAX          Counter
    ACCESS          read-only
    STATUS          mandatory
    DESCRIPTION     
            "Outgoing API's to SM."
    ::= { sonusSs7Mtp2LinkStatEntry 8 }

sonusSs7Mtp2LinkStatErrApiSu OBJECT-TYPE
    SYNTAX          Counter
    ACCESS          read-only
    STATUS          mandatory
    DESCRIPTION     
            "Errors in incoming API's from SU."
    ::= { sonusSs7Mtp2LinkStatEntry 9 }

sonusSs7Mtp2LinkStatErrApiLl OBJECT-TYPE
    SYNTAX          Counter
    ACCESS          read-only
    STATUS          mandatory
    DESCRIPTION     
            "Errors in incoming API's from LL."
    ::= { sonusSs7Mtp2LinkStatEntry 10 }

sonusSs7Mtp2LinkStatErrApiSm OBJECT-TYPE
    SYNTAX          Counter
    ACCESS          read-only
    STATUS          mandatory
    DESCRIPTION     
            "Errors in incoming API's from SM."
    ::= { sonusSs7Mtp2LinkStatEntry 11 }

sonusSs7Mtp2LinkStatErrOutApiLl OBJECT-TYPE
    SYNTAX          Counter
    ACCESS          read-only
    STATUS          mandatory
    DESCRIPTION     
            "Errors in outgoing API's to LL."
    ::= { sonusSs7Mtp2LinkStatEntry 12 }

sonusSs7Mtp2LinkStatErrApiMisc OBJECT-TYPE
    SYNTAX          Counter
    ACCESS          read-only
    STATUS          mandatory
    DESCRIPTION     
            "Miscellaneous API errors."
    ::= { sonusSs7Mtp2LinkStatEntry 13 }

sonusSs7Mtp2LinkStatLinkInServiceStartTime OBJECT-TYPE
    SYNTAX          INTEGER
    ACCESS          read-only
    STATUS          mandatory
    DESCRIPTION     
            "The link uptime, measured in milliseconds."
    ::= { sonusSs7Mtp2LinkStatEntry 14 }

sonusSs7Mtp2LinkStatSlFailureAllReason OBJECT-TYPE
    SYNTAX          Counter
    ACCESS          read-only
    STATUS          mandatory
    DESCRIPTION     
            "Link failure, all reasons."
    ::= { sonusSs7Mtp2LinkStatEntry 15 }

sonusSs7Mtp2LinkStatSlFailureAbnormalFibBsnr OBJECT-TYPE
    SYNTAX          Counter
    ACCESS          read-only
    STATUS          mandatory
    DESCRIPTION     
            "Link failure, abnormal FIBR/BSNR."
    ::= { sonusSs7Mtp2LinkStatEntry 16 }

sonusSs7Mtp2LinkStatSlFailureT7Expiry OBJECT-TYPE
    SYNTAX          Counter
    ACCESS          read-only
    STATUS          mandatory
    DESCRIPTION     
            "Link failure, excessive delay of ack."
    ::= { sonusSs7Mtp2LinkStatEntry 17 }

sonusSs7Mtp2LinkStatSlCongTooLong OBJECT-TYPE
    SYNTAX          Counter
    ACCESS          read-only
    STATUS          mandatory
    DESCRIPTION     
            "Link failure, excessive duration of congestion."
    ::= { sonusSs7Mtp2LinkStatEntry 18 }

sonusSs7Mtp2LinkStatSlProvAlgnFailed OBJECT-TYPE
    SYNTAX          Counter
    ACCESS          read-only
    STATUS          mandatory
    DESCRIPTION     
            "Link alignment/proving attempt failure."
    ::= { sonusSs7Mtp2LinkStatEntry 19 }

sonusSs7Mtp2LinkStatNumSuError OBJECT-TYPE
    SYNTAX          Counter
    ACCESS          read-only
    STATUS          mandatory
    DESCRIPTION     
            "Number of SUs in error."
    ::= { sonusSs7Mtp2LinkStatEntry 20 }

sonusSs7Mtp2LinkStatNumNegAck OBJECT-TYPE
    SYNTAX          Counter
    ACCESS          read-only
    STATUS          mandatory
    DESCRIPTION     
            "Number of negative ack recv."
    ::= { sonusSs7Mtp2LinkStatEntry 21 }

sonusSs7Mtp2LinkStatNumSifSioOctetTx OBJECT-TYPE
    SYNTAX          Counter
    ACCESS          read-only
    STATUS          mandatory
    DESCRIPTION     
            "Number of MSU octets transmitted."
    ::= { sonusSs7Mtp2LinkStatEntry 22 }

sonusSs7Mtp2LinkStatNumOctetRtx OBJECT-TYPE
    SYNTAX          Counter
    ACCESS          read-only
    STATUS          mandatory
    DESCRIPTION     
            "Number of octets retransmitted."
    ::= { sonusSs7Mtp2LinkStatEntry 23 }

sonusSs7Mtp2LinkStatNumMsuTx OBJECT-TYPE
    SYNTAX          Counter
    ACCESS          read-only
    STATUS          mandatory
    DESCRIPTION     
            "Number of MSUs transmitted."
    ::= { sonusSs7Mtp2LinkStatEntry 24 }

sonusSs7Mtp2LinkStatNumSifSioOctetRx OBJECT-TYPE
    SYNTAX          Counter
    ACCESS          read-only
    STATUS          mandatory
    DESCRIPTION     
            "Number of MSU octets recevied."
    ::= { sonusSs7Mtp2LinkStatEntry 25 }

sonusSs7Mtp2LinkStatNumMsuRx OBJECT-TYPE
    SYNTAX          Counter
    ACCESS          read-only
    STATUS          mandatory
    DESCRIPTION     
            "Number of MSUs received."
    ::= { sonusSs7Mtp2LinkStatEntry 26 }

sonusSs7Mtp2LinkStatErrApi OBJECT-TYPE
    SYNTAX          Counter
    ACCESS          read-only
    STATUS          mandatory
    DESCRIPTION     
            "Errors in incomming API's."
    ::= { sonusSs7Mtp2LinkStatEntry 27 }

sonusSs7Mtp2LinkStatErrMsg OBJECT-TYPE
    SYNTAX          Counter
    ACCESS          read-only
    STATUS          mandatory
    DESCRIPTION     
            "Erroneous messages received from peer."
    ::= { sonusSs7Mtp2LinkStatEntry 28 }

sonusSs7Mtp2LinkStatErrSys OBJECT-TYPE
    SYNTAX          Counter
    ACCESS          read-only
    STATUS          mandatory
    DESCRIPTION     
            "System call failures."
    ::= { sonusSs7Mtp2LinkStatEntry 29 }

sonusSs7Mtp2LinkStatErrSystemRes OBJECT-TYPE
    SYNTAX          Counter
    ACCESS          read-only
    STATUS          mandatory
    DESCRIPTION     
            "System resource failures."
    ::= { sonusSs7Mtp2LinkStatEntry 30 }

sonusSs7Mtp2LinkProfile OBJECT IDENTIFIER
    ::= { sonusSs7ServicesMIBObjects 9 }

sonusSs7Mtp2LinkProfileNextIndex OBJECT-TYPE
    SYNTAX          INTEGER
    ACCESS          read-only
    STATUS          mandatory
    DESCRIPTION     
            "The next valid index to use when creating a new sonusSs7Mtp2LinkProfileEntry"
    ::= { sonusSs7Mtp2LinkProfile 1 }

sonusSs7Mtp2LinkProfileTable OBJECT-TYPE
    SYNTAX          SEQUENCE OF SonusSs7Mtp2LinkProfileEntry
    ACCESS          not-accessible
    STATUS          mandatory
    DESCRIPTION     
            "This table contains SS7 MTP2 link profile information."
    ::= { sonusSs7Mtp2LinkProfile 2 }

sonusSs7Mtp2LinkProfileEntry OBJECT-TYPE
    SYNTAX          SonusSs7Mtp2LinkProfileEntry
    ACCESS          not-accessible
    STATUS          mandatory
    DESCRIPTION     
            "This table describes the SS7 MTP2 link profiles that are configured
             on the GSX9000."
    INDEX           { sonusSs7Mtp2LinkProfileListIndex }
    ::= { sonusSs7Mtp2LinkProfileTable 1 }

SonusSs7Mtp2LinkProfileEntry ::=
    SEQUENCE {
        sonusSs7Mtp2LinkProfileListIndex INTEGER,
        sonusSs7Mtp2LinkProfileLinkName SonusName,
        sonusSs7Mtp2LinkProfileProtocol INTEGER,
        sonusSs7Mtp2LinkProfileLinkspeed INTEGER,
        sonusSs7Mtp2LinkProfileBitrate  INTEGER,
        sonusSs7Mtp2LinkProfileEcm      INTEGER,
        sonusSs7Mtp2LinkProfileT1       INTEGER,
        sonusSs7Mtp2LinkProfileT2       INTEGER,
        sonusSs7Mtp2LinkProfileT3       INTEGER,
        sonusSs7Mtp2LinkProfileT4n      INTEGER,
        sonusSs7Mtp2LinkProfileT4e      INTEGER,
        sonusSs7Mtp2LinkProfileT5       INTEGER,
        sonusSs7Mtp2LinkProfileT6       INTEGER,
        sonusSs7Mtp2LinkProfileT7       INTEGER,
        sonusSs7Mtp2LinkProfileTs       INTEGER,
        sonusSs7Mtp2LinkProfileTo       INTEGER,
        sonusSs7Mtp2LinkProfileTa       INTEGER,
        sonusSs7Mtp2LinkProfileTf       INTEGER,
        sonusSs7Mtp2LinkProfileTfn      INTEGER,
        sonusSs7Mtp2LinkProfileTfp      INTEGER,
        sonusSs7Mtp2LinkProfileTe       INTEGER,
        sonusSs7Mtp2LinkProfileAdminState SonusAdminState,
        sonusSs7Mtp2LinkProfileRowStatus RowStatus
    }

sonusSs7Mtp2LinkProfileListIndex OBJECT-TYPE
    SYNTAX          INTEGER (1..128)
    ACCESS          read-only
    STATUS          mandatory
    DESCRIPTION     
            "The index of the SS7 MTP2 link profile entry."
    ::= { sonusSs7Mtp2LinkProfileEntry 1 }

sonusSs7Mtp2LinkProfileLinkName OBJECT-TYPE
    SYNTAX          SonusName
    ACCESS          read-write
    STATUS          mandatory
    DESCRIPTION     
            "The name of the SS7 MTP2 link profile."
    ::= { sonusSs7Mtp2LinkProfileEntry 2 }

sonusSs7Mtp2LinkProfileProtocol OBJECT-TYPE
    SYNTAX          INTEGER { itu(1), ansi(2), jt(3) }
    ACCESS          read-write
    STATUS          mandatory
    DESCRIPTION     
            "The SS7 MTP2 stack type protocol variant."
    DEFVAL          { itu }
    ::= { sonusSs7Mtp2LinkProfileEntry 3 }

sonusSs7Mtp2LinkProfileLinkspeed OBJECT-TYPE
    SYNTAX          INTEGER { low(1), high(2) }
    ACCESS          read-write
    STATUS          mandatory
    DESCRIPTION     
            "The SS7 MTP2 linkspeed."
    DEFVAL          { low }
    ::= { sonusSs7Mtp2LinkProfileEntry 4 }

sonusSs7Mtp2LinkProfileBitrate OBJECT-TYPE
    SYNTAX          INTEGER { bitrate64(1), bitrate56(2), bitrate48(3) }
    ACCESS          read-write
    STATUS          mandatory
    DESCRIPTION     
            "The SS7 MTP2 bitrate in Kbps."
    DEFVAL          { bitrate64 }
    ::= { sonusSs7Mtp2LinkProfileEntry 5 }

sonusSs7Mtp2LinkProfileEcm OBJECT-TYPE
    SYNTAX          INTEGER { basic(1), pcr(2) }
    ACCESS          read-write
    STATUS          mandatory
    DESCRIPTION     
            "The SS7 MTP2 error correcton method."
    DEFVAL          { basic }
    ::= { sonusSs7Mtp2LinkProfileEntry 6 }

sonusSs7Mtp2LinkProfileT1 OBJECT-TYPE
    SYNTAX          INTEGER (0..65536)
    ACCESS          read-write
    STATUS          mandatory
    DESCRIPTION     
            "T1 timer."
    DEFVAL          { 1000 }
    ::= { sonusSs7Mtp2LinkProfileEntry 7 }

sonusSs7Mtp2LinkProfileT2 OBJECT-TYPE
    SYNTAX          INTEGER (0..65536)
    ACCESS          read-write
    STATUS          mandatory
    DESCRIPTION     
            "T2 timer."
    DEFVAL          { 1000 }
    ::= { sonusSs7Mtp2LinkProfileEntry 8 }

sonusSs7Mtp2LinkProfileT3 OBJECT-TYPE
    SYNTAX          INTEGER (0..65536)
    ACCESS          read-write
    STATUS          mandatory
    DESCRIPTION     
            "T3 timer."
    DEFVAL          { 1000 }
    ::= { sonusSs7Mtp2LinkProfileEntry 9 }

sonusSs7Mtp2LinkProfileT4n OBJECT-TYPE
    SYNTAX          INTEGER (0..65536)
    ACCESS          read-write
    STATUS          mandatory
    DESCRIPTION     
            "T4n timer."
    DEFVAL          { 1000 }
    ::= { sonusSs7Mtp2LinkProfileEntry 10 }

sonusSs7Mtp2LinkProfileT4e OBJECT-TYPE
    SYNTAX          INTEGER (0..65536)
    ACCESS          read-write
    STATUS          mandatory
    DESCRIPTION     
            "T4e timer."
    DEFVAL          { 1000 }
    ::= { sonusSs7Mtp2LinkProfileEntry 11 }

sonusSs7Mtp2LinkProfileT5 OBJECT-TYPE
    SYNTAX          INTEGER (0..65536)
    ACCESS          read-write
    STATUS          mandatory
    DESCRIPTION     
            "T5 timer."
    DEFVAL          { 1000 }
    ::= { sonusSs7Mtp2LinkProfileEntry 12 }

sonusSs7Mtp2LinkProfileT6 OBJECT-TYPE
    SYNTAX          INTEGER (0..65536)
    ACCESS          read-write
    STATUS          mandatory
    DESCRIPTION     
            "T6 timer."
    DEFVAL          { 1000 }
    ::= { sonusSs7Mtp2LinkProfileEntry 13 }

sonusSs7Mtp2LinkProfileT7 OBJECT-TYPE
    SYNTAX          INTEGER (0..65536)
    ACCESS          read-write
    STATUS          mandatory
    DESCRIPTION     
            "T7 timer."
    DEFVAL          { 1000 }
    ::= { sonusSs7Mtp2LinkProfileEntry 14 }

sonusSs7Mtp2LinkProfileTs OBJECT-TYPE
    SYNTAX          INTEGER (0..65536)
    ACCESS          read-write
    STATUS          mandatory
    DESCRIPTION     
            "Ts timer (Japan only)."
    DEFVAL          { 1000 }
    ::= { sonusSs7Mtp2LinkProfileEntry 15 }

sonusSs7Mtp2LinkProfileTo OBJECT-TYPE
    SYNTAX          INTEGER (0..65536)
    ACCESS          read-write
    STATUS          mandatory
    DESCRIPTION     
            "To timer (Japan only)."
    DEFVAL          { 1000 }
    ::= { sonusSs7Mtp2LinkProfileEntry 16 }

sonusSs7Mtp2LinkProfileTa OBJECT-TYPE
    SYNTAX          INTEGER (0..65536)
    ACCESS          read-write
    STATUS          mandatory
    DESCRIPTION     
            "Ta timer (Japan only)."
    DEFVAL          { 1000 }
    ::= { sonusSs7Mtp2LinkProfileEntry 17 }

sonusSs7Mtp2LinkProfileTf OBJECT-TYPE
    SYNTAX          INTEGER (0..65536)
    ACCESS          read-write
    STATUS          mandatory
    DESCRIPTION     
            "Tf timer (Japan only)."
    DEFVAL          { 1000 }
    ::= { sonusSs7Mtp2LinkProfileEntry 18 }

sonusSs7Mtp2LinkProfileTfn OBJECT-TYPE
    SYNTAX          INTEGER (0..65536)
    ACCESS          read-write
    STATUS          mandatory
    DESCRIPTION     
            "Tfn timer (Japan only)."
    DEFVAL          { 1000 }
    ::= { sonusSs7Mtp2LinkProfileEntry 19 }

sonusSs7Mtp2LinkProfileTfp OBJECT-TYPE
    SYNTAX          INTEGER (0..65536)
    ACCESS          read-write
    STATUS          mandatory
    DESCRIPTION     
            "Tfp timer (Japan only)."
    DEFVAL          { 1000 }
    ::= { sonusSs7Mtp2LinkProfileEntry 20 }

sonusSs7Mtp2LinkProfileTe OBJECT-TYPE
    SYNTAX          INTEGER (0..65536)
    ACCESS          read-write
    STATUS          mandatory
    DESCRIPTION     
            "Te timer (Japan only)."
    DEFVAL          { 1000 }
    ::= { sonusSs7Mtp2LinkProfileEntry 21 }

sonusSs7Mtp2LinkProfileAdminState OBJECT-TYPE
    SYNTAX          SonusAdminState
    ACCESS          read-write
    STATUS          mandatory
    DESCRIPTION     
            "The admin state of the SS7 MTP2 link profile."
    DEFVAL          { disabled }
    ::= { sonusSs7Mtp2LinkProfileEntry 22 }

sonusSs7Mtp2LinkProfileRowStatus OBJECT-TYPE
    SYNTAX          RowStatus
    ACCESS          read-write
    STATUS          mandatory
    DESCRIPTION     
            "The row status of the SS7 MTP2 link profile."
    ::= { sonusSs7Mtp2LinkProfileEntry 23 }

sonusSs7Mtp2LinkInServiceNotification TRAP-TYPE
    ENTERPRISE      sonusSs7Mtp2MIBNotifications
    VARIABLES       { sonusSs7Mtp2LinkName, sonusEventDescription, 
                      sonusEventClass, sonusEventLevel, sonusSequenceId, 
                      sonusEventTime }
--     STATUS          mandatory
    DESCRIPTION     
            "This trap indicates that the identified MTP2 link has 
             entered IN-SERVICE state."
    ::= 1

sonusSs7Mtp2LinkOutOfServiceNotification TRAP-TYPE
    ENTERPRISE      sonusSs7Mtp2MIBNotifications
    VARIABLES       { sonusSs7Mtp2LinkName, sonusEventDescription, 
                      sonusEventClass, sonusEventLevel, sonusSequenceId, 
                      sonusEventTime }
--     STATUS          mandatory
    DESCRIPTION     
            "This trap indicates that the identified MTP2 link has 
             entered OUT-OF-SERVICE state."
    ::= 2

END -- end of module SONUS-SS7-MTP2-MIB.
