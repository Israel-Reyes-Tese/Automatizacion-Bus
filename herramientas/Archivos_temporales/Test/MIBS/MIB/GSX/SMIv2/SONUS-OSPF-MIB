--
-- This SMIv2 module has been generated by smidump 0.2-cvs. Do not edit.
--

SONUS-OSPF-MIB DEFINITIONS ::= BEGIN

IMPORTS
    Ipv6Address
        FROM IPV6-TC
    MODULE-COMPLIANCE, OBJECT-GROUP
        FROM SNMPv2-CONF
    Counter32, Gauge32, Integer32, IpAddress, MODULE-IDENTITY, 
    NOTIFICATION-TYPE, OBJECT-TYPE
        FROM SNMPv2-SMI
    RowStatus, TEXTUAL-CONVENTION, TruthValue
        FROM SNMPv2-TC
    sonusEventClass, sonusEventDescription, sonusEventLevel, 
    sonusEventTime, sonusSequenceId
        FROM SONUS-COMMON-MIB
    sonusPacketMIBs
        FROM SONUS-SMI
    SonusShelfIndex, SonusSlotIndex
        FROM SONUS-TC;

sonusOspf MODULE-IDENTITY
    LAST-UPDATED    "201505200000Z"
    ORGANIZATION    
            "IETF OSPF Working Group"
    CONTACT-INFO    
            "   Customer Support    
             Sonus Networks, Inc.
             7 Technology Park Drive
             Westford, MA 01886
             USA
             
             Tel: 978-614-8100
             Fax: 978-614-8609"
    DESCRIPTION     
            "The MIB module to describe the OSPF Version 2
             Protocol"
    ::= { sonusPacketMIBs 6 }


SonusOspfAreaID ::= TEXTUAL-CONVENTION
    STATUS          current
    DESCRIPTION     
            "An OSPF Area Identifier."
    SYNTAX          IpAddress

SonusOspfRouterID ::= TEXTUAL-CONVENTION
    STATUS          current
    DESCRIPTION     
            "A OSPF Router Identifier."
    SYNTAX          IpAddress

SonusOspfMetric ::= TEXTUAL-CONVENTION
    STATUS          current
    DESCRIPTION     
            "The OSPF Internal Metric."
    SYNTAX          Integer32 (0..65535)

SonusOspfBigMetric ::= TEXTUAL-CONVENTION
    STATUS          current
    DESCRIPTION     
            "The OSPF External Metric."
    SYNTAX          Integer32 (0..16777215)

SonusOspfStatus ::= TEXTUAL-CONVENTION
    STATUS          current
    DESCRIPTION     
            "The status of an interface: 'enabled' indicates that
             it is willing to communicate with other OSPF Routers,
             while 'disabled' indicates that it is not."
    SYNTAX          INTEGER { enabled(1), disabled(2) }

SonusOspfPositiveInteger ::= TEXTUAL-CONVENTION
    STATUS          current
    DESCRIPTION     
            "A positive integer. Values in excess are precluded as
             unnecessary and prone to interoperability issues."
    SYNTAX          Integer32 (0..2147483647)

SonusOspfHelloRange ::= TEXTUAL-CONVENTION
    STATUS          current
    DESCRIPTION     
            "The range of intervals on which hello messages are
             exchanged."
    SYNTAX          Integer32 (1..65535)

SonusOspfUpToMaxAge ::= TEXTUAL-CONVENTION
    STATUS          current
    DESCRIPTION     
            "The values that one might find or configure for
             variables bounded by the maximum age of an LSA."
    SYNTAX          Integer32 (0..3600)

SonusOspfInterfaceIndex ::= TEXTUAL-CONVENTION
    STATUS          current
    DESCRIPTION     
            "The range of ifIndex."
    SYNTAX          Integer32

SonusOspfDesignatedRouterPriority ::= TEXTUAL-CONVENTION
    STATUS          current
    DESCRIPTION     
            "The values defined for the priority of a system for
             becoming the designated router."
    SYNTAX          Integer32 (0..255)

SonusOspfTOSType ::= TEXTUAL-CONVENTION
    STATUS          current
    DESCRIPTION     
            "Type of Service is defined as a mapping to the IP Type of
             Service Flags as defined in the IP Forwarding Table MIB
             
             +-----+-----+-----+-----+-----+-----+-----+-----+
             |                 |                       |     |
             |   PRECEDENCE    |    TYPE OF SERVICE    |  0  |
             |                 |                       |     |
             +-----+-----+-----+-----+-----+-----+-----+-----+
             
                      IP TOS                IP TOS
                 Field     Policy      Field     Policy
             
                 Contents    Code      Contents    Code
                 0 0 0 0  ==>   0      0 0 0 1  ==>   2
                 0 0 1 0  ==>   4      0 0 1 1  ==>   6
                 0 1 0 0  ==>   8      0 1 0 1  ==>  10
                 0 1 1 0  ==>  12      0 1 1 1  ==>  14
                 1 0 0 0  ==>  16      1 0 0 1  ==>  18
                 1 0 1 0  ==>  20      1 0 1 1  ==>  22
                 1 1 0 0  ==>  24      1 1 0 1  ==>  26
                 1 1 1 0  ==>  28      1 1 1 1  ==>  30
             
             The remaining values are left for future definition."
    SYNTAX          Integer32 (0..30)

sonusOspfGeneralGroupTable OBJECT-TYPE
    SYNTAX          SEQUENCE OF SonusOspfGeneralGroupEntry
    MAX-ACCESS      not-accessible
    STATUS          current
    DESCRIPTION     
            "The collection of OSPF General Group information for the
             specified instance."
    ::= { sonusOspf 1 }

sonusOspfGeneralGroupEntry OBJECT-TYPE
    SYNTAX          SonusOspfGeneralGroupEntry
    MAX-ACCESS      not-accessible
    STATUS          current
    DESCRIPTION     
            "The collection of OSPF General Group information for the
             specified instance."
    INDEX           { sonusOspfGeneralGroupShelf, 
                      sonusOspfGeneralGroupSlot, 
                      sonusOspfGeneralGroupInstance }
    ::= { sonusOspfGeneralGroupTable 1 }

SonusOspfGeneralGroupEntry ::=
    SEQUENCE {
        sonusOspfGeneralGroupShelf      SonusShelfIndex,
        sonusOspfGeneralGroupSlot       SonusSlotIndex,
        sonusOspfGeneralGroupInstance   Integer32,
        sonusOspfGeneralGroupStatus     RowStatus,
        sonusOspfRouterId               SonusOspfRouterID,
        sonusOspfAdminStat              SonusOspfStatus,
        sonusOspfVersionNumber          INTEGER,
        sonusOspfAreaBdrRtrStatus       TruthValue,
        sonusOspfASBdrRtrStatus         TruthValue,
        sonusOspfExternLsaCount         Gauge32,
        sonusOspfExternLsaCksumSum      Integer32,
        sonusOspfTOSSupport             TruthValue,
        sonusOspfOriginateNewLsas       Counter32,
        sonusOspfRxNewLsas              Counter32,
        sonusOspfExtLsdbLimit           Integer32,
        sonusOspfMulticastExtensions    Integer32,
        sonusOspfExitOverflowInterval   SonusOspfPositiveInteger,
        sonusOspfDemandExtensions       TruthValue,
        sonusOspfGeneralAreaId          SonusOspfAreaID,
        sonusOspfAreaType               INTEGER,
        sonusOspfMnsAreaId              SonusOspfAreaID,
        sonusOspfPnsAreaId              SonusOspfAreaID,
        sonusOspfAreaRouteCalcType      INTEGER,
        sonusOspfMnsAreaRouteCalcType   INTEGER,
        sonusOspfPnsAreaRouteCalcType   INTEGER,
        sonusOspfMode                   INTEGER,
        sonusOspfStandbyCostOffset      Integer32,
        sonusOspfAdvHostRouteFrmSby     SonusOspfStatus
    }

sonusOspfGeneralGroupShelf OBJECT-TYPE
    SYNTAX          SonusShelfIndex
    MAX-ACCESS      read-only
    STATUS          current
    DESCRIPTION     
            "A 32-bit integer identifying the OSPF Shelf"
    ::= { sonusOspfGeneralGroupEntry 1 }

sonusOspfGeneralGroupSlot OBJECT-TYPE
    SYNTAX          SonusSlotIndex
    MAX-ACCESS      read-only
    STATUS          current
    DESCRIPTION     
            "A 32-bit integer identifying the OSPF slot. 
             This is no longer an active general group table index"
    ::= { sonusOspfGeneralGroupEntry 2 }

sonusOspfGeneralGroupInstance OBJECT-TYPE
    SYNTAX          Integer32
    MAX-ACCESS      read-only
    STATUS          current
    DESCRIPTION     
            "A 32-bit integer identifying the OSPF Instance"
    ::= { sonusOspfGeneralGroupEntry 3 }

sonusOspfGeneralGroupStatus OBJECT-TYPE
    SYNTAX          RowStatus
    MAX-ACCESS      read-write
    STATUS          current
    DESCRIPTION     
            "This variable displays the status of  the  en-
             try.  Setting it to 'invalid' has the effect of
             rendering it inoperative.  The internal  effect
             (row removal) is implementation dependent."
    ::= { sonusOspfGeneralGroupEntry 4 }

sonusOspfRouterId OBJECT-TYPE
    SYNTAX          SonusOspfRouterID
    MAX-ACCESS      read-write
    STATUS          current
    DESCRIPTION     
            "A  32-bit  integer  uniquely  identifying  the
             router in the Autonomous System.
             
             By  convention,  to  ensure  uniqueness,   this
             should  default  to  the  value  of  one of the
             router's IP interface addresses."
    REFERENCE       
            "OSPF Version 2, C.1 Global parameters"
    ::= { sonusOspfGeneralGroupEntry 5 }

sonusOspfAdminStat OBJECT-TYPE
    SYNTAX          SonusOspfStatus
    MAX-ACCESS      read-write
    STATUS          current
    DESCRIPTION     
            "The  administrative  status  of  OSPF  in  the
             router.   The  value 'enabled' denotes that the
             OSPF Process is active on at least  one  inter-
             face;  'disabled'  disables  it  on  all inter-
             faces."
    ::= { sonusOspfGeneralGroupEntry 6 }

sonusOspfVersionNumber OBJECT-TYPE
    SYNTAX          INTEGER { version2(2), version3(3) }
    MAX-ACCESS      read-write
    STATUS          current
    DESCRIPTION     
            "The current version number of the OSPF  proto-
             col is 2/3."
    REFERENCE       
            "OSPF Version 2, Title"
    ::= { sonusOspfGeneralGroupEntry 7 }

sonusOspfAreaBdrRtrStatus OBJECT-TYPE
    SYNTAX          TruthValue
    MAX-ACCESS      read-only
    STATUS          current
    DESCRIPTION     
            "A flag to note whether this router is an  area
             border router."
    REFERENCE       
            "OSPF Version 2, Section 3 Splitting the AS into
             Areas"
    ::= { sonusOspfGeneralGroupEntry 8 }

sonusOspfASBdrRtrStatus OBJECT-TYPE
    SYNTAX          TruthValue
    MAX-ACCESS      read-write
    STATUS          current
    DESCRIPTION     
            "A flag to note whether this router is  config-
             ured as an Autonomous System border router."
    REFERENCE       
            "OSPF Version 2, Section 3.3  Classification  of
             routers"
    ::= { sonusOspfGeneralGroupEntry 9 }

sonusOspfExternLsaCount OBJECT-TYPE
    SYNTAX          Gauge32
    MAX-ACCESS      read-only
    STATUS          current
    DESCRIPTION     
            "The number of external (LS type 5)  link-state
             advertisements in the link-state database."
    REFERENCE       
            "OSPF Version 2, Appendix A.4.5 AS external link
             advertisements"
    ::= { sonusOspfGeneralGroupEntry 10 }

sonusOspfExternLsaCksumSum OBJECT-TYPE
    SYNTAX          Integer32
    MAX-ACCESS      read-only
    STATUS          current
    DESCRIPTION     
            "The 32-bit unsigned sum of the LS checksums of
             the  external  link-state  advertisements  con-
             tained in the link-state  database.   This  sum
             can  be  used  to determine if there has been a
             change in a router's link state  database,  and
             to  compare  the  link-state  database  of  two
             routers."
    ::= { sonusOspfGeneralGroupEntry 11 }

sonusOspfTOSSupport OBJECT-TYPE
    SYNTAX          TruthValue
    MAX-ACCESS      read-write
    STATUS          current
    DESCRIPTION     
            "The router's support for type-of-service rout-
             ing."
    REFERENCE       
            "OSPF Version 2,  Appendix  F.1.2  Optional  TOS
             support"
    ::= { sonusOspfGeneralGroupEntry 12 }

sonusOspfOriginateNewLsas OBJECT-TYPE
    SYNTAX          Counter32
    MAX-ACCESS      read-only
    STATUS          current
    DESCRIPTION     
            "The number of  new  link-state  advertisements
             that  have been originated.  This number is in-
             cremented each time the router originates a new
             LSA."
    ::= { sonusOspfGeneralGroupEntry 13 }

sonusOspfRxNewLsas OBJECT-TYPE
    SYNTAX          Counter32
    MAX-ACCESS      read-only
    STATUS          current
    DESCRIPTION     
            "The number of  link-state  advertisements  re-
             ceived  determined  to  be  new instantiations.
             This number does not include  newer  instantia-
             tions  of self-originated link-state advertise-
             ments."
    ::= { sonusOspfGeneralGroupEntry 14 }

sonusOspfExtLsdbLimit OBJECT-TYPE
    SYNTAX          Integer32 (1..512)
    MAX-ACCESS      read-write
    STATUS          current
    DESCRIPTION     
            "The  maximum   number of   AS external LSAs than
             can be stored in the database.  
             
             When the number of AS-external-LSAs in   a  router's
             link-state  database  reaches ospfExtLsdbLimit, the 
             router  enters  Overflow-State.   The  router  never
             holds  more  than ospfExtLsdbLimit AS-external-LSAs
             in  its  database. "
    DEFVAL          { 256 }
    ::= { sonusOspfGeneralGroupEntry 15 }

sonusOspfMulticastExtensions OBJECT-TYPE
    SYNTAX          Integer32
    MAX-ACCESS      read-write
    STATUS          current
    DESCRIPTION     
            "A Bit Mask indicating whether  the  router  is
             forwarding  IP  multicast  (Class  D) datagrams
             based on the algorithms defined in  the  Multi-
             cast Extensions to OSPF.
             
             Bit 0, if set, indicates that  the  router  can
             forward  IP multicast datagrams in the router's
             directly attached areas (called intra-area mul-
             ticast routing).
             
             Bit 1, if set, indicates that  the  router  can
             forward  IP  multicast  datagrams  between OSPF
             areas (called inter-area multicast routing).
             
             Bit 2, if set, indicates that  the  router  can
             forward  IP  multicast  datagrams between Auto-
             nomous Systems (called inter-AS multicast rout-
             ing).
             
             Only certain combinations of bit  settings  are
             allowed,  namely: 0 (no multicast forwarding is
             enabled), 1 (intra-area multicasting  only),  3
             (intra-area  and  inter-area  multicasting),  5
             (intra-area and inter-AS  multicasting)  and  7
             (multicasting  everywhere). By default, no mul-
             ticast forwarding is enabled."
    DEFVAL          { 0 }
    ::= { sonusOspfGeneralGroupEntry 16 }

sonusOspfExitOverflowInterval OBJECT-TYPE
    SYNTAX          SonusOspfPositiveInteger
    MAX-ACCESS      read-write
    STATUS          current
    DESCRIPTION     
            "The number of  seconds  that,  after  entering
             OverflowState,  a  router will attempt to leave
             OverflowState. This allows the router to  again
             originate  non-default  AS-external-LSAs.  When
             set to 0, the router will not  leave  Overflow-
             State until restarted."
    DEFVAL          { 0 }
    ::= { sonusOspfGeneralGroupEntry 17 }

sonusOspfDemandExtensions OBJECT-TYPE
    SYNTAX          TruthValue
    MAX-ACCESS      read-write
    STATUS          current
    DESCRIPTION     
            "The router's support for demand routing."
    REFERENCE       
            "OSPF Version 2, Appendix on Demand Routing"
    ::= { sonusOspfGeneralGroupEntry 18 }

sonusOspfGeneralAreaId OBJECT-TYPE
    SYNTAX          SonusOspfAreaID
    MAX-ACCESS      read-write
    STATUS          current
    DESCRIPTION     
            "A 32-bit integer uniquely identifying an area.
             This field is currently used to communicate the configured
             area between CLI and NRS modules. Depending on the area
             type either MNS or PNS area values are set.  This value is
             never used directly by the OSPF engine"
    ::= { sonusOspfGeneralGroupEntry 19 }

sonusOspfAreaType OBJECT-TYPE
    SYNTAX          INTEGER { mns(1), pns(2), common(3) }
    MAX-ACCESS      read-write
    STATUS          current
    DESCRIPTION     
            "Type of the area Id.  This is used when configuring OSPF
             to indicate the area that is being configured is for MNS
             interfaces or PNS interfaces or common to all interfaces"
    ::= { sonusOspfGeneralGroupEntry 20 }

sonusOspfMnsAreaId OBJECT-TYPE
    SYNTAX          SonusOspfAreaID
    MAX-ACCESS      read-write
    STATUS          current
    DESCRIPTION     
            "A 32-bit integer uniquely identifying area where all MNS
             interfaces would be configured in"
    ::= { sonusOspfGeneralGroupEntry 21 }

sonusOspfPnsAreaId OBJECT-TYPE
    SYNTAX          SonusOspfAreaID
    MAX-ACCESS      read-write
    STATUS          current
    DESCRIPTION     
            "A 32-bit integer uniquely identifying area where all PNS
             interfaces would be configured in"
    ::= { sonusOspfGeneralGroupEntry 22 }

sonusOspfAreaRouteCalcType OBJECT-TYPE
    SYNTAX          INTEGER { spf(1), sorc(2) }
    MAX-ACCESS      read-write
    STATUS          current
    DESCRIPTION     
            "Type of the route calculation for the area.  This can be
             SPF or SORC.  Default is set to SORC. This variable is 
             used to simply set the MNS or PNS area route calculation
             types. i.e. a means of communication between CLI and
             NRS. This is of no use after the pertinent area calculation
             types are set."
    ::= { sonusOspfGeneralGroupEntry 23 }

sonusOspfMnsAreaRouteCalcType OBJECT-TYPE
    SYNTAX          INTEGER { spf(1), sorc(2) }
    MAX-ACCESS      read-only
    STATUS          current
    DESCRIPTION     
            "Type of the route calculation for the MNS area.  This can be
             SPF or SORC.  Default is set to SORC."
    ::= { sonusOspfGeneralGroupEntry 24 }

sonusOspfPnsAreaRouteCalcType OBJECT-TYPE
    SYNTAX          INTEGER { spf(1), sorc(2) }
    MAX-ACCESS      read-only
    STATUS          current
    DESCRIPTION     
            "Type of the route calculation for the PNS area.  This can be
             SPF or SORC.  Default is set to SORC."
    ::= { sonusOspfGeneralGroupEntry 25 }

sonusOspfMode OBJECT-TYPE
    SYNTAX          INTEGER { passive(1), active(2) }
    MAX-ACCESS      read-write
    STATUS          current
    DESCRIPTION     
            "Mode of SPF operation.  If it is set to passive, GSX
             wouldn't perform any SPF calculations thus, none of the
             OSPF learnt routes would be installed in the routing
             table."
    ::= { sonusOspfGeneralGroupEntry 26 }

sonusOspfStandbyCostOffset OBJECT-TYPE
    SYNTAX          Integer32 (2..14)
    MAX-ACCESS      read-write
    STATUS          current
    DESCRIPTION     
            "Cost offset for the routes advertised on standby
             interfaces. The upper limit is set 1 less than the actual 
             cost of the active interface"
    DEFVAL          { 2 }
    ::= { sonusOspfGeneralGroupEntry 27 }

sonusOspfAdvHostRouteFrmSby OBJECT-TYPE
    SYNTAX          SonusOspfStatus
    MAX-ACCESS      read-write
    STATUS          current
    DESCRIPTION     
            "Host routes should be advertised from standby card or not. By default
             they are advertised, so this setting is enabled by default. If it is disabled,
             host routes wont be advertised from standby card"
    DEFVAL          { 1 }
    ::= { sonusOspfGeneralGroupEntry 28 }

sonusOspfAreaTable OBJECT-TYPE
    SYNTAX          SEQUENCE OF SonusOspfAreaEntry
    MAX-ACCESS      not-accessible
    STATUS          current
    DESCRIPTION     
            "Information describing the configured  parame-
             ters  and cumulative statistics of the router's
             attached areas."
    REFERENCE       
            "OSPF Version 2, Section 6  The Area Data Struc-
             ture"
    ::= { sonusOspf 2 }

sonusOspfAreaEntry OBJECT-TYPE
    SYNTAX          SonusOspfAreaEntry
    MAX-ACCESS      not-accessible
    STATUS          current
    DESCRIPTION     
            "Information describing the configured  parame-
             ters  and  cumulative  statistics of one of the
             router's attached areas."
    INDEX           { sonusOspfAreaShelf, sonusOspfAreaSlot, 
                      sonusOspfAreaInstance, sonusOspfAreaId }
    ::= { sonusOspfAreaTable 1 }

SonusOspfAreaEntry ::=
    SEQUENCE {
        sonusOspfAreaId                 SonusOspfAreaID,
        sonusOspfAuthType               INTEGER,
        sonusOspfImportAsExtern         INTEGER,
        sonusOspfSpfRuns                Counter32,
        sonusOspfAreaBdrRtrCount        Gauge32,
        sonusOspfAsBdrRtrCount          Gauge32,
        sonusOspfAreaLsaCount           Gauge32,
        sonusOspfAreaLsaCksumSum        Integer32,
        sonusOspfAreaSummary            INTEGER,
        sonusOspfAreaStatus             RowStatus,
        sonusOspfAreaShelf              SonusShelfIndex,
        sonusOspfAreaSlot               SonusSlotIndex,
        sonusOspfAreaInstance           Integer32
    }

sonusOspfAreaId OBJECT-TYPE
    SYNTAX          SonusOspfAreaID
    MAX-ACCESS      read-only
    STATUS          current
    DESCRIPTION     
            "A 32-bit integer uniquely identifying an area.
             Area ID 0.0.0.0 is used for the OSPF backbone."
    REFERENCE       
            "OSPF Version 2, Appendix C.2 Area parameters"
    ::= { sonusOspfAreaEntry 1 }

sonusOspfAuthType OBJECT-TYPE
    SYNTAX          INTEGER { none(0), simplePassword(1), md5(2) }
    MAX-ACCESS      read-create
    STATUS          obsolete
    DESCRIPTION     
            "The authentication type specified for an area.
             Additional authentication types may be assigned
             locally on a per Area basis."
    REFERENCE       
            "OSPF Version 2, Appendix E Authentication"
    DEFVAL          { 0 }
    ::= { sonusOspfAreaEntry 2 }

sonusOspfImportAsExtern OBJECT-TYPE
    SYNTAX          INTEGER { importExternal(1), importNoExternal(2), 
                        importNssa(3) }
    MAX-ACCESS      read-create
    STATUS          current
    DESCRIPTION     
            "The area's support for importing  AS  external
             link- state advertisements."
    REFERENCE       
            "OSPF Version 2, Appendix C.2 Area parameters"
    DEFVAL          { importExternal }
    ::= { sonusOspfAreaEntry 3 }

sonusOspfSpfRuns OBJECT-TYPE
    SYNTAX          Counter32
    MAX-ACCESS      read-only
    STATUS          current
    DESCRIPTION     
            "The number of times that the intra-area  route
             table  has  been  calculated  using this area's
             link-state database.  This  is  typically  done
             using Dijkstra's algorithm."
    ::= { sonusOspfAreaEntry 4 }

sonusOspfAreaBdrRtrCount OBJECT-TYPE
    SYNTAX          Gauge32
    MAX-ACCESS      read-only
    STATUS          current
    DESCRIPTION     
            "The total number of area border routers reach-
             able within this area.  This is initially zero,
             and is calculated in each SPF Pass."
    ::= { sonusOspfAreaEntry 5 }

sonusOspfAsBdrRtrCount OBJECT-TYPE
    SYNTAX          Gauge32
    MAX-ACCESS      read-only
    STATUS          current
    DESCRIPTION     
            "The total number of Autonomous  System  border
             routers  reachable  within  this area.  This is
             initially zero, and is calculated in  each  SPF
             Pass."
    ::= { sonusOspfAreaEntry 6 }

sonusOspfAreaLsaCount OBJECT-TYPE
    SYNTAX          Gauge32
    MAX-ACCESS      read-only
    STATUS          current
    DESCRIPTION     
            "The total number of link-state  advertisements
             in  this  area's link-state database, excluding
             AS External LSA's."
    ::= { sonusOspfAreaEntry 7 }

sonusOspfAreaLsaCksumSum OBJECT-TYPE
    SYNTAX          Integer32
    MAX-ACCESS      read-only
    STATUS          current
    DESCRIPTION     
            "The 32-bit unsigned sum of the link-state  ad-
             vertisements'  LS  checksums  contained in this
             area's link-state database.  This sum  excludes
             external (LS type 5) link-state advertisements.
             The sum can be used to determine if  there  has
             been  a  change  in a router's link state data-
             base, and to compare the link-state database of
             two routers."
    DEFVAL          { 0 }
    ::= { sonusOspfAreaEntry 8 }

sonusOspfAreaSummary OBJECT-TYPE
    SYNTAX          INTEGER { noAreaSummary(1), sendAreaSummary(2) }
    MAX-ACCESS      read-create
    STATUS          current
    DESCRIPTION     
            "The variable ospfAreaSummary controls the  im-
             port  of  summary LSAs into stub areas.  It has
             no effect on other areas.
             
             If it is noAreaSummary, the router will neither
             originate  nor  propagate summary LSAs into the
             stub area.  It will rely entirely  on  its  de-
             fault route.
             
             If it is sendAreaSummary, the router will  both
             summarize and propagate summary LSAs."
    DEFVAL          { noAreaSummary }
    ::= { sonusOspfAreaEntry 9 }

sonusOspfAreaStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfAreaEntry 10 }

sonusOspfAreaShelf OBJECT-TYPE
    SYNTAX          SonusShelfIndex
    MAX-ACCESS      read-only
    STATUS          current
    DESCRIPTION     
            "A 32-bit integer identifying the OSPF Shelf"
    ::= { sonusOspfAreaEntry 11 }

sonusOspfAreaSlot OBJECT-TYPE
    SYNTAX          SonusSlotIndex
    MAX-ACCESS      read-only
    STATUS          current
    DESCRIPTION     
            "A 32-bit integer identifying the OSPF slot.
             This is no longer an active Area table index"
    ::= { sonusOspfAreaEntry 12 }

sonusOspfAreaInstance OBJECT-TYPE
    SYNTAX          Integer32
    MAX-ACCESS      read-only
    STATUS          current
    DESCRIPTION     
            "A 32-bit integer identifying the OSPF Instance"
    ::= { sonusOspfAreaEntry 13 }

sonusOspfStubAreaTable OBJECT-TYPE
    SYNTAX          SEQUENCE OF SonusOspfStubAreaEntry
    MAX-ACCESS      not-accessible
    STATUS          current
    DESCRIPTION     
            "The set of metrics that will be advertised  by
             a default Area Border Router into a stub area."
    REFERENCE       
            "OSPF Version 2, Appendix C.2, Area Parameters"
    ::= { sonusOspf 3 }

sonusOspfStubAreaEntry OBJECT-TYPE
    SYNTAX          SonusOspfStubAreaEntry
    MAX-ACCESS      not-accessible
    STATUS          current
    DESCRIPTION     
            "The metric for a given Type  of  Service  that
             will  be  advertised  by  a default Area Border
             Router into a stub area."
    REFERENCE       
            "OSPF Version 2, Appendix C.2, Area Parameters"
    INDEX           { sonusOspfStubAreaShelf, sonusOspfStubAreaSlot, 
                      sonusOspfStubAreaInstance, sonusOspfStubAreaId, 
                      sonusOspfStubTOS }
    ::= { sonusOspfStubAreaTable 1 }

SonusOspfStubAreaEntry ::=
    SEQUENCE {
        sonusOspfStubAreaId             SonusOspfAreaID,
        sonusOspfStubTOS                SonusOspfTOSType,
        sonusOspfStubMetric             SonusOspfBigMetric,
        sonusOspfStubStatus             RowStatus,
        sonusOspfStubMetricType         INTEGER,
        sonusOspfStubAreaShelf          SonusShelfIndex,
        sonusOspfStubAreaSlot           SonusSlotIndex,
        sonusOspfStubAreaInstance       Integer32
    }

sonusOspfStubAreaId OBJECT-TYPE
    SYNTAX          SonusOspfAreaID
    MAX-ACCESS      read-only
    STATUS          current
    DESCRIPTION     
            "The 32 bit identifier for the Stub  Area.   On
             creation,  this  can  be  derived  from the in-
             stance."
    ::= { sonusOspfStubAreaEntry 1 }

sonusOspfStubTOS OBJECT-TYPE
    SYNTAX          SonusOspfTOSType
    MAX-ACCESS      read-only
    STATUS          current
    DESCRIPTION     
            "The  Type  of  Service  associated  with   the
             metric.   On creation, this can be derived from
             the instance."
    ::= { sonusOspfStubAreaEntry 2 }

sonusOspfStubMetric OBJECT-TYPE
    SYNTAX          SonusOspfBigMetric
    MAX-ACCESS      read-create
    STATUS          current
    DESCRIPTION     
            "The metric value applied at the indicated type
             of  service.  By default, this equals the least
             metric at the type of service among the  inter-
             faces to other areas."
    ::= { sonusOspfStubAreaEntry 3 }

sonusOspfStubStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfStubAreaEntry 4 }

sonusOspfStubMetricType OBJECT-TYPE
    SYNTAX          INTEGER { ospfMetric(1), comparableCost(2), 
                        nonComparable(3) }
    MAX-ACCESS      read-create
    STATUS          current
    DESCRIPTION     
            "This variable displays the type of metric  ad-
             vertised as a default route."
    DEFVAL          { ospfMetric }
    ::= { sonusOspfStubAreaEntry 5 }

sonusOspfStubAreaShelf OBJECT-TYPE
    SYNTAX          SonusShelfIndex
    MAX-ACCESS      read-only
    STATUS          current
    DESCRIPTION     
            "A 32-bit integer identifying the OSPF Shelf"
    ::= { sonusOspfStubAreaEntry 6 }

sonusOspfStubAreaSlot OBJECT-TYPE
    SYNTAX          SonusSlotIndex
    MAX-ACCESS      read-only
    STATUS          current
    DESCRIPTION     
            "A 32-bit integer identifying the OSPF slot"
    ::= { sonusOspfStubAreaEntry 7 }

sonusOspfStubAreaInstance OBJECT-TYPE
    SYNTAX          Integer32
    MAX-ACCESS      read-only
    STATUS          current
    DESCRIPTION     
            "A 32-bit integer identifying the OSPF Instance"
    ::= { sonusOspfStubAreaEntry 8 }

sonusOspfLsdbTable OBJECT-TYPE
    SYNTAX          SEQUENCE OF SonusOspfLsdbEntry
    MAX-ACCESS      not-accessible
    STATUS          current
    DESCRIPTION     
            "The OSPF Process's Link State Database."
    REFERENCE       
            "OSPF Version 2, Section 12  Link  State  Adver-
             tisements"
    ::= { sonusOspf 4 }

sonusOspfLsdbEntry OBJECT-TYPE
    SYNTAX          SonusOspfLsdbEntry
    MAX-ACCESS      not-accessible
    STATUS          current
    DESCRIPTION     
            "A single Link State Advertisement."
    INDEX           { sonusOspfLsdbShelf, sonusOspfLsdbSlot, 
                      sonusOspfLsdbInstance, sonusOspfLsdbAreaId, 
                      sonusOspfLsdbType, sonusOspfLsdbLsid, 
                      sonusOspfLsdbRouterId }
    ::= { sonusOspfLsdbTable 1 }

SonusOspfLsdbEntry ::=
    SEQUENCE {
        sonusOspfLsdbAreaId             SonusOspfAreaID,
        sonusOspfLsdbType               INTEGER,
        sonusOspfLsdbLsid               IpAddress,
        sonusOspfLsdbRouterId           SonusOspfRouterID,
        sonusOspfLsdbSequence           Integer32,
        sonusOspfLsdbAge                Integer32,
        sonusOspfLsdbChecksum           Integer32,
        sonusOspfLsdbAdvertisement      OCTET STRING,
        sonusOspfLsdbShelf              SonusShelfIndex,
        sonusOspfLsdbSlot               SonusSlotIndex,
        sonusOspfLsdbInstance           Integer32
    }

sonusOspfLsdbAreaId OBJECT-TYPE
    SYNTAX          SonusOspfAreaID
    MAX-ACCESS      read-only
    STATUS          current
    DESCRIPTION     
            "The 32 bit identifier of the Area  from  which
             the LSA was received."
    REFERENCE       
            "OSPF Version 2, Appendix C.2 Area parameters"
    ::= { sonusOspfLsdbEntry 1 }

sonusOspfLsdbType OBJECT-TYPE
    SYNTAX          INTEGER { routerLink(1), networkLink(2), 
                        summaryLink(3), asSummaryLink(4), 
                        asExternalLink(5), multicastLink(6), 
                        nssaExternalLink(7), router-lsa(8193), 
                        network-lsa(8194), inter-prefix-lsa(8195), 
                        inter-router-lsa(8196), as-external-lsa(8197), 
                        group-membership-lsa(8198), nssa-lsa(8199), 
                        link-lsa(8200), intra-prefix-lsa(8201) }
    MAX-ACCESS      read-only
    STATUS          current
    DESCRIPTION     
            "The type  of  the  link  state  advertisement.
             Each  link state type has a separate advertise-
             ment format."
    REFERENCE       
            "OSPF Version 2/version 3, Appendix A.4.1 The  Link  State
             Advertisement header"
    ::= { sonusOspfLsdbEntry 2 }

sonusOspfLsdbLsid OBJECT-TYPE
    SYNTAX          IpAddress
    MAX-ACCESS      read-only
    STATUS          current
    DESCRIPTION     
            "The Link State ID is an LS Type Specific field
             containing either a Router ID or an IP Address;
             it identifies the piece of the  routing  domain
             that is being described by the advertisement."
    REFERENCE       
            "OSPF Version 2, Section 12.1.4 Link State ID"
    ::= { sonusOspfLsdbEntry 3 }

sonusOspfLsdbRouterId OBJECT-TYPE
    SYNTAX          SonusOspfRouterID
    MAX-ACCESS      read-only
    STATUS          current
    DESCRIPTION     
            "The 32 bit number that uniquely identifies the
             originating router in the Autonomous System."
    REFERENCE       
            "OSPF Version 2, Appendix C.1 Global parameters"
    ::= { sonusOspfLsdbEntry 4 }

sonusOspfLsdbSequence OBJECT-TYPE
    SYNTAX          Integer32
    MAX-ACCESS      read-only
    STATUS          current
    DESCRIPTION     
            "The sequence number field is a  signed  32-bit
             integer.   It  is used to detect old and dupli-
             cate link state advertisements.  The  space  of
             sequence  numbers  is  linearly  ordered.   The
             larger the sequence number the more recent  the
             advertisement."
    REFERENCE       
            "OSPF Version  2,  Section  12.1.6  LS  sequence
             number"
    ::= { sonusOspfLsdbEntry 5 }

sonusOspfLsdbAge OBJECT-TYPE
    SYNTAX          Integer32
    MAX-ACCESS      read-only
    STATUS          current
    DESCRIPTION     
            "This field is the age of the link state adver-
             tisement in seconds."
    REFERENCE       
            "OSPF Version 2, Section 12.1.1 LS age"
    ::= { sonusOspfLsdbEntry 6 }

sonusOspfLsdbChecksum OBJECT-TYPE
    SYNTAX          Integer32
    MAX-ACCESS      read-only
    STATUS          current
    DESCRIPTION     
            "This field is the  checksum  of  the  complete
             contents  of  the  advertisement, excepting the
             age field.  The age field is excepted  so  that
             an   advertisement's  age  can  be  incremented
             without updating the  checksum.   The  checksum
             used  is  the same that is used for ISO connec-
             tionless datagrams; it is commonly referred  to
             as the Fletcher checksum."
    REFERENCE       
            "OSPF Version 2, Section 12.1.7 LS checksum"
    ::= { sonusOspfLsdbEntry 7 }

sonusOspfLsdbAdvertisement OBJECT-TYPE
    SYNTAX          OCTET STRING (SIZE(1..128))
    MAX-ACCESS      read-only
    STATUS          current
    DESCRIPTION     
            "The entire Link State Advertisement, including
             its header."
    REFERENCE       
            "OSPF Version 2, Section 12  Link  State  Adver-
             tisements"
    ::= { sonusOspfLsdbEntry 8 }

sonusOspfLsdbShelf OBJECT-TYPE
    SYNTAX          SonusShelfIndex
    MAX-ACCESS      read-only
    STATUS          current
    DESCRIPTION     
            "A 32-bit integer identifying the OSPF Shelf"
    ::= { sonusOspfLsdbEntry 9 }

sonusOspfLsdbSlot OBJECT-TYPE
    SYNTAX          SonusSlotIndex
    MAX-ACCESS      read-only
    STATUS          current
    DESCRIPTION     
            "A 32-bit integer identifying the OSPF slot.
             This is no longer an active LSDB table index"
    ::= { sonusOspfLsdbEntry 10 }

sonusOspfLsdbInstance OBJECT-TYPE
    SYNTAX          Integer32
    MAX-ACCESS      read-only
    STATUS          current
    DESCRIPTION     
            "A 32-bit integer identifying the OSPF Instance"
    ::= { sonusOspfLsdbEntry 11 }

sonusOspfAreaRangeTable OBJECT-TYPE
    SYNTAX          SEQUENCE OF SonusOspfAreaRangeEntry
    MAX-ACCESS      not-accessible
    STATUS          obsolete
    DESCRIPTION     
            "A range if IP addresses  specified  by  an  IP
             address/IP  network  mask  pair.   For example,
             class B address range of X.X.X.X with a network
             mask  of  255.255.0.0 includes all IP addresses
             from X.X.0.0 to X.X.255.255"
    REFERENCE       
            "OSPF Version 2, Appendix C.2  Area parameters"
    ::= { sonusOspf 5 }

sonusOspfAreaRangeEntry OBJECT-TYPE
    SYNTAX          SonusOspfAreaRangeEntry
    MAX-ACCESS      not-accessible
    STATUS          obsolete
    DESCRIPTION     
            "A range if IP addresses  specified  by  an  IP
             address/IP  network  mask  pair.   For example,
             class B address range of X.X.X.X with a network
             mask  of  255.255.0.0 includes all IP addresses
             from X.X.0.0 to X.X.255.255"
    REFERENCE       
            "OSPF Version 2, Appendix C.2  Area parameters"
    INDEX           { sonusOspfAreaRangeShelf, sonusOspfAreaRangeSlot, 
                      sonusOspfAreaRangeInstance, 
                      sonusOspfAreaRangeAreaId, sonusOspfAreaRangeNet }
    ::= { sonusOspfAreaRangeTable 1 }

SonusOspfAreaRangeEntry ::=
    SEQUENCE {
        sonusOspfAreaRangeAreaId        SonusOspfAreaID,
        sonusOspfAreaRangeNet           IpAddress,
        sonusOspfAreaRangeMask          IpAddress,
        sonusOspfAreaRangeStatus        RowStatus,
        sonusOspfAreaRangeEffect        INTEGER,
        sonusOspfAreaRangeShelf         SonusShelfIndex,
        sonusOspfAreaRangeSlot          SonusSlotIndex,
        sonusOspfAreaRangeInstance      Integer32
    }

sonusOspfAreaRangeAreaId OBJECT-TYPE
    SYNTAX          SonusOspfAreaID
    MAX-ACCESS      read-only
    STATUS          obsolete
    DESCRIPTION     
            "The Area the Address  Range  is  to  be  found
             within."
    REFERENCE       
            "OSPF Version 2, Appendix C.2 Area parameters"
    ::= { sonusOspfAreaRangeEntry 1 }

sonusOspfAreaRangeNet OBJECT-TYPE
    SYNTAX          IpAddress
    MAX-ACCESS      read-only
    STATUS          obsolete
    DESCRIPTION     
            "The IP Address of the Net or Subnet  indicated
             by the range."
    REFERENCE       
            "OSPF Version 2, Appendix C.2 Area parameters"
    ::= { sonusOspfAreaRangeEntry 2 }

sonusOspfAreaRangeMask OBJECT-TYPE
    SYNTAX          IpAddress
    MAX-ACCESS      read-create
    STATUS          obsolete
    DESCRIPTION     
            "The Subnet Mask that pertains to  the  Net  or
             Subnet."
    REFERENCE       
            "OSPF Version 2, Appendix C.2 Area parameters"
    ::= { sonusOspfAreaRangeEntry 3 }

sonusOspfAreaRangeStatus OBJECT-TYPE
    SYNTAX          RowStatus
    MAX-ACCESS      read-create
    STATUS          obsolete
    DESCRIPTION     
            "This variable displays the status of  the  en-
             try.  Setting it to 'invalid' has the effect of
             rendering it inoperative.  The internal  effect
             (row removal) is implementation dependent."
    ::= { sonusOspfAreaRangeEntry 4 }

sonusOspfAreaRangeEffect OBJECT-TYPE
    SYNTAX          INTEGER { advertiseMatching(1), 
                        doNotAdvertiseMatching(2) }
    MAX-ACCESS      read-create
    STATUS          obsolete
    DESCRIPTION     
            "Subnets subsumed by ranges either trigger  the
             advertisement  of the indicated summary (adver-
             tiseMatching), or result in  the  subnet's  not
             being advertised at all outside the area."
    DEFVAL          { advertiseMatching }
    ::= { sonusOspfAreaRangeEntry 5 }

sonusOspfAreaRangeShelf OBJECT-TYPE
    SYNTAX          SonusShelfIndex
    MAX-ACCESS      read-only
    STATUS          current
    DESCRIPTION     
            "A 32-bit integer identifying the OSPF Shelf"
    ::= { sonusOspfAreaRangeEntry 6 }

sonusOspfAreaRangeSlot OBJECT-TYPE
    SYNTAX          SonusSlotIndex
    MAX-ACCESS      read-only
    STATUS          current
    DESCRIPTION     
            "A 32-bit integer identifying the OSPF slot"
    ::= { sonusOspfAreaRangeEntry 7 }

sonusOspfAreaRangeInstance OBJECT-TYPE
    SYNTAX          Integer32
    MAX-ACCESS      read-only
    STATUS          current
    DESCRIPTION     
            "A 32-bit integer identifying the OSPF Instance"
    ::= { sonusOspfAreaRangeEntry 8 }

sonusOspfHostTable OBJECT-TYPE
    SYNTAX          SEQUENCE OF SonusOspfHostEntry
    MAX-ACCESS      not-accessible
    STATUS          current
    DESCRIPTION     
            "The list of Hosts, and their metrics, that the
             router will advertise as host routes."
    REFERENCE       
            "OSPF Version 2, Appendix C.6  Host route param-
             eters"
    ::= { sonusOspf 6 }

sonusOspfHostEntry OBJECT-TYPE
    SYNTAX          SonusOspfHostEntry
    MAX-ACCESS      not-accessible
    STATUS          current
    DESCRIPTION     
            "A metric to be advertised, for a given type of
             service, when a given host is reachable."
    INDEX           { sonusOspfHostShelf, sonusOspfHostSlot, 
                      sonusOspfHostInstance, sonusOspfHostIpAddress }
    ::= { sonusOspfHostTable 1 }

SonusOspfHostEntry ::=
    SEQUENCE {
        sonusOspfHostIpAddress          IpAddress,
        sonusOspfHostTOS                SonusOspfTOSType,
        sonusOspfHostMetric             SonusOspfMetric,
        sonusOspfHostStatus             RowStatus,
        sonusOspfHostAreaID             SonusOspfAreaID,
        sonusOspfHostAdminStat          SonusOspfStatus,
        sonusOspfHostType               INTEGER,
        sonusOspfHostReachableSlot      Integer32,
        sonusOspfHostReachableIntf      IpAddress,
        sonusOspfHostShelf              SonusShelfIndex,
        sonusOspfHostSlot               SonusSlotIndex,
        sonusOspfHostInstance           Integer32
    }

sonusOspfHostIpAddress OBJECT-TYPE
    SYNTAX          IpAddress
    MAX-ACCESS      read-only
    STATUS          current
    DESCRIPTION     
            "The IP Address of the Host."
    REFERENCE       
            "OSPF Version 2, Appendix C.6 Host route parame-
             ters"
    ::= { sonusOspfHostEntry 1 }

sonusOspfHostTOS OBJECT-TYPE
    SYNTAX          SonusOspfTOSType
    MAX-ACCESS      read-only
    STATUS          current
    DESCRIPTION     
            "The Type of Service of the route being config-
             ured."
    REFERENCE       
            "OSPF Version 2, Appendix C.6 Host route parame-
             ters"
    ::= { sonusOspfHostEntry 2 }

sonusOspfHostMetric OBJECT-TYPE
    SYNTAX          SonusOspfMetric
    MAX-ACCESS      read-create
    STATUS          current
    DESCRIPTION     
            "The Metric to be advertised."
    REFERENCE       
            "OSPF Version 2, Appendix C.6 Host route parame-
             ters"
    ::= { sonusOspfHostEntry 3 }

sonusOspfHostStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfHostEntry 4 }

sonusOspfHostAreaID OBJECT-TYPE
    SYNTAX          SonusOspfAreaID
    MAX-ACCESS      read-only
    STATUS          current
    DESCRIPTION     
            "The Area the Host Entry is to be found within.
             By  default, the area that a subsuming OSPF in-
             terface is in, or 0.0.0.0"
    REFERENCE       
            "OSPF Version 2, Appendix C.2 Area parameters"
    ::= { sonusOspfHostEntry 5 }

sonusOspfHostAdminStat OBJECT-TYPE
    SYNTAX          SonusOspfStatus
    MAX-ACCESS      read-create
    STATUS          current
    DESCRIPTION     
            "The OSPF  host route's  administrative  status.
             When enabled this host route will be advertised as
             an internal route.  When disabled, OSPF stops to
             advertise this route."
    DEFVAL          { enabled }
    ::= { sonusOspfHostEntry 6 }

sonusOspfHostType OBJECT-TYPE
    SYNTAX          INTEGER { mns-reachable(1), pns-reachable(2), 
                        normal(3) }
    MAX-ACCESS      read-create
    STATUS          current
    DESCRIPTION     
            "The type of host route.  MNS signaling and management
             addresses are reachable only from management interfaces.
             PNS signaling is reachable from any of the PNS interfaces
             on that card.  By default all host addresses are considered
             normal host routes.  Normal host routes are reachable from
             both MNS and PNS interfaces."
    DEFVAL          { normal }
    ::= { sonusOspfHostEntry 7 }

sonusOspfHostReachableSlot OBJECT-TYPE
    SYNTAX          Integer32 (0..16)
    MAX-ACCESS      read-create
    STATUS          current
    DESCRIPTION     
            "Specifies what particular card to use to receive traffic
             on.  This host route is advertised only on those interfaces
             on that card. Card 0 indicates host route is recahble from
             all slots."
    DEFVAL          { 0 }
    ::= { sonusOspfHostEntry 8 }

sonusOspfHostReachableIntf OBJECT-TYPE
    SYNTAX          IpAddress
    MAX-ACCESS      read-create
    STATUS          current
    DESCRIPTION     
            "Specifies what particular port on a given card the traffic
             meant for this host address will be received.  If it is
             MNS, traffic will be received on the corresponding port of
             the standby port also.  This value is useless unless
             ReachableSlot is > 0 "
    ::= { sonusOspfHostEntry 9 }

sonusOspfHostShelf OBJECT-TYPE
    SYNTAX          SonusShelfIndex
    MAX-ACCESS      read-only
    STATUS          current
    DESCRIPTION     
            "A 32-bit integer identifying the OSPF Shelf"
    ::= { sonusOspfHostEntry 10 }

sonusOspfHostSlot OBJECT-TYPE
    SYNTAX          SonusSlotIndex
    MAX-ACCESS      read-only
    STATUS          current
    DESCRIPTION     
            "A 32-bit integer identifying the OSPF slot.
             This is no longer an active OSPF host table index"
    ::= { sonusOspfHostEntry 11 }

sonusOspfHostInstance OBJECT-TYPE
    SYNTAX          Integer32
    MAX-ACCESS      read-only
    STATUS          current
    DESCRIPTION     
            "A 32-bit integer identifying the OSPF Instance"
    ::= { sonusOspfHostEntry 12 }

sonusOspfIfTable OBJECT-TYPE
    SYNTAX          SEQUENCE OF SonusOspfIfEntry
    MAX-ACCESS      not-accessible
    STATUS          current
    DESCRIPTION     
            "The OSPF Interface Table describes the  inter-
             faces from the viewpoint of OSPF."
    REFERENCE       
            "OSPF Version 2, Appendix C.3  Router  interface
             parameters"
    ::= { sonusOspf 7 }

sonusOspfIfEntry OBJECT-TYPE
    SYNTAX          SonusOspfIfEntry
    MAX-ACCESS      not-accessible
    STATUS          current
    DESCRIPTION     
            "The OSPF Interface Entry describes one  inter-
             face from the viewpoint of OSPF."
    INDEX           { sonusOspfIfShelf, sonusOspfIfSlot, 
                      sonusOspfIfInstance, sonusOspfIfIpVersion, 
                      sonusOspfIfIpAddress, sonusOspfIfIp6Address, 
                      sonusOspfAddressLessIf }
    ::= { sonusOspfIfTable 1 }

SonusOspfIfEntry ::=
    SEQUENCE {
        sonusOspfIfIpAddress            IpAddress,
        sonusOspfIfIpMask               IpAddress,
        sonusOspfAddressLessIf          Integer32,
        sonusOspfIfAreaId               SonusOspfAreaID,
        sonusOspfIfType                 INTEGER,
        sonusOspfIfAdminStat            SonusOspfStatus,
        sonusOspfIfRtrPriority          SonusOspfDesignatedRouterPriority,
        sonusOspfIfTransitDelay         SonusOspfUpToMaxAge,
        sonusOspfIfRetransInterval      SonusOspfUpToMaxAge,
        sonusOspfIfHelloInterval        SonusOspfHelloRange,
        sonusOspfIfRtrDeadInterval      SonusOspfPositiveInteger,
        sonusOspfIfPollInterval         SonusOspfPositiveInteger,
        sonusOspfIfState                INTEGER,
        sonusOspfIfDesignatedRouter     IpAddress,
        sonusOspfIfBackupDesignatedRouter IpAddress,
        sonusOspfIfEvents               Counter32,
        sonusOspfIfAuthKey              OCTET STRING,
        sonusOspfIfStatus               RowStatus,
        sonusOspfIfMulticastForwarding  INTEGER,
        sonusOspfIfDemand               TruthValue,
        sonusOspfIfAuthType             Integer32,
        sonusOspfIfNbrAddr              IpAddress,
        sonusOspfIfLogicalAddr          IpAddress,
        sonusOspfIfShelf                SonusShelfIndex,
        sonusOspfIfSlot                 SonusSlotIndex,
        sonusOspfIfInstance             Integer32,
        sonusOspfIfNum                  Integer32,
        sonusOspfIfFlags                Integer32,
        sonusOspfIfIp6Address           Ipv6Address,
        sonusOspfIfIpVersion            INTEGER,
        sonusOspfIfPrefixlen            Integer32,
        sonusOspfIfNbrAddr6             Ipv6Address,
        sonusOspfIfIpLinkLocalAddress   Ipv6Address
    }

sonusOspfIfIpAddress OBJECT-TYPE
    SYNTAX          IpAddress
    MAX-ACCESS      read-only
    STATUS          current
    DESCRIPTION     
            "The IP address of this OSPF interface."
    ::= { sonusOspfIfEntry 1 }

sonusOspfIfIpMask OBJECT-TYPE
    SYNTAX          IpAddress
    MAX-ACCESS      read-only
    STATUS          current
    DESCRIPTION     
            "The IP Mask of this OSPF interface."
    ::= { sonusOspfIfEntry 2 }

sonusOspfAddressLessIf OBJECT-TYPE
    SYNTAX          Integer32
    MAX-ACCESS      read-only
    STATUS          current
    DESCRIPTION     
            "For the purpose of easing  the  instancing  of
             addressed   and  addressless  interfaces;  This
             variable takes the value 0 on  interfaces  with
             IP  Addresses,  and  the corresponding value of
             ifIndex for interfaces having no IP Address."
    ::= { sonusOspfIfEntry 3 }

sonusOspfIfAreaId OBJECT-TYPE
    SYNTAX          SonusOspfAreaID
    MAX-ACCESS      read-create
    STATUS          current
    DESCRIPTION     
            "A 32-bit integer uniquely identifying the area
             to  which  the  interface  connects.   Area  ID
             0.0.0.0 is used for the OSPF backbone."
    DEFVAL          { '00000000'H }
    ::= { sonusOspfIfEntry 4 }

sonusOspfIfType OBJECT-TYPE
    SYNTAX          INTEGER { broadcast(1), nbma(2), pointToPoint(3), 
                        pointToMultipoint(5) }
    MAX-ACCESS      read-create
    STATUS          current
    DESCRIPTION     
            "The OSPF interface type.
             
             By way of a default, this field may be intuited
             from the corresponding value of ifType.  Broad-
             cast LANs, such as  Ethernet  and  IEEE  802.5,
             take  the  value  'broadcast', X.25 and similar
             technologies take the value 'nbma',  and  links
             that  are  definitively point to point take the
             value 'pointToPoint'."
    ::= { sonusOspfIfEntry 5 }

sonusOspfIfAdminStat OBJECT-TYPE
    SYNTAX          SonusOspfStatus
    MAX-ACCESS      read-create
    STATUS          current
    DESCRIPTION     
            "The OSPF  interface's  administrative  status.
             The  value formed on the interface, and the in-
             terface will be advertised as an internal route
             to  some  area.   The  value 'disabled' denotes
             that the interface is external to OSPF."
    DEFVAL          { enabled }
    ::= { sonusOspfIfEntry 6 }

sonusOspfIfRtrPriority OBJECT-TYPE
    SYNTAX          SonusOspfDesignatedRouterPriority
    MAX-ACCESS      read-create
    STATUS          current
    DESCRIPTION     
            "The  priority  of  this  interface.   Used  in
             multi-access  networks,  this  field is used in
             the designated router election algorithm.   The
             value 0 signifies that the router is not eligi-
             ble to become the  designated  router  on  this
             particular  network.   In the event of a tie in
             this value, routers will use their Router ID as
             a tie breaker."
    DEFVAL          { 1 }
    ::= { sonusOspfIfEntry 7 }

sonusOspfIfTransitDelay OBJECT-TYPE
    SYNTAX          SonusOspfUpToMaxAge
    MAX-ACCESS      read-create
    STATUS          current
    DESCRIPTION     
            "The estimated number of seconds  it  takes  to
             transmit  a  link state update packet over this
             interface."
    DEFVAL          { 1 }
    ::= { sonusOspfIfEntry 8 }

sonusOspfIfRetransInterval OBJECT-TYPE
    SYNTAX          SonusOspfUpToMaxAge
    MAX-ACCESS      read-create
    STATUS          current
    DESCRIPTION     
            "The number of seconds between  link-state  ad-
             vertisement  retransmissions,  for  adjacencies
             belonging to this  interface.   This  value  is
             also used when retransmitting database descrip-
             tion and link-state request packets."
    DEFVAL          { 5 }
    ::= { sonusOspfIfEntry 9 }

sonusOspfIfHelloInterval OBJECT-TYPE
    SYNTAX          SonusOspfHelloRange
    MAX-ACCESS      read-create
    STATUS          current
    DESCRIPTION     
            "The length of time, in  seconds,  between  the
             Hello  packets that the router sends on the in-
             terface.  This value must be the same  for  all
             routers attached to a common network."
    DEFVAL          { 10 }
    ::= { sonusOspfIfEntry 10 }

sonusOspfIfRtrDeadInterval OBJECT-TYPE
    SYNTAX          SonusOspfPositiveInteger
    MAX-ACCESS      read-create
    STATUS          current
    DESCRIPTION     
            "The number of seconds that  a  router's  Hello
             packets  have  not been seen before it's neigh-
             bors declare the router down.  This  should  be
             some  multiple  of  the  Hello  interval.  This
             value must be the same for all routers attached
             to a common network."
    DEFVAL          { 40 }
    ::= { sonusOspfIfEntry 11 }

sonusOspfIfPollInterval OBJECT-TYPE
    SYNTAX          SonusOspfPositiveInteger
    MAX-ACCESS      read-create
    STATUS          current
    DESCRIPTION     
            "The larger time interval, in seconds,  between
             the  Hello  packets  sent  to  an inactive non-
             broadcast multi- access neighbor."
    DEFVAL          { 120 }
    ::= { sonusOspfIfEntry 12 }

sonusOspfIfState OBJECT-TYPE
    SYNTAX          INTEGER { down(1), loopback(2), waiting(3), 
                        pointToPoint(4), designatedRouter(5), 
                        backupDesignatedRouter(6), 
                        otherDesignatedRouter(7) }
    MAX-ACCESS      read-only
    STATUS          current
    DESCRIPTION     
            "The OSPF Interface State."
    DEFVAL          { down }
    ::= { sonusOspfIfEntry 13 }

sonusOspfIfDesignatedRouter OBJECT-TYPE
    SYNTAX          IpAddress
    MAX-ACCESS      read-only
    STATUS          current
    DESCRIPTION     
            "The IP Address of the Designated Router."
    DEFVAL          { '00000000'H }
    ::= { sonusOspfIfEntry 14 }

sonusOspfIfBackupDesignatedRouter OBJECT-TYPE
    SYNTAX          IpAddress
    MAX-ACCESS      read-only
    STATUS          current
    DESCRIPTION     
            "The  IP  Address  of  the  Backup   Designated
             Router."
    DEFVAL          { '00000000'H }
    ::= { sonusOspfIfEntry 15 }

sonusOspfIfEvents OBJECT-TYPE
    SYNTAX          Counter32
    MAX-ACCESS      read-only
    STATUS          current
    DESCRIPTION     
            "The number of times this  OSPF  interface  has
             changed its state, or an error has occurred."
    ::= { sonusOspfIfEntry 16 }

sonusOspfIfAuthKey OBJECT-TYPE
    SYNTAX          OCTET STRING (SIZE(0..256))
    MAX-ACCESS      read-create
    STATUS          current
    DESCRIPTION     
            "The Authentication Key.  If the Area's Author-
             ization  Type  is  simplePassword,  and the key
             length is shorter than 8 octets, the agent will
             left adjust and zero fill to 8 octets.
             
             Note that unauthenticated  interfaces  need  no
             authentication key, and simple password authen-
             tication cannot use a key of more  than  8  oc-
             tets.  Larger keys are useful only with authen-
             tication mechanisms not specified in this docu-
             ment.
             
             When read, ospfIfAuthKey always returns an  Oc-
             tet String of length zero."
    REFERENCE       
            "OSPF Version 2, Section 9  The  Interface  Data
             Structure"
    DEFVAL          { '0000000000000000'H }
    ::= { sonusOspfIfEntry 17 }

sonusOspfIfStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfIfEntry 18 }

sonusOspfIfMulticastForwarding OBJECT-TYPE
    SYNTAX          INTEGER { blocked(1), multicast(2), unicast(3) }
    MAX-ACCESS      read-create
    STATUS          current
    DESCRIPTION     
            "The way multicasts should  forwarded  on  this
             interface;  not  forwarded,  forwarded  as data
             link multicasts, or forwarded as data link uni-
             casts.   Data link multicasting is not meaning-
             ful on point to point and NBMA interfaces,  and
             setting ospfMulticastForwarding to 0 effective-
             ly disables all multicast forwarding."
    DEFVAL          { blocked }
    ::= { sonusOspfIfEntry 19 }

sonusOspfIfDemand OBJECT-TYPE
    SYNTAX          TruthValue
    MAX-ACCESS      read-create
    STATUS          current
    DESCRIPTION     
            "Indicates whether Demand OSPF procedures (hel-
             lo supression to FULL neighbors and setting the
             DoNotAge flag on proogated LSAs) should be per-
             formed on this interface."
    DEFVAL          { false }
    ::= { sonusOspfIfEntry 20 }

sonusOspfIfAuthType OBJECT-TYPE
    SYNTAX          Integer32 (0..255)
    MAX-ACCESS      read-create
    STATUS          current
    DESCRIPTION     
            "The authentication type specified for  an  in-
             terface.   Additional  authentication types may
             be assigned locally."
    REFERENCE       
            "OSPF Version 2, Appendix E Authentication"
    DEFVAL          { 0 }
    ::= { sonusOspfIfEntry 21 }

sonusOspfIfNbrAddr OBJECT-TYPE
    SYNTAX          IpAddress
    MAX-ACCESS      read-create
    STATUS          current
    DESCRIPTION     
            "The address of the neighbor.  This is not a mandatory
             field to configure.  However, on broadcast nets if GSX
             interface is configured as p2p, then this field helps in
             establishing adjacency with the correct neighbor"
    ::= { sonusOspfIfEntry 22 }

sonusOspfIfLogicalAddr OBJECT-TYPE
    SYNTAX          IpAddress
    MAX-ACCESS      read-create
    STATUS          current
    DESCRIPTION     
            "The Logical address of this OSPF interface. Valid only for
             OSPF interfaces on the PNS cards."
    ::= { sonusOspfIfEntry 23 }

sonusOspfIfShelf OBJECT-TYPE
    SYNTAX          SonusShelfIndex
    MAX-ACCESS      read-only
    STATUS          current
    DESCRIPTION     
            "A 32-bit integer identifying the OSPF Shelf"
    ::= { sonusOspfIfEntry 24 }

sonusOspfIfSlot OBJECT-TYPE
    SYNTAX          SonusSlotIndex
    MAX-ACCESS      read-only
    STATUS          current
    DESCRIPTION     
            "A 32-bit integer identifying the OSPF slot.
             This is no longer an active OSPF Interface table index"
    ::= { sonusOspfIfEntry 25 }

sonusOspfIfInstance OBJECT-TYPE
    SYNTAX          Integer32
    MAX-ACCESS      read-only
    STATUS          current
    DESCRIPTION     
            "A 32-bit integer identifying the OSPF Instance"
    ::= { sonusOspfIfEntry 26 }

sonusOspfIfNum OBJECT-TYPE
    SYNTAX          Integer32
    MAX-ACCESS      read-only
    STATUS          current
    DESCRIPTION     
            "Interface number of the OSPF interface."
    ::= { sonusOspfIfEntry 27 }

sonusOspfIfFlags OBJECT-TYPE
    SYNTAX          Integer32
    MAX-ACCESS      read-only
    STATUS          current
    DESCRIPTION     
            "Interface flags. such as type of interface (PNS/MNS) etc."
    ::= { sonusOspfIfEntry 28 }

sonusOspfIfIp6Address OBJECT-TYPE
    SYNTAX          Ipv6Address
    MAX-ACCESS      read-create
    STATUS          current
    DESCRIPTION     
            "The IPv6 address of this OSPF interface."
    ::= { sonusOspfIfEntry 29 }

sonusOspfIfIpVersion OBJECT-TYPE
    SYNTAX          INTEGER { afInet(2), afInet6(24) }
    MAX-ACCESS      read-only
    STATUS          current
    DESCRIPTION     
            "IP address version type"
    ::= { sonusOspfIfEntry 30 }

sonusOspfIfPrefixlen OBJECT-TYPE
    SYNTAX          Integer32
    MAX-ACCESS      read-only
    STATUS          current
    DESCRIPTION     
            "Ipv6 Prefix Length"
    ::= { sonusOspfIfEntry 31 }

sonusOspfIfNbrAddr6 OBJECT-TYPE
    SYNTAX          Ipv6Address
    MAX-ACCESS      read-create
    STATUS          current
    DESCRIPTION     
            "The address of the neighbor.  This is not a mandatory
             field to configure.  However, on broadcast nets if GSX
             interface is configured as p2p, then this field helps in
             establishing adjacency with the correct neighbor"
    ::= { sonusOspfIfEntry 32 }

sonusOspfIfIpLinkLocalAddress OBJECT-TYPE
    SYNTAX          Ipv6Address
    MAX-ACCESS      read-create
    STATUS          current
    DESCRIPTION     
            "Link Local address of this ospfv3 interface."
    ::= { sonusOspfIfEntry 33 }

sonusOspfIfMetricTable OBJECT-TYPE
    SYNTAX          SEQUENCE OF SonusOspfIfMetricEntry
    MAX-ACCESS      not-accessible
    STATUS          current
    DESCRIPTION     
            "The TOS metrics for  a  non-virtual  interface
             identified by the interface index."
    REFERENCE       
            "OSPF Version 2, Appendix C.3  Router  interface
             parameters"
    ::= { sonusOspf 8 }

sonusOspfIfMetricEntry OBJECT-TYPE
    SYNTAX          SonusOspfIfMetricEntry
    MAX-ACCESS      not-accessible
    STATUS          current
    DESCRIPTION     
            "A particular TOS metric for a non-virtual  in-
             terface identified by the interface index."
    REFERENCE       
            "OSPF Version 2, Appendix C.3  Router  interface
             parameters"
    INDEX           { sonusOspfIfMetricShelf, sonusOspfIfMetricSlot, 
                      sonusOspfIfMetricInstance, 
                      sonusOspfIfMetricIpAddress, 
                      sonusOspfIfMetricAddressLessIf, 
                      sonusOspfIfMetricTOS }
    ::= { sonusOspfIfMetricTable 1 }

SonusOspfIfMetricEntry ::=
    SEQUENCE {
        sonusOspfIfMetricIpAddress      IpAddress,
        sonusOspfIfMetricAddressLessIf  Integer32,
        sonusOspfIfMetricTOS            SonusOspfTOSType,
        sonusOspfIfMetricValue          SonusOspfMetric,
        sonusOspfIfMetricStatus         RowStatus,
        sonusOspfIfMetricShelf          SonusShelfIndex,
        sonusOspfIfMetricSlot           SonusSlotIndex,
        sonusOspfIfMetricInstance       Integer32
    }

sonusOspfIfMetricIpAddress OBJECT-TYPE
    SYNTAX          IpAddress
    MAX-ACCESS      read-only
    STATUS          current
    DESCRIPTION     
            "The IP address of this OSPF interface.  On row
             creation,  this  can  be  derived  from the in-
             stance."
    ::= { sonusOspfIfMetricEntry 1 }

sonusOspfIfMetricAddressLessIf OBJECT-TYPE
    SYNTAX          Integer32
    MAX-ACCESS      read-only
    STATUS          current
    DESCRIPTION     
            "For the purpose of easing  the  instancing  of
             addressed   and  addressless  interfaces;  This
             variable takes the value 0 on  interfaces  with
             IP  Addresses, and the value of ifIndex for in-
             terfaces having no IP Address.   On  row  crea-
             tion, this can be derived from the instance."
    ::= { sonusOspfIfMetricEntry 2 }

sonusOspfIfMetricTOS OBJECT-TYPE
    SYNTAX          SonusOspfTOSType
    MAX-ACCESS      read-only
    STATUS          current
    DESCRIPTION     
            "The type of service metric  being  referenced.
             On  row  creation, this can be derived from the
             instance."
    ::= { sonusOspfIfMetricEntry 3 }

sonusOspfIfMetricValue OBJECT-TYPE
    SYNTAX          SonusOspfMetric
    MAX-ACCESS      read-create
    STATUS          current
    DESCRIPTION     
            "The metric of using this type  of  service  on
             this interface.  The default value of the TOS 0
             Metric is 10^8 / ifSpeed."
    ::= { sonusOspfIfMetricEntry 4 }

sonusOspfIfMetricStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfIfMetricEntry 5 }

sonusOspfIfMetricShelf OBJECT-TYPE
    SYNTAX          SonusShelfIndex
    MAX-ACCESS      read-only
    STATUS          current
    DESCRIPTION     
            "A 32-bit integer identifying the OSPF Shelf"
    ::= { sonusOspfIfMetricEntry 6 }

sonusOspfIfMetricSlot OBJECT-TYPE
    SYNTAX          SonusSlotIndex
    MAX-ACCESS      read-only
    STATUS          current
    DESCRIPTION     
            "A 32-bit integer identifying the OSPF Slot"
    ::= { sonusOspfIfMetricEntry 7 }

sonusOspfIfMetricInstance OBJECT-TYPE
    SYNTAX          Integer32
    MAX-ACCESS      read-only
    STATUS          current
    DESCRIPTION     
            "A 32-bit integer identifying the OSPF Instance"
    ::= { sonusOspfIfMetricEntry 8 }

sonusOspfVirtIfTable OBJECT-TYPE
    SYNTAX          SEQUENCE OF SonusOspfVirtIfEntry
    MAX-ACCESS      not-accessible
    STATUS          current
    DESCRIPTION     
            "Information about this router's virtual inter-
             faces."
    REFERENCE       
            "OSPF Version  2,  Appendix  C.4   Virtual  link
             parameters"
    ::= { sonusOspf 9 }

sonusOspfVirtIfEntry OBJECT-TYPE
    SYNTAX          SonusOspfVirtIfEntry
    MAX-ACCESS      not-accessible
    STATUS          current
    DESCRIPTION     
            "Information about a single Virtual Interface."
    INDEX           { sonusOspfVirtIfShelf, sonusOspfVirtIfSlot, 
                      sonusOspfVirtIfInstance, sonusOspfVirtIfAreaId, 
                      sonusOspfVirtIfNeighbor }
    ::= { sonusOspfVirtIfTable 1 }

SonusOspfVirtIfEntry ::=
    SEQUENCE {
        sonusOspfVirtIfAreaId           SonusOspfAreaID,
        sonusOspfVirtIfNeighbor         SonusOspfRouterID,
        sonusOspfVirtIfTransitDelay     SonusOspfUpToMaxAge,
        sonusOspfVirtIfRetransInterval  SonusOspfUpToMaxAge,
        sonusOspfVirtIfHelloInterval    SonusOspfHelloRange,
        sonusOspfVirtIfRtrDeadInterval  SonusOspfPositiveInteger,
        sonusOspfVirtIfState            INTEGER,
        sonusOspfVirtIfEvents           Counter32,
        sonusOspfVirtIfAuthKey          OCTET STRING,
        sonusOspfVirtIfStatus           RowStatus,
        sonusOspfVirtIfAuthType         Integer32,
        sonusOspfVirtIfShelf            SonusShelfIndex,
        sonusOspfVirtIfSlot             SonusSlotIndex,
        sonusOspfVirtIfInstance         Integer32
    }

sonusOspfVirtIfAreaId OBJECT-TYPE
    SYNTAX          SonusOspfAreaID
    MAX-ACCESS      read-only
    STATUS          current
    DESCRIPTION     
            "The  Transit  Area  that  the   Virtual   Link
             traverses.  By definition, this is not 0.0.0.0"
    ::= { sonusOspfVirtIfEntry 1 }

sonusOspfVirtIfNeighbor OBJECT-TYPE
    SYNTAX          SonusOspfRouterID
    MAX-ACCESS      read-only
    STATUS          current
    DESCRIPTION     
            "The Router ID of the Virtual Neighbor."
    ::= { sonusOspfVirtIfEntry 2 }

sonusOspfVirtIfTransitDelay OBJECT-TYPE
    SYNTAX          SonusOspfUpToMaxAge
    MAX-ACCESS      read-create
    STATUS          current
    DESCRIPTION     
            "The estimated number of seconds  it  takes  to
             transmit  a link- state update packet over this
             interface."
    DEFVAL          { 1 }
    ::= { sonusOspfVirtIfEntry 3 }

sonusOspfVirtIfRetransInterval OBJECT-TYPE
    SYNTAX          SonusOspfUpToMaxAge
    MAX-ACCESS      read-create
    STATUS          current
    DESCRIPTION     
            "The number of seconds between  link-state  ad-
             vertisement  retransmissions,  for  adjacencies
             belonging to this  interface.   This  value  is
             also used when retransmitting database descrip-
             tion  and  link-state  request  packets.   This
             value  should  be well over the expected round-
             trip time."
    DEFVAL          { 5 }
    ::= { sonusOspfVirtIfEntry 4 }

sonusOspfVirtIfHelloInterval OBJECT-TYPE
    SYNTAX          SonusOspfHelloRange
    MAX-ACCESS      read-create
    STATUS          current
    DESCRIPTION     
            "The length of time, in  seconds,  between  the
             Hello  packets that the router sends on the in-
             terface.  This value must be the same  for  the
             virtual neighbor."
    DEFVAL          { 10 }
    ::= { sonusOspfVirtIfEntry 5 }

sonusOspfVirtIfRtrDeadInterval OBJECT-TYPE
    SYNTAX          SonusOspfPositiveInteger
    MAX-ACCESS      read-create
    STATUS          current
    DESCRIPTION     
            "The number of seconds that  a  router's  Hello
             packets  have  not been seen before it's neigh-
             bors declare the router down.  This  should  be
             some  multiple  of  the  Hello  interval.  This
             value must be the same for the  virtual  neigh-
             bor."
    DEFVAL          { 60 }
    ::= { sonusOspfVirtIfEntry 6 }

sonusOspfVirtIfState OBJECT-TYPE
    SYNTAX          INTEGER { down(1), pointToPoint(4) }
    MAX-ACCESS      read-only
    STATUS          current
    DESCRIPTION     
            "OSPF virtual interface states."
    DEFVAL          { down }
    ::= { sonusOspfVirtIfEntry 7 }

sonusOspfVirtIfEvents OBJECT-TYPE
    SYNTAX          Counter32
    MAX-ACCESS      read-only
    STATUS          current
    DESCRIPTION     
            "The number of state changes or error events on
             this Virtual Link"
    ::= { sonusOspfVirtIfEntry 8 }

sonusOspfVirtIfAuthKey OBJECT-TYPE
    SYNTAX          OCTET STRING (SIZE(0..256))
    MAX-ACCESS      read-create
    STATUS          current
    DESCRIPTION     
            "If Authentication Type is simplePassword,  the
             device  will left adjust and zero fill to 8 oc-
             tets.
             
             Note that unauthenticated  interfaces  need  no
             authentication key, and simple password authen-
             tication cannot use a key of more  than  8  oc-
             tets.  Larger keys are useful only with authen-
             tication mechanisms not specified in this docu-
             ment.
             
             When  read,  ospfVifAuthKey  always  returns  a
             string of length zero."
    REFERENCE       
            "OSPF Version 2, Section 9  The  Interface  Data
             Structure"
    DEFVAL          { '0000000000000000'H }
    ::= { sonusOspfVirtIfEntry 9 }

sonusOspfVirtIfStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfVirtIfEntry 10 }

sonusOspfVirtIfAuthType OBJECT-TYPE
    SYNTAX          Integer32 (0..255)
    MAX-ACCESS      read-create
    STATUS          current
    DESCRIPTION     
            "The authentication type specified for a virtu-
             al  interface.  Additional authentication types
             may be assigned locally."
    REFERENCE       
            "OSPF Version 2, Appendix E Authentication"
    DEFVAL          { 0 }
    ::= { sonusOspfVirtIfEntry 11 }

sonusOspfVirtIfShelf OBJECT-TYPE
    SYNTAX          SonusShelfIndex
    MAX-ACCESS      read-only
    STATUS          current
    DESCRIPTION     
            "A 32-bit integer identifying the OSPF Shelf"
    ::= { sonusOspfVirtIfEntry 12 }

sonusOspfVirtIfSlot OBJECT-TYPE
    SYNTAX          SonusSlotIndex
    MAX-ACCESS      read-only
    STATUS          current
    DESCRIPTION     
            "A 32-bit integer identifying the OSPF Slot"
    ::= { sonusOspfVirtIfEntry 13 }

sonusOspfVirtIfInstance OBJECT-TYPE
    SYNTAX          Integer32
    MAX-ACCESS      read-only
    STATUS          current
    DESCRIPTION     
            "A 32-bit integer identifying the OSPF Instance"
    ::= { sonusOspfVirtIfEntry 14 }

sonusOspfNbrTable OBJECT-TYPE
    SYNTAX          SEQUENCE OF SonusOspfNbrEntry
    MAX-ACCESS      not-accessible
    STATUS          current
    DESCRIPTION     
            "A table of non-virtual neighbor information."
    REFERENCE       
            "OSPF Version 2, Section 10  The  Neighbor  Data
             Structure"
    ::= { sonusOspf 10 }

sonusOspfNbrEntry OBJECT-TYPE
    SYNTAX          SonusOspfNbrEntry
    MAX-ACCESS      not-accessible
    STATUS          current
    DESCRIPTION     
            "The information regarding a single neighbor."
    REFERENCE       
            "OSPF Version 2, Section 10  The  Neighbor  Data
             Structure"
    INDEX           { sonusOspfNbrShelf, sonusOspfNbrSlot, 
                      sonusOspfNbrInstance, sonusOspfNbrIpVersion, 
                      sonusOspfNbrIpAddr, sonusOspfNbrIp6Addr, 
                      sonusOspfNbrAddressLessIndex }
    ::= { sonusOspfNbrTable 1 }

SonusOspfNbrEntry ::=
    SEQUENCE {
        sonusOspfNbrIpAddr              IpAddress,
        sonusOspfNbrAddressLessIndex    SonusOspfInterfaceIndex,
        sonusOspfNbrRtrId               SonusOspfRouterID,
        sonusOspfNbrOptions             Integer32,
        sonusOspfNbrPriority            SonusOspfDesignatedRouterPriority,
        sonusOspfNbrState               INTEGER,
        sonusOspfNbrEvents              Counter32,
        sonusOspfNbrLsRetransQLen       Gauge32,
        sonusOspfNbmaNbrStatus          RowStatus,
        sonusOspfNbmaNbrPermanence      INTEGER,
        sonusOspfNbrHelloSuppressed     TruthValue,
        sonusOspfNbrShelf               SonusShelfIndex,
        sonusOspfNbrSlot                SonusSlotIndex,
        sonusOspfNbrInstance            Integer32,
        sonusOspfNbrIp6Addr             Ipv6Address,
        sonusOspfNbrIpVersion           INTEGER
    }

sonusOspfNbrIpAddr OBJECT-TYPE
    SYNTAX          IpAddress
    MAX-ACCESS      read-only
    STATUS          current
    DESCRIPTION     
            "The IP address this neighbor is using  in  its
             IP  Source  Address.  Note that, on addressless
             links, this will not be 0.0.0.0,  but  the  ad-
             dress of another of the neighbor's interfaces."
    ::= { sonusOspfNbrEntry 1 }

sonusOspfNbrAddressLessIndex OBJECT-TYPE
    SYNTAX          SonusOspfInterfaceIndex
    MAX-ACCESS      read-only
    STATUS          current
    DESCRIPTION     
            "On an interface having an  IP  Address,  zero.
             On  addressless  interfaces,  the corresponding
             value of ifIndex in the Internet Standard  MIB.
             On  row  creation, this can be derived from the
             instance."
    ::= { sonusOspfNbrEntry 2 }

sonusOspfNbrRtrId OBJECT-TYPE
    SYNTAX          SonusOspfRouterID
    MAX-ACCESS      read-only
    STATUS          current
    DESCRIPTION     
            "A 32-bit integer (represented as a type  IpAd-
             dress)  uniquely  identifying  the  neighboring
             router in the Autonomous System."
    DEFVAL          { '00000000'H }
    ::= { sonusOspfNbrEntry 3 }

sonusOspfNbrOptions OBJECT-TYPE
    SYNTAX          Integer32
    MAX-ACCESS      read-only
    STATUS          current
    DESCRIPTION     
            "A Bit Mask corresponding to the neighbor's op-
             tions field.
             
             Bit 0, if set, indicates that the  system  will
             operate  on  Type of Service metrics other than
             TOS 0.  If zero, the neighbor will  ignore  all
             metrics except the TOS 0 metric.
             
             Bit 1, if set, indicates  that  the  associated
             area  accepts and operates on external informa-
             tion; if zero, it is a stub area.
             
             Bit 2, if set, indicates that the system is ca-
             pable  of routing IP Multicast datagrams; i.e.,
             that it implements the Multicast Extensions  to
             OSPF.
             
             Bit 3, if set, indicates  that  the  associated
             area  is  an  NSSA.  These areas are capable of
             carrying type 7 external advertisements,  which
             are  translated into type 5 external advertise-
             ments at NSSA borders."
    REFERENCE       
            "OSPF Version 2, Section 12.1.2 Options"
    DEFVAL          { 0 }
    ::= { sonusOspfNbrEntry 4 }

sonusOspfNbrPriority OBJECT-TYPE
    SYNTAX          SonusOspfDesignatedRouterPriority
    MAX-ACCESS      read-create
    STATUS          current
    DESCRIPTION     
            "The priority of this neighbor in the designat-
             ed router election algorithm.  The value 0 sig-
             nifies that the neighbor is not eligible to be-
             come  the  designated router on this particular
             network."
    DEFVAL          { 1 }
    ::= { sonusOspfNbrEntry 5 }

sonusOspfNbrState OBJECT-TYPE
    SYNTAX          INTEGER { down(1), attempt(2), init(3), twoWay(4), 
                        exchangeStart(5), exchange(6), loading(7), 
                        full(8) }
    MAX-ACCESS      read-only
    STATUS          current
    DESCRIPTION     
            "The State of the relationship with this Neigh-
             bor."
    REFERENCE       
            "OSPF Version 2, Section 10.1 Neighbor States"
    DEFVAL          { down }
    ::= { sonusOspfNbrEntry 6 }

sonusOspfNbrEvents OBJECT-TYPE
    SYNTAX          Counter32
    MAX-ACCESS      read-only
    STATUS          current
    DESCRIPTION     
            "The number of times this neighbor relationship
             has changed state, or an error has occurred."
    ::= { sonusOspfNbrEntry 7 }

sonusOspfNbrLsRetransQLen OBJECT-TYPE
    SYNTAX          Gauge32
    MAX-ACCESS      read-only
    STATUS          current
    DESCRIPTION     
            "The  current  length  of  the   retransmission
             queue."
    ::= { sonusOspfNbrEntry 8 }

sonusOspfNbmaNbrStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfNbrEntry 9 }

sonusOspfNbmaNbrPermanence OBJECT-TYPE
    SYNTAX          INTEGER { dynamic(1), permanent(2) }
    MAX-ACCESS      read-only
    STATUS          current
    DESCRIPTION     
            "This variable displays the status of  the  en-
             try.   'dynamic'  and  'permanent' refer to how
             the neighbor became known."
    DEFVAL          { permanent }
    ::= { sonusOspfNbrEntry 10 }

sonusOspfNbrHelloSuppressed OBJECT-TYPE
    SYNTAX          TruthValue
    MAX-ACCESS      read-only
    STATUS          current
    DESCRIPTION     
            "Indicates whether Hellos are being  suppressed
             to the neighbor"
    ::= { sonusOspfNbrEntry 11 }

sonusOspfNbrShelf OBJECT-TYPE
    SYNTAX          SonusShelfIndex
    MAX-ACCESS      read-only
    STATUS          current
    DESCRIPTION     
            "A 32-bit integer identifying the OSPF Shelf"
    ::= { sonusOspfNbrEntry 12 }

sonusOspfNbrSlot OBJECT-TYPE
    SYNTAX          SonusSlotIndex
    MAX-ACCESS      read-only
    STATUS          current
    DESCRIPTION     
            "A 32-bit integer identifying the OSPF Slot.
             This is no longer an active OSPF Neighbor table index"
    ::= { sonusOspfNbrEntry 13 }

sonusOspfNbrInstance OBJECT-TYPE
    SYNTAX          Integer32
    MAX-ACCESS      read-only
    STATUS          current
    DESCRIPTION     
            "A 32-bit integer identifying the OSPF Instance"
    ::= { sonusOspfNbrEntry 14 }

sonusOspfNbrIp6Addr OBJECT-TYPE
    SYNTAX          Ipv6Address
    MAX-ACCESS      read-only
    STATUS          current
    DESCRIPTION     
            "The IP address this neighbor is using  in  its
             IP  Source  Address.  Note that, on addressless
             links, this will not be 0.0.0.0,  but  the  ad-
             dress of another of the neighbor's interfaces."
    ::= { sonusOspfNbrEntry 15 }

sonusOspfNbrIpVersion OBJECT-TYPE
    SYNTAX          INTEGER { afInet(2), afInet6(24) }
    MAX-ACCESS      read-only
    STATUS          current
    DESCRIPTION     
            "IP address version type"
    ::= { sonusOspfNbrEntry 16 }

sonusOspfVirtNbrTable OBJECT-TYPE
    SYNTAX          SEQUENCE OF SonusOspfVirtNbrEntry
    MAX-ACCESS      not-accessible
    STATUS          current
    DESCRIPTION     
            "A table of virtual neighbor information."
    REFERENCE       
            "OSPF Version 2, Section 15  Virtual Links"
    ::= { sonusOspf 11 }

sonusOspfVirtNbrEntry OBJECT-TYPE
    SYNTAX          SonusOspfVirtNbrEntry
    MAX-ACCESS      not-accessible
    STATUS          current
    DESCRIPTION     
            "Virtual neighbor information."
    INDEX           { sonusOspfVirtNbrShelf, sonusOspfVirtNbrSlot, 
                      sonusOspfVirtNbrInstance, sonusOspfVirtNbrArea, 
                      sonusOspfVirtNbrRtrId }
    ::= { sonusOspfVirtNbrTable 1 }

SonusOspfVirtNbrEntry ::=
    SEQUENCE {
        sonusOspfVirtNbrArea            SonusOspfAreaID,
        sonusOspfVirtNbrRtrId           SonusOspfRouterID,
        sonusOspfVirtNbrIpAddr          IpAddress,
        sonusOspfVirtNbrOptions         Integer32,
        sonusOspfVirtNbrState           INTEGER,
        sonusOspfVirtNbrEvents          Counter32,
        sonusOspfVirtNbrLsRetransQLen   Gauge32,
        sonusOspfVirtNbrHelloSuppressed TruthValue,
        sonusOspfVirtNbrShelf           SonusShelfIndex,
        sonusOspfVirtNbrSlot            SonusSlotIndex,
        sonusOspfVirtNbrInstance        Integer32
    }

sonusOspfVirtNbrArea OBJECT-TYPE
    SYNTAX          SonusOspfAreaID
    MAX-ACCESS      read-only
    STATUS          current
    DESCRIPTION     
            "The Transit Area Identifier."
    ::= { sonusOspfVirtNbrEntry 1 }

sonusOspfVirtNbrRtrId OBJECT-TYPE
    SYNTAX          SonusOspfRouterID
    MAX-ACCESS      read-only
    STATUS          current
    DESCRIPTION     
            "A  32-bit  integer  uniquely  identifying  the
             neighboring router in the Autonomous System."
    ::= { sonusOspfVirtNbrEntry 2 }

sonusOspfVirtNbrIpAddr OBJECT-TYPE
    SYNTAX          IpAddress
    MAX-ACCESS      read-only
    STATUS          current
    DESCRIPTION     
            "The IP address this Virtual  Neighbor  is  us-
             ing."
    ::= { sonusOspfVirtNbrEntry 3 }

sonusOspfVirtNbrOptions OBJECT-TYPE
    SYNTAX          Integer32
    MAX-ACCESS      read-only
    STATUS          current
    DESCRIPTION     
            "A Bit Mask corresponding to the neighbor's op-
             tions field.
             
             Bit 1, if set, indicates that the  system  will
             operate  on  Type of Service metrics other than
             TOS 0.  If zero, the neighbor will  ignore  all
             metrics except the TOS 0 metric.
             
             Bit 2, if set, indicates  that  the  system  is
             Network  Multicast  capable; ie, that it imple-
             ments OSPF Multicast Routing."
    ::= { sonusOspfVirtNbrEntry 4 }

sonusOspfVirtNbrState OBJECT-TYPE
    SYNTAX          INTEGER { down(1), attempt(2), init(3), twoWay(4), 
                        exchangeStart(5), exchange(6), loading(7), 
                        full(8) }
    MAX-ACCESS      read-only
    STATUS          current
    DESCRIPTION     
            "The state of the  Virtual  Neighbor  Relation-
             ship."
    ::= { sonusOspfVirtNbrEntry 5 }

sonusOspfVirtNbrEvents OBJECT-TYPE
    SYNTAX          Counter32
    MAX-ACCESS      read-only
    STATUS          current
    DESCRIPTION     
            "The number of  times  this  virtual  link  has
             changed its state, or an error has occurred."
    ::= { sonusOspfVirtNbrEntry 6 }

sonusOspfVirtNbrLsRetransQLen OBJECT-TYPE
    SYNTAX          Gauge32
    MAX-ACCESS      read-only
    STATUS          current
    DESCRIPTION     
            "The  current  length  of  the   retransmission
             queue."
    ::= { sonusOspfVirtNbrEntry 7 }

sonusOspfVirtNbrHelloSuppressed OBJECT-TYPE
    SYNTAX          TruthValue
    MAX-ACCESS      read-only
    STATUS          current
    DESCRIPTION     
            "Indicates whether Hellos are being  suppressed
             to the neighbor"
    ::= { sonusOspfVirtNbrEntry 8 }

sonusOspfVirtNbrShelf OBJECT-TYPE
    SYNTAX          SonusShelfIndex
    MAX-ACCESS      read-only
    STATUS          current
    DESCRIPTION     
            "A 32-bit integer identifying the OSPF Shelf"
    ::= { sonusOspfVirtNbrEntry 9 }

sonusOspfVirtNbrSlot OBJECT-TYPE
    SYNTAX          SonusSlotIndex
    MAX-ACCESS      read-only
    STATUS          current
    DESCRIPTION     
            "A 32-bit integer identifying the OSPF Slot"
    ::= { sonusOspfVirtNbrEntry 10 }

sonusOspfVirtNbrInstance OBJECT-TYPE
    SYNTAX          Integer32
    MAX-ACCESS      read-only
    STATUS          current
    DESCRIPTION     
            "A 32-bit integer identifying the OSPF Instance"
    ::= { sonusOspfVirtNbrEntry 11 }

sonusOspfExtLsdbTable OBJECT-TYPE
    SYNTAX          SEQUENCE OF SonusOspfExtLsdbEntry
    MAX-ACCESS      not-accessible
    STATUS          current
    DESCRIPTION     
            "The OSPF Process's Links State Database."
    REFERENCE       
            "OSPF Version 2, Section 12  Link  State  Adver-
             tisements"
    ::= { sonusOspf 12 }

sonusOspfExtLsdbEntry OBJECT-TYPE
    SYNTAX          SonusOspfExtLsdbEntry
    MAX-ACCESS      not-accessible
    STATUS          current
    DESCRIPTION     
            "A single Link State Advertisement."
    INDEX           { sonusOspfExtLsdbShelf, sonusOspfExtLsdbSlot, 
                      sonusOspfExtLsdbInstance, sonusOspfExtLsdbType, 
                      sonusOspfExtLsdbLsid, sonusOspfExtLsdbRouterId }
    ::= { sonusOspfExtLsdbTable 1 }

SonusOspfExtLsdbEntry ::=
    SEQUENCE {
        sonusOspfExtLsdbType            INTEGER,
        sonusOspfExtLsdbLsid            IpAddress,
        sonusOspfExtLsdbRouterId        SonusOspfRouterID,
        sonusOspfExtLsdbSequence        Integer32,
        sonusOspfExtLsdbAge             Integer32,
        sonusOspfExtLsdbChecksum        Integer32,
        sonusOspfExtLsdbAdvertisement   OCTET STRING,
        sonusOspfExtLsdbShelf           SonusShelfIndex,
        sonusOspfExtLsdbSlot            SonusSlotIndex,
        sonusOspfExtLsdbInstance        Integer32
    }

sonusOspfExtLsdbType OBJECT-TYPE
    SYNTAX          INTEGER { asExternalLink(5) }
    MAX-ACCESS      read-only
    STATUS          current
    DESCRIPTION     
            "The type  of  the  link  state  advertisement.
             Each  link state type has a separate advertise-
             ment format."
    REFERENCE       
            "OSPF Version 2, Appendix A.4.1 The  Link  State
             Advertisement header"
    ::= { sonusOspfExtLsdbEntry 1 }

sonusOspfExtLsdbLsid OBJECT-TYPE
    SYNTAX          IpAddress
    MAX-ACCESS      read-only
    STATUS          current
    DESCRIPTION     
            "The Link State ID is an LS Type Specific field
             containing either a Router ID or an IP Address;
             it identifies the piece of the  routing  domain
             that is being described by the advertisement."
    REFERENCE       
            "OSPF Version 2, Section 12.1.4 Link State ID"
    ::= { sonusOspfExtLsdbEntry 2 }

sonusOspfExtLsdbRouterId OBJECT-TYPE
    SYNTAX          SonusOspfRouterID
    MAX-ACCESS      read-only
    STATUS          current
    DESCRIPTION     
            "The 32 bit number that uniquely identifies the
             originating router in the Autonomous System."
    REFERENCE       
            "OSPF Version 2, Appendix C.1 Global parameters"
    ::= { sonusOspfExtLsdbEntry 3 }

sonusOspfExtLsdbSequence OBJECT-TYPE
    SYNTAX          Integer32
    MAX-ACCESS      read-only
    STATUS          current
    DESCRIPTION     
            "The sequence number field is a  signed  32-bit
             integer.   It  is used to detect old and dupli-
             cate link state advertisements.  The  space  of
             sequence  numbers  is  linearly  ordered.   The
             larger the sequence number the more recent  the
             advertisement."
    REFERENCE       
            "OSPF Version  2,  Section  12.1.6  LS  sequence
             number"
    ::= { sonusOspfExtLsdbEntry 4 }

sonusOspfExtLsdbAge OBJECT-TYPE
    SYNTAX          Integer32
    MAX-ACCESS      read-only
    STATUS          current
    DESCRIPTION     
            "This field is the age of the link state adver-
             tisement in seconds."
    REFERENCE       
            "OSPF Version 2, Section 12.1.1 LS age"
    ::= { sonusOspfExtLsdbEntry 5 }

sonusOspfExtLsdbChecksum OBJECT-TYPE
    SYNTAX          Integer32
    MAX-ACCESS      read-only
    STATUS          current
    DESCRIPTION     
            "This field is the  checksum  of  the  complete
             contents  of  the  advertisement, excepting the
             age field.  The age field is excepted  so  that
             an   advertisement's  age  can  be  incremented
             without updating the  checksum.   The  checksum
             used  is  the same that is used for ISO connec-
             tionless datagrams; it is commonly referred  to
             as the Fletcher checksum."
    REFERENCE       
            "OSPF Version 2, Section 12.1.7 LS checksum"
    ::= { sonusOspfExtLsdbEntry 6 }

sonusOspfExtLsdbAdvertisement OBJECT-TYPE
    SYNTAX          OCTET STRING (SIZE(36))
    MAX-ACCESS      read-only
    STATUS          current
    DESCRIPTION     
            "The entire Link State Advertisement, including
             its header."
    REFERENCE       
            "OSPF Version 2, Section 12  Link  State  Adver-
             tisements"
    ::= { sonusOspfExtLsdbEntry 7 }

sonusOspfExtLsdbShelf OBJECT-TYPE
    SYNTAX          SonusShelfIndex
    MAX-ACCESS      read-only
    STATUS          current
    DESCRIPTION     
            "A 32-bit integer identifying the OSPF Shelf"
    ::= { sonusOspfExtLsdbEntry 8 }

sonusOspfExtLsdbSlot OBJECT-TYPE
    SYNTAX          SonusSlotIndex
    MAX-ACCESS      read-only
    STATUS          current
    DESCRIPTION     
            "A 32-bit integer identifying the OSPF Slot"
    ::= { sonusOspfExtLsdbEntry 9 }

sonusOspfExtLsdbInstance OBJECT-TYPE
    SYNTAX          Integer32
    MAX-ACCESS      read-only
    STATUS          current
    DESCRIPTION     
            "A 32-bit integer identifying the OSPF Instance"
    ::= { sonusOspfExtLsdbEntry 10 }

sonusOspfRouteGroup OBJECT IDENTIFIER
    ::= { sonusOspf 13 }

sonusOspfIntraArea OBJECT IDENTIFIER
    ::= { sonusOspfRouteGroup 1 }

sonusOspfInterArea OBJECT IDENTIFIER
    ::= { sonusOspfRouteGroup 2 }

sonusOspfExternalType1 OBJECT IDENTIFIER
    ::= { sonusOspfRouteGroup 3 }

sonusOspfExternalType2 OBJECT IDENTIFIER
    ::= { sonusOspfRouteGroup 4 }

sonusOspfAreaAggregateTable OBJECT-TYPE
    SYNTAX          SEQUENCE OF SonusOspfAreaAggregateEntry
    MAX-ACCESS      not-accessible
    STATUS          current
    DESCRIPTION     
            "A range of IP addresses  specified  by  an  IP
             address/IP  network  mask  pair.   For example,
             class B address range of X.X.X.X with a network
             mask  of  255.255.0.0 includes all IP addresses
             from X.X.0.0  to  X.X.255.255.   Note  that  if
             ranges  are configured such that one range sub-
             sumes  another  range  (e.g.,   10.0.0.0   mask
             255.0.0.0  and  10.1.0.0 mask 255.255.0.0), the
             most specific match is the preferred one."
    REFERENCE       
            "OSPF Version 2, Appendix C.2  Area parameters"
    ::= { sonusOspf 14 }

sonusOspfAreaAggregateEntry OBJECT-TYPE
    SYNTAX          SonusOspfAreaAggregateEntry
    MAX-ACCESS      not-accessible
    STATUS          current
    DESCRIPTION     
            "A range of IP addresses  specified  by  an  IP
             address/IP  network  mask  pair.   For example,
             class B address range of X.X.X.X with a network
             mask  of  255.255.0.0 includes all IP addresses
             from X.X.0.0  to  X.X.255.255.   Note  that  if
             ranges are range configured such that one range
             subsumes another  range  (e.g.,  10.0.0.0  mask
             255.0.0.0  and  10.1.0.0 mask 255.255.0.0), the
             most specific match is the preferred one."
    REFERENCE       
            "OSPF Version 2, Appendix C.2  Area parameters"
    INDEX           { sonusOspfAreaAggregateShelf, 
                      sonusOspfAreaAggregateSlot, 
                      sonusOspfAreaAggregateInstance, 
                      sonusOspfAreaAggregateAreaID, 
                      sonusOspfAreaAggregateLsdbType, 
                      sonusOspfAreaAggregateNet, 
                      sonusOspfAreaAggregateMask }
    ::= { sonusOspfAreaAggregateTable 1 }

SonusOspfAreaAggregateEntry ::=
    SEQUENCE {
        sonusOspfAreaAggregateAreaID    SonusOspfAreaID,
        sonusOspfAreaAggregateLsdbType  INTEGER,
        sonusOspfAreaAggregateNet       IpAddress,
        sonusOspfAreaAggregateMask      IpAddress,
        sonusOspfAreaAggregateStatus    RowStatus,
        sonusOspfAreaAggregateEffect    INTEGER,
        sonusOspfAreaAggregateShelf     SonusShelfIndex,
        sonusOspfAreaAggregateSlot      SonusSlotIndex,
        sonusOspfAreaAggregateInstance  Integer32
    }

sonusOspfAreaAggregateAreaID OBJECT-TYPE
    SYNTAX          SonusOspfAreaID
    MAX-ACCESS      read-only
    STATUS          current
    DESCRIPTION     
            "The Area the Address Aggregate is to be  found
             within."
    REFERENCE       
            "OSPF Version 2, Appendix C.2 Area parameters"
    ::= { sonusOspfAreaAggregateEntry 1 }

sonusOspfAreaAggregateLsdbType OBJECT-TYPE
    SYNTAX          INTEGER { summaryLink(3), nssaExternalLink(7) }
    MAX-ACCESS      read-only
    STATUS          current
    DESCRIPTION     
            "The type of the Address Aggregate.  This field
             specifies  the  Lsdb type that this Address Ag-
             gregate applies to."
    REFERENCE       
            "OSPF Version 2, Appendix A.4.1 The  Link  State
             Advertisement header"
    ::= { sonusOspfAreaAggregateEntry 2 }

sonusOspfAreaAggregateNet OBJECT-TYPE
    SYNTAX          IpAddress
    MAX-ACCESS      read-only
    STATUS          current
    DESCRIPTION     
            "The IP Address of the Net or Subnet  indicated
             by the range."
    REFERENCE       
            "OSPF Version 2, Appendix C.2 Area parameters"
    ::= { sonusOspfAreaAggregateEntry 3 }

sonusOspfAreaAggregateMask OBJECT-TYPE
    SYNTAX          IpAddress
    MAX-ACCESS      read-only
    STATUS          current
    DESCRIPTION     
            "The Subnet Mask that pertains to  the  Net  or
             Subnet."
    REFERENCE       
            "OSPF Version 2, Appendix C.2 Area parameters"
    ::= { sonusOspfAreaAggregateEntry 4 }

sonusOspfAreaAggregateStatus OBJECT-TYPE
    SYNTAX          RowStatus
    MAX-ACCESS      read-create
    STATUS          current
    DESCRIPTION     
            "This variable displays the status of  the  en-
             try.  Setting it to 'invalid' has the effect of
             rendering it inoperative.  The internal  effect
             (row removal) is implementation dependent."
    ::= { sonusOspfAreaAggregateEntry 5 }

sonusOspfAreaAggregateEffect OBJECT-TYPE
    SYNTAX          INTEGER { advertiseMatching(1), 
                        doNotAdvertiseMatching(2) }
    MAX-ACCESS      read-create
    STATUS          current
    DESCRIPTION     
            "Subnets subsumed by ranges either trigger  the
             advertisement  of  the indicated aggregate (ad-
             vertiseMatching), or result in the subnet's not
             being advertised at all outside the area."
    DEFVAL          { advertiseMatching }
    ::= { sonusOspfAreaAggregateEntry 6 }

sonusOspfAreaAggregateShelf OBJECT-TYPE
    SYNTAX          SonusShelfIndex
    MAX-ACCESS      read-only
    STATUS          current
    DESCRIPTION     
            "A 32-bit integer identifying the OSPF Shelf"
    ::= { sonusOspfAreaAggregateEntry 7 }

sonusOspfAreaAggregateSlot OBJECT-TYPE
    SYNTAX          SonusSlotIndex
    MAX-ACCESS      read-only
    STATUS          current
    DESCRIPTION     
            "A 32-bit integer identifying the OSPF Slot"
    ::= { sonusOspfAreaAggregateEntry 8 }

sonusOspfAreaAggregateInstance OBJECT-TYPE
    SYNTAX          Integer32
    MAX-ACCESS      read-only
    STATUS          current
    DESCRIPTION     
            "A 32-bit integer identifying the OSPF Instance"
    ::= { sonusOspfAreaAggregateEntry 9 }

sonusOspfConformance OBJECT IDENTIFIER
    ::= { sonusOspf 15 }

sonusOspfGroups OBJECT IDENTIFIER
    ::= { sonusOspfConformance 1 }

sonusOspfCompliances OBJECT IDENTIFIER
    ::= { sonusOspfConformance 2 }

sonusOspfMIBNotifications OBJECT IDENTIFIER
    ::= { sonusOspf 16 }

sonusOspfMIBNotificationsPrefix OBJECT IDENTIFIER
    ::= { sonusOspfMIBNotifications 0 }

sonusOspfMIBNotificationsObjects OBJECT IDENTIFIER
    ::= { sonusOspfMIBNotifications 1 }

sonusOspfProcessStateChangeNotification NOTIFICATION-TYPE
    OBJECTS         { sonusOspfAdminStat, sonusEventDescription, 
                      sonusEventClass, sonusEventLevel, sonusSequenceId, 
                      sonusEventTime }
    STATUS          current
    DESCRIPTION     
            "This trap indicates admin state change of OSPF process"
    ::= { sonusOspfMIBNotificationsPrefix 1 }

sonusOspfNeighborStateChangeNotification NOTIFICATION-TYPE
    OBJECTS         { sonusOspfNbrIpAddr, sonusOspfIfIpAddress, 
                      sonusOspfNbrState, sonusEventDescription, 
                      sonusEventClass, sonusEventLevel, sonusSequenceId, 
                      sonusEventTime }
    STATUS          current
    DESCRIPTION     
            "This trap indicates OSPF neighbor state change"
    ::= { sonusOspfMIBNotificationsPrefix 2 }

sonusOspfNeighborInactiveNotification NOTIFICATION-TYPE
    OBJECTS         { sonusOspfNbrIpAddr, sonusOspfIfRtrDeadInterval, 
                      sonusEventDescription, sonusEventClass, 
                      sonusEventLevel, sonusSequenceId, sonusEventTime }
    STATUS          current
    DESCRIPTION     
            "This trap indicates OSPF neighbor is nolonger active"
    ::= { sonusOspfMIBNotificationsPrefix 3 }

sonusOspfIntfUpNotification NOTIFICATION-TYPE
    OBJECTS         { sonusOspfIfIpAddress, sonusEventDescription, 
                      sonusEventClass, sonusEventLevel, sonusSequenceId, 
                      sonusEventTime }
    STATUS          current
    DESCRIPTION     
            "This trap indicates OSPF interface state is currently
             Up"
    ::= { sonusOspfMIBNotificationsPrefix 4 }

sonusOspfIntfDownNotification NOTIFICATION-TYPE
    OBJECTS         { sonusOspfIfIpAddress, sonusEventDescription, 
                      sonusEventClass, sonusEventLevel, sonusSequenceId, 
                      sonusEventTime }
    STATUS          current
    DESCRIPTION     
            "This trap indicates OSPF interface state is currently
             Down"
    ::= { sonusOspfMIBNotificationsPrefix 5 }

sonusOspfNeighborStateChangeNotificationV6 NOTIFICATION-TYPE
    OBJECTS         { sonusOspfNbrIpAddr, sonusOspfIfIp6Address, 
                      sonusOspfNbrState, sonusEventDescription, 
                      sonusEventClass, sonusEventLevel, sonusSequenceId, 
                      sonusEventTime }
    STATUS          current
    DESCRIPTION     
            "This trap indicates OSPF neighbor state change"
    ::= { sonusOspfMIBNotificationsPrefix 6 }

sonusOspfNeighborInactiveNotificationV6 NOTIFICATION-TYPE
    OBJECTS         { sonusOspfNbrIp6Addr, sonusOspfIfRtrDeadInterval, 
                      sonusEventDescription, sonusEventClass, 
                      sonusEventLevel, sonusSequenceId, sonusEventTime }
    STATUS          current
    DESCRIPTION     
            "This trap indicates OSPF neighbor is nolonger active"
    ::= { sonusOspfMIBNotificationsPrefix 7 }

sonusOspfIntfUpNotificationV6 NOTIFICATION-TYPE
    OBJECTS         { sonusOspfIfIp6Address, sonusEventDescription, 
                      sonusEventClass, sonusEventLevel, sonusSequenceId, 
                      sonusEventTime }
    STATUS          current
    DESCRIPTION     
            "This trap indicates OSPF interface state is currently
             Up"
    ::= { sonusOspfMIBNotificationsPrefix 8 }

sonusOspfIntfDownNotificationV6 NOTIFICATION-TYPE
    OBJECTS         { sonusOspfIfIp6Address, sonusEventDescription, 
                      sonusEventClass, sonusEventLevel, sonusSequenceId, 
                      sonusEventTime }
    STATUS          current
    DESCRIPTION     
            "This trap indicates OSPF interface state is currently
             Down"
    ::= { sonusOspfMIBNotificationsPrefix 9 }

sonusOspfBasicGroup OBJECT-GROUP
    OBJECTS         { sonusOspfRouterId, sonusOspfAdminStat, 
                      sonusOspfVersionNumber, sonusOspfAreaBdrRtrStatus, 
                      sonusOspfASBdrRtrStatus, sonusOspfExternLsaCount, 
                      sonusOspfExternLsaCksumSum, sonusOspfTOSSupport, 
                      sonusOspfOriginateNewLsas, sonusOspfRxNewLsas, 
                      sonusOspfExtLsdbLimit, 
                      sonusOspfMulticastExtensions, 
                      sonusOspfExitOverflowInterval, 
                      sonusOspfDemandExtensions }
    STATUS          current
    DESCRIPTION     
            "These objects are required for OSPF systems."
    ::= { sonusOspfGroups 1 }

sonusOspfAreaGroup OBJECT-GROUP
    OBJECTS         { sonusOspfAreaId, sonusOspfImportAsExtern, 
                      sonusOspfSpfRuns, sonusOspfAreaBdrRtrCount, 
                      sonusOspfAsBdrRtrCount, sonusOspfAreaLsaCount, 
                      sonusOspfAreaLsaCksumSum, sonusOspfAreaSummary, 
                      sonusOspfAreaStatus }
    STATUS          current
    DESCRIPTION     
            "These objects are required  for  OSPF  systems
             supporting areas."
    ::= { sonusOspfGroups 2 }

sonusOspfStubAreaGroup OBJECT-GROUP
    OBJECTS         { sonusOspfStubAreaId, sonusOspfStubTOS, 
                      sonusOspfStubMetric, sonusOspfStubStatus, 
                      sonusOspfStubMetricType }
    STATUS          current
    DESCRIPTION     
            "These objects are required  for  OSPF  systems
             supporting stub areas."
    ::= { sonusOspfGroups 3 }

sonusOspfLsdbGroup OBJECT-GROUP
    OBJECTS         { sonusOspfLsdbAreaId, sonusOspfLsdbType, 
                      sonusOspfLsdbLsid, sonusOspfLsdbRouterId, 
                      sonusOspfLsdbSequence, sonusOspfLsdbAge, 
                      sonusOspfLsdbChecksum, sonusOspfLsdbAdvertisement }
    STATUS          current
    DESCRIPTION     
            "These objects are required  for  OSPF  systems
             that display their link state database."
    ::= { sonusOspfGroups 4 }

sonusOspfAreaRangeGroup OBJECT-GROUP
    OBJECTS         { sonusOspfAreaRangeAreaId, sonusOspfAreaRangeNet, 
                      sonusOspfAreaRangeMask, sonusOspfAreaRangeStatus, 
                      sonusOspfAreaRangeEffect }
    STATUS          obsolete
    DESCRIPTION     
            "These objects are required for  non-CIDR  OSPF
             systems that support multiple areas."
    ::= { sonusOspfGroups 5 }

sonusOspfHostGroup OBJECT-GROUP
    OBJECTS         { sonusOspfHostIpAddress, sonusOspfHostTOS, 
                      sonusOspfHostMetric, sonusOspfHostStatus, 
                      sonusOspfHostAreaID }
    STATUS          current
    DESCRIPTION     
            "These objects are required  for  OSPF  systems
             that support attached hosts."
    ::= { sonusOspfGroups 6 }

sonusOspfIfGroup OBJECT-GROUP
    OBJECTS         { sonusOspfIfIpAddress, sonusOspfAddressLessIf, 
                      sonusOspfIfAreaId, sonusOspfIfType, 
                      sonusOspfIfAdminStat, sonusOspfIfRtrPriority, 
                      sonusOspfIfTransitDelay, 
                      sonusOspfIfRetransInterval, 
                      sonusOspfIfHelloInterval, 
                      sonusOspfIfRtrDeadInterval, 
                      sonusOspfIfPollInterval, sonusOspfIfState, 
                      sonusOspfIfDesignatedRouter, 
                      sonusOspfIfBackupDesignatedRouter, 
                      sonusOspfIfEvents, sonusOspfIfAuthType, 
                      sonusOspfIfAuthKey, sonusOspfIfStatus, 
                      sonusOspfIfMulticastForwarding, sonusOspfIfDemand }
    STATUS          current
    DESCRIPTION     
            "These objects are required for OSPF systems."
    ::= { sonusOspfGroups 7 }

sonusOspfIfMetricGroup OBJECT-GROUP
    OBJECTS         { sonusOspfIfMetricIpAddress, 
                      sonusOspfIfMetricAddressLessIf, 
                      sonusOspfIfMetricTOS, sonusOspfIfMetricValue, 
                      sonusOspfIfMetricStatus }
    STATUS          current
    DESCRIPTION     
            "These objects are required for OSPF systems."
    ::= { sonusOspfGroups 8 }

sonusOspfVirtIfGroup OBJECT-GROUP
    OBJECTS         { sonusOspfVirtIfAreaId, sonusOspfVirtIfNeighbor, 
                      sonusOspfVirtIfTransitDelay, 
                      sonusOspfVirtIfRetransInterval, 
                      sonusOspfVirtIfHelloInterval, 
                      sonusOspfVirtIfRtrDeadInterval, 
                      sonusOspfVirtIfState, sonusOspfVirtIfEvents, 
                      sonusOspfVirtIfAuthType, sonusOspfVirtIfAuthKey, 
                      sonusOspfVirtIfStatus }
    STATUS          current
    DESCRIPTION     
            "These objects are required for OSPF systems."
    ::= { sonusOspfGroups 9 }

sonusOspfNbrGroup OBJECT-GROUP
    OBJECTS         { sonusOspfNbrIpAddr, sonusOspfNbrAddressLessIndex, 
                      sonusOspfNbrRtrId, sonusOspfNbrOptions, 
                      sonusOspfNbrPriority, sonusOspfNbrState, 
                      sonusOspfNbrEvents, sonusOspfNbrLsRetransQLen, 
                      sonusOspfNbmaNbrStatus, sonusOspfNbmaNbrPermanence, 
                      sonusOspfNbrHelloSuppressed, sonusOspfNbrIp6Addr }
    STATUS          current
    DESCRIPTION     
            "These objects are required for OSPF systems."
    ::= { sonusOspfGroups 10 }

sonusOspfVirtNbrGroup OBJECT-GROUP
    OBJECTS         { sonusOspfVirtNbrArea, sonusOspfVirtNbrRtrId, 
                      sonusOspfVirtNbrIpAddr, sonusOspfVirtNbrOptions, 
                      sonusOspfVirtNbrState, sonusOspfVirtNbrEvents, 
                      sonusOspfVirtNbrLsRetransQLen, 
                      sonusOspfVirtNbrHelloSuppressed }
    STATUS          current
    DESCRIPTION     
            "These objects are required for OSPF systems."
    ::= { sonusOspfGroups 11 }

sonusOspfExtLsdbGroup OBJECT-GROUP
    OBJECTS         { sonusOspfExtLsdbType, sonusOspfExtLsdbLsid, 
                      sonusOspfExtLsdbRouterId, sonusOspfExtLsdbSequence, 
                      sonusOspfExtLsdbAge, sonusOspfExtLsdbChecksum, 
                      sonusOspfExtLsdbAdvertisement }
    STATUS          current
    DESCRIPTION     
            "These objects are required  for  OSPF  systems
             that display their link state database."
    ::= { sonusOspfGroups 12 }

sonusOspfAreaAggregateGroup OBJECT-GROUP
    OBJECTS         { sonusOspfAreaAggregateAreaID, 
                      sonusOspfAreaAggregateLsdbType, 
                      sonusOspfAreaAggregateNet, 
                      sonusOspfAreaAggregateMask, 
                      sonusOspfAreaAggregateStatus, 
                      sonusOspfAreaAggregateEffect }
    STATUS          current
    DESCRIPTION     
            "These objects are required for OSPF systems."
    ::= { sonusOspfGroups 13 }

sonusOspfCompliance MODULE-COMPLIANCE
    STATUS          current
    DESCRIPTION     
            "The compliance statement "

    MODULE          -- this module

        MANDATORY-GROUPS    { sonusOspfBasicGroup, sonusOspfAreaGroup, 
                      sonusOspfStubAreaGroup, sonusOspfIfGroup, 
                      sonusOspfIfMetricGroup, sonusOspfVirtIfGroup, 
                      sonusOspfNbrGroup, sonusOspfVirtNbrGroup, 
                      sonusOspfAreaAggregateGroup }

    ::= { sonusOspfCompliances 1 }

END -- end of module SONUS-OSPF-MIB.
