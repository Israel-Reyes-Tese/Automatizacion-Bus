--
-- This SMIv1 module has been generated by smidump 0.2-cvs. Do not edit.
--

SONUS-TRUNK-GROUP-RESOURCES-MIB DEFINITIONS ::= BEGIN

IMPORTS
    Ipv6Address
        FROM IPV6-TC
    OBJECT-TYPE
        FROM RFC-1212
    TRAP-TYPE
        FROM RFC-1215
    IpAddress
        FROM RFC1155-SMI
    RowStatus
        FROM SNMPv2-TC
    sonusEventClass, sonusEventDescription, sonusEventLevel, 
    sonusEventTime, sonusPortIndex, sonusSequenceId, sonusShelfIndex, 
    sonusSlotIndex
        FROM SONUS-COMMON-MIB
    sonusResourcesMIBs
        FROM SONUS-SMI
    SonusAdminState, SonusBoolean, SonusName, SonusNameReference, 
    SonusShelfIndex
        FROM SONUS-TC;

sonusTrunkGroupResourcesMIB OBJECT IDENTIFIER
    ::= { sonusResourcesMIBs 3 }

-- sonusTrunkGroupResourcesMIB MODULE-IDENTITY
--     LAST-UPDATED    "201511080000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Trunk Group Resources Management."
--     ::= { sonusResourcesMIBs 3 }


sonusTrunkGroupResourcesMIBObjects OBJECT IDENTIFIER
    ::= { sonusTrunkGroupResourcesMIB 1 }

sonusTrunkObjects OBJECT IDENTIFIER
    ::= { sonusTrunkGroupResourcesMIBObjects 1 }

sonusTrunkConfigObjects OBJECT IDENTIFIER
    ::= { sonusTrunkObjects 1 }

sonusTgMaxRpcLpcs OBJECT-TYPE
    SYNTAX          INTEGER (1..65535)
    ACCESS          read-write
    STATUS          obsolete
    DESCRIPTION     
            "Maximum number of RPC-LPC pairs for this gateway.  This object is 
             not used and was made obsolete in GSX release 5.1."
    DEFVAL          { 500 }
    ::= { sonusTrunkConfigObjects 1 }

sonusTgMaxCics OBJECT-TYPE
    SYNTAX          INTEGER (1..65535)
    ACCESS          read-write
    STATUS          obsolete
    DESCRIPTION     
            "Maximum number of CICs for this gateway.  This object is 
             not used and was made obsolete in GSX release 5.1."
    DEFVAL          { 10000 }
    ::= { sonusTrunkConfigObjects 2 }

sonusTgMaxTrunkGroups OBJECT-TYPE
    SYNTAX          INTEGER (1..2048)
    ACCESS          read-write
    STATUS          mandatory
    DESCRIPTION     
            "Maximum number of trunk groups for this gateway."
    DEFVAL          { 250 }
    ::= { sonusTrunkConfigObjects 3 }

sonusTgMaxServiceGroups OBJECT-TYPE
    SYNTAX          INTEGER (1..65535)
    ACCESS          read-write
    STATUS          obsolete
    DESCRIPTION     
            "Maximum number of Service Groups for this gateway.  This object is 
             not used and was made obsolete in GSX release 5.1."
    DEFVAL          { 500 }
    ::= { sonusTrunkConfigObjects 4 }

sonusTgMaxSgInstances OBJECT-TYPE
    SYNTAX          INTEGER (1..65535)
    ACCESS          read-write
    STATUS          obsolete
    DESCRIPTION     
            "Maximum number of Service Group Instances for this gateway. This object is 
             not used and was made obsolete in GSX release 5.1."
    DEFVAL          { 500 }
    ::= { sonusTrunkConfigObjects 5 }

sonusTgObjects OBJECT IDENTIFIER
    ::= { sonusTrunkObjects 2 }

sonusTgNextIndex OBJECT-TYPE
    SYNTAX          INTEGER
    ACCESS          read-only
    STATUS          mandatory
    DESCRIPTION     
            "The next valid index to use when creating a new sonusTgEntry"
    ::= { sonusTgObjects 1 }

sonusTgTable OBJECT-TYPE
    SYNTAX          SEQUENCE OF SonusTgEntry
    ACCESS          not-accessible
    STATUS          mandatory
    DESCRIPTION     
            "A list of trunk group entries."
    ::= { sonusTgObjects 2 }

sonusTgEntry OBJECT-TYPE
    SYNTAX          SonusTgEntry
    ACCESS          not-accessible
    STATUS          mandatory
    DESCRIPTION     
            "Each sonusTgEntry containing configuration objects.
             Rules & Behaviors:
                  A sonusTgEntry cannot be deleted when it is enabled.
                  When disabling the trunk group entry, it must not have 
                  any associated SGs.  All SGs must be removed before
                  disabling the trunk group.
                  A sonusTgEntry cannot be modified when it is enabled."
    INDEX           { sonusTgIndex }
    ::= { sonusTgTable 1 }

SonusTgEntry ::=
    SEQUENCE {
        sonusTgIndex                    INTEGER,
        sonusTgName                     SonusName,
        sonusTgProfName                 DisplayString,
        sonusTgSgSelect                 INTEGER,
        sonusTgLnpTranslate             SonusBoolean,
        sonusTg800Translate             SonusBoolean,
        sonusTgCallingNumVerify         SonusBoolean,
        sonusTgInboundReserved          INTEGER,
        sonusTgIsupOnly                 SonusBoolean,
        sonusTgCarrier                  DisplayString,
        sonusTgIsupNode                 DisplayString,
        sonusTgAdminState               SonusAdminState,
        sonusTgMode                     INTEGER,
        sonusTgAction                   INTEGER,
        sonusTgTimeout                  INTEGER,
        sonusTgRowStatus                RowStatus,
        sonusTgCirResvState             INTEGER,
        sonusTgPriorityCallReserve      INTEGER,
        sonusTgIncomingCallReserve      INTEGER,
        sonusTgOutgoingCallReserve      INTEGER,
        sonusTgSfgType                  INTEGER,
        sonusTgNumber                   DisplayString,
        sonusTgRenameTimer              INTEGER,
        sonusTgAlternateName            DisplayString,
        sonusTgSilcState                INTEGER,
        sonusTgSilcMC1Percent           INTEGER,
        sonusTgSilcMC2Percent           INTEGER,
        sonusTgType                     INTEGER,
        sonusTgIpParentTgName           SonusNameReference,
        sonusTgIpNetworkSelectorTableName SonusNameReference,
        sonusTgIpCallLimit              INTEGER,
        sonusTgIpBandwidthLimit         INTEGER,
        sonusTgIpPacketOutageDetectionMinimumDuration             INTEGER,
        sonusTgIpPacketOutageDetectionMinimumCalls          INTEGER,
        sonusTgIpPacketOutageDetectionBandwidthLimitReduction                     INTEGER,
        sonusTgIpPacketOutageDetectionState   SonusAdminState,
        sonusTgIpDirection              INTEGER,
        sonusTgIpPacketOutageDetectionInterval      INTEGER,
        sonusTgMasterTgName             DisplayString,
        sonusTgMtrgCallsPerReq          INTEGER,
        sonusTgMtrgBWPerReq             INTEGER,
        sonusTgClearPacketOutageDetection INTEGER,
        sonusTgMaxSustainedCallRate     INTEGER,
        sonusTgMaxCallBurstSize         INTEGER,
        sonusTgMaxSustainedSIPRegRate   INTEGER,
        sonusTgMaxSIPRegBurstSize       INTEGER,
        sonusTgHpcProfileName           SonusNameReference,
        sonusTgHpcSendEarlyAcm          INTEGER,
        sonusTgHpcIpOversubscriptionOverride    SonusAdminState,
        sonusTgHpcIpOversubscriptionFactor  Gauge,
        sonusTgLpTgProfIndex            Gauge,
        sonusTgEgressMaxSustainedCallRate Gauge,
        sonusTgEgressMaxCallBurstSize   Gauge,
        sonusTgEgressMaxSustainedSIPRegRate   Gauge,
        sonusTgEgressMaxSIPRegBurstSize Gauge,
        sonusTgEmerIpOversubscriptionFactor   Gauge,
        sonusTgIngressNonPriorityThreshold  Gauge,
        sonusTgEgressNonPriorityThreshold Gauge,
        sonusTgIpRegistrationLimit      INTEGER,
        sonusTgIpEstChild               INTEGER,
        sonusTgAdditionalData           DisplayString,
        sonusTgMlppProfileName          SonusNameReference,
        sonusTgResAllocation            INTEGER,
        sonusTgNormIpOversubscriptionFactor   Gauge,
        sonusTgBlockDirection           INTEGER,
        sonusTghonorSdpClockRate        SonusAdminState
    }

sonusTgIndex OBJECT-TYPE
    SYNTAX          INTEGER
    ACCESS          read-only
    STATUS          mandatory
    DESCRIPTION     
            "A unique value for each trunk group that is between 1
             and maximum allowed"
    ::= { sonusTgEntry 1 }

sonusTgName OBJECT-TYPE
    SYNTAX          SonusName
    ACCESS          read-write
    STATUS          mandatory
    DESCRIPTION     
            "The name of the trunk group.  The trunk group name must be present when the
             instance is created.  A trunk group can be renamed by setting sonusTgName
             in an existing instance.  When sonusTgName is set in an existing instance,
             the prior value of this object is placed in sonusTgAlternateName.  The new
             name will placed in sonusIsupsgServiceGroupTG from sonusIsupsg.mib, 
             sonusIsdnsgServiceGroupTrunkGroup from sonusIsdnsg.mib, and 
             sonusCassgServiceGroupTG from sonusCassg.mib.  Both the name in sonusTgName and 
             sonusTgAlternateName will be accepted for routing requests.  No other
             trunk group table instance can use the name in sonusTgName or 
             sonusTgAlternateName."
    ::= { sonusTgEntry 2 }

sonusTgProfName OBJECT-TYPE
    SYNTAX          DisplayString (SIZE(0..23))
    ACCESS          read-write
    STATUS          mandatory
    DESCRIPTION     
            "The name of the profile applied to this trunk group entry. "
    ::= { sonusTgEntry 3 }

sonusTgSgSelect OBJECT-TYPE
    SYNTAX          INTEGER { leastcost(1), configured(2), 
                        circularforward(3), circularbackward(4) }
    ACCESS          read-write
    STATUS          mandatory
    DESCRIPTION     
            "Selection for hunting within a PSTN trunk group that has 
             more than 1 associated service group(SG).
             It is either based on cost associated with each SG,
             how the SG is ordered during configuration (for circular also).
             		 If either circular option is chosen, then SG hunt algorithm
             		 is ignored."
    DEFVAL          { leastcost }
    ::= { sonusTgEntry 4 }

sonusTgLnpTranslate OBJECT-TYPE
    SYNTAX          SonusBoolean
    ACCESS          read-write
    STATUS          obsolete
    DESCRIPTION     
            "This is only meaningful for PSTN trunk groups that may require
             LNP translation for the called number.
             This object was obsoleted in release 5.0."
    DEFVAL          { true }
    ::= { sonusTgEntry 5 }

sonusTg800Translate OBJECT-TYPE
    SYNTAX          SonusBoolean
    ACCESS          read-write
    STATUS          obsolete
    DESCRIPTION     
            "This is only meaningful for PSTN trunk groups that may require
             800 number translation for the called number.
             This object was obsoleted in release 5.0."
    DEFVAL          { true }
    ::= { sonusTgEntry 6 }

sonusTgCallingNumVerify OBJECT-TYPE
    SYNTAX          SonusBoolean
    ACCESS          read-write
    STATUS          obsolete
    DESCRIPTION     
            "This is only meaningful for PSTN trunk groups that requires
             verification for the calling number.
             This object was obsoleted in release 5.0."
    DEFVAL          { true }
    ::= { sonusTgEntry 7 }

sonusTgInboundReserved OBJECT-TYPE
    SYNTAX          INTEGER (0..100)
    ACCESS          read-write
    STATUS          mandatory
    DESCRIPTION     
            "This is only meaninful for PSTN Trunk Groups.  This the
             percent of channels reserved for handling inbound calls.
             Default is 0% and valid for both direction type trunks.
             The amount reserved is round off to next number. For
             example, 50% of 23 hannels is 12.5 or 13 channels.  
             Percentage selection allowed in 5% increments."
    DEFVAL          { 0 }
    ::= { sonusTgEntry 8 }

sonusTgIsupOnly OBJECT-TYPE
    SYNTAX          SonusBoolean
    ACCESS          read-write
    STATUS          obsolete
    DESCRIPTION     
            "This is only meaningful for PSTN trunk groups that is either an
             ISUP only or mixed of ISUP and other PSTN types
             This object was obsoleted in release 5.0."
    DEFVAL          { true }
    ::= { sonusTgEntry 9 }

sonusTgCarrier OBJECT-TYPE
    SYNTAX          DisplayString (SIZE(0..23))
    ACCESS          read-write
    STATUS          mandatory
    DESCRIPTION     
            "This is only meaningful for PSTN trunk groups and is specific
             to Isup only.  This is the name of the Isup that this trunk 
             group is bound to. "
    ::= { sonusTgEntry 10 }

sonusTgIsupNode OBJECT-TYPE
    SYNTAX          DisplayString (SIZE(0..23))
    ACCESS          read-write
    STATUS          mandatory
    DESCRIPTION     
            "This is meaningful for PSTN trunk groups and is specific
             to Isup only.  This is the name of the Isup that this trunk 
             group is bound to. "
    ::= { sonusTgEntry 11 }

sonusTgAdminState OBJECT-TYPE
    SYNTAX          SonusAdminState
    ACCESS          read-write
    STATUS          mandatory
    DESCRIPTION     
            "Administrative state to disable or enable a trunk group. All
             trunk groups are created with its state disabled.  If trunk group
             is disabled, the trunk group must be enabled to allow calls to 
             proceed."
    DEFVAL          { disabled }
    ::= { sonusTgEntry 12 }

sonusTgMode OBJECT-TYPE
    SYNTAX          INTEGER { inService(1), outOfService(2) }
    ACCESS          read-write
    STATUS          mandatory
    DESCRIPTION     
            "The operation mode for this trunk."
    DEFVAL          { inService }
    ::= { sonusTgEntry 13 }

sonusTgAction OBJECT-TYPE
    SYNTAX          INTEGER { dryUp(1), force(2) }
    ACCESS          read-write
    STATUS          mandatory
    DESCRIPTION     
            "The action for the operation mode for this trunk."
    DEFVAL          { dryUp }
    ::= { sonusTgEntry 14 }

sonusTgTimeout OBJECT-TYPE
    SYNTAX          INTEGER (1..1440)
    ACCESS          read-write
    STATUS          mandatory
    DESCRIPTION     
            "Timeout value in minutes for the dry up action."
    DEFVAL          { 5 }
    ::= { sonusTgEntry 15 }

sonusTgRowStatus OBJECT-TYPE
    SYNTAX          RowStatus
    ACCESS          read-write
    STATUS          mandatory
    DESCRIPTION     
            "This is for SNMP use."
    ::= { sonusTgEntry 16 }

sonusTgCirResvState OBJECT-TYPE
    SYNTAX          INTEGER { disabled(1), enabled(2) }
    ACCESS          read-write
    STATUS          mandatory
    DESCRIPTION     
            "Administrative state to disable or enable the circuit reservation feature on a trunk group.
             All trunk groups are created with this feature disabled.  If this feature is enabled,
             the sonusTgInboundReserved feature is overriden automatically."
    DEFVAL          { disabled }
    ::= { sonusTgEntry 17 }

sonusTgPriorityCallReserve OBJECT-TYPE
    SYNTAX          INTEGER (0..100)
    ACCESS          read-write
    STATUS          mandatory
    DESCRIPTION     
            "The minimum number of priority call allowed set for this trunk group when sonusTgCirResvState 
             is set to enabled."
    DEFVAL          { 1 }
    ::= { sonusTgEntry 18 }

sonusTgIncomingCallReserve OBJECT-TYPE
    SYNTAX          INTEGER (0..128)
    ACCESS          read-write
    STATUS          mandatory
    DESCRIPTION     
            "The minimum number of incoming call allowed set for this trunk group when sonusTgCirResvState 
             is set to enabled."
    DEFVAL          { 1 }
    ::= { sonusTgEntry 19 }

sonusTgOutgoingCallReserve OBJECT-TYPE
    SYNTAX          INTEGER (0..100)
    ACCESS          read-write
    STATUS          mandatory
    DESCRIPTION     
            "The minimum percent of outgoing call allowed set for this trunk group when sonusTgCirResvState 
             is set to enabled."
    DEFVAL          { 10 }
    ::= { sonusTgEntry 20 }

sonusTgSfgType OBJECT-TYPE
    SYNTAX          INTEGER { none(1), ni2(2), dms(3), user(4) }
    ACCESS          read-write
    STATUS          mandatory
    DESCRIPTION     
            "The type of simulated facility group used by this trunk group."
    DEFVAL          { none }
    ::= { sonusTgEntry 21 }

sonusTgNumber OBJECT-TYPE
    SYNTAX          DisplayString (SIZE(4))
    ACCESS          read-write
    STATUS          mandatory
    DESCRIPTION     
            "A unique number assigned to the trunk group by the customer, used for circuit 
             validation testing purposes."
    DEFVAL          { "0000" }
    ::= { sonusTgEntry 22 }

sonusTgRenameTimer OBJECT-TYPE
    SYNTAX          INTEGER (0..3600)
    ACCESS          read-write
    STATUS          mandatory
    DESCRIPTION     
            "The amount of time in seconds that the alternate trunk group name will be accepted
             when a trunk group is renamed.  During this time, the alternate name cannot be used
             for the name of another trunk group.  If the timer value is set to 0, then
             the alternate trunk group name will be accepted until the sonusTgAlternateName object
             is set to a null string."
    DEFVAL          { 10 }
    ::= { sonusTgEntry 23 }

sonusTgAlternateName OBJECT-TYPE
    SYNTAX          DisplayString (SIZE(0..23))
    ACCESS          read-write
    STATUS          mandatory
    DESCRIPTION     
            "The alternate name of the trunk group.  sonusTgAlternateName automatically gets
             set to the prior value of sonusTgName when sonusTgName is set for an existing instance.
             sonusTgAlternateName automatically gets set to a null string when sonusTgRenameTimer
             expires.  If sonusTgRenameTimer is set to 0, sonusTgAlternateName may be set to
             a null string to remove the alternate trunk group name.  This object cannot be directly 
             set to any value other than the null string."
    ::= { sonusTgEntry 24 }

sonusTgSilcState OBJECT-TYPE
    SYNTAX          INTEGER { disabled(1), enabled(2) }
    ACCESS          read-write
    STATUS          mandatory
    DESCRIPTION     
            "Administrative state to enable/disable the SILC traffic control."
    DEFVAL          { 1 }
    ::= { sonusTgEntry 25 }

sonusTgSilcMC1Percent OBJECT-TYPE
    SYNTAX          INTEGER (0..100)
    ACCESS          read-write
    STATUS          mandatory
    DESCRIPTION     
            "The percentage of calls to accept when in machine congestion level 1."
    DEFVAL          { 75 }
    ::= { sonusTgEntry 26 }

sonusTgSilcMC2Percent OBJECT-TYPE
    SYNTAX          INTEGER (0..100)
    ACCESS          read-write
    STATUS          mandatory
    DESCRIPTION     
            "The percentage of calls to accept when in machine congestion level 2."
    DEFVAL          { 25 }
    ::= { sonusTgEntry 27 }

sonusTgType OBJECT-TYPE
    SYNTAX          INTEGER { pstn(1), ipSelected(2), ipLinked(3) }
    ACCESS          read-write
    STATUS          mandatory
    DESCRIPTION     
            "The type of trunk group. Selected IP Trunk Group is the
             one which can take calls and Linked IP Trunk is used in
             making IP Hierarchy. Selected IP Trunk is also called
             child and Linked is also called Parent."
    DEFVAL          { pstn }
    ::= { sonusTgEntry 28 }

sonusTgIpParentTgName OBJECT-TYPE
    SYNTAX          SonusNameReference
    ACCESS          read-write
    STATUS          mandatory
    DESCRIPTION     
            "The name of a parent IP trunk group. "
    ::= { sonusTgEntry 29 }

sonusTgIpNetworkSelectorTableName OBJECT-TYPE
    SYNTAX          SonusNameReference
    ACCESS          read-write
    STATUS          mandatory
    DESCRIPTION     
            "The name of the Network Selector table used
             by this trunk group.  This object is only valid
             for IP trunk groups."
    ::= { sonusTgEntry 30 }

sonusTgIpCallLimit OBJECT-TYPE
    SYNTAX          INTEGER (-1..2147483647)
    ACCESS          read-write
    STATUS          mandatory
    DESCRIPTION     
            "The number of calls allowed on this IP trunk group."
    DEFVAL          { -1 }
    ::= { sonusTgEntry 31 }

sonusTgIpBandwidthLimit OBJECT-TYPE
    SYNTAX          INTEGER (-1..2147483647)
    ACCESS          read-write
    STATUS          mandatory
    DESCRIPTION     
            "Bandwidth limit in units of 1K bits/sec."
    DEFVAL          { -1 }
    ::= { sonusTgEntry 32 }

sonusTgIpPacketOutageDetectionMinimumDuration OBJECT-TYPE
    SYNTAX          INTEGER (0..65535)
    ACCESS          read-write
    STATUS          mandatory
    DESCRIPTION     
            "This is the minimum outage on a call for that
             call to be counted as part of the packet outage
             detection algorithm.  The duration is in 
             units of milliseconds."
    DEFVAL          { 6000 }
    ::= { sonusTgEntry 33 }

sonusTgIpPacketOutageDetectionMinimumCalls OBJECT-TYPE
    SYNTAX          INTEGER (0..65535)
    ACCESS          read-write
    STATUS          mandatory
    DESCRIPTION     
            "The number of calls with outages required within
             the current interval to declare a packet outage event."
    DEFVAL          { 1000 }
    ::= { sonusTgEntry 34 }

sonusTgIpPacketOutageDetectionBandwidthLimitReduction OBJECT-TYPE
    SYNTAX          INTEGER (0..100)
    ACCESS          read-write
    STATUS          mandatory
    DESCRIPTION     
            "The amount to reduce the bandwidth limit (as a percentage
             of the configured limit) when a packet outage is detected."
    DEFVAL          { 50 }
    ::= { sonusTgEntry 35 }

sonusTgIpPacketOutageDetectionState OBJECT-TYPE
    SYNTAX          SonusAdminState
    ACCESS          read-write
    STATUS          mandatory
    DESCRIPTION     
            "Used to enable automatic bandwidth reduction when
             a packet outage is detected.  The bandwidth limit
             is restored when the feature is disabled."
    DEFVAL          { 1 }
    ::= { sonusTgEntry 36 }

sonusTgIpDirection OBJECT-TYPE
    SYNTAX          INTEGER { inComing(1), outGoing(2), bothWays(3) }
    ACCESS          read-write
    STATUS          mandatory
    DESCRIPTION     
            "The direction of calls on this IP trunk group.
             This object is only valid for IP trunk groups."
    DEFVAL          { 3 }
    ::= { sonusTgEntry 37 }

sonusTgIpPacketOutageDetectionInterval OBJECT-TYPE
    SYNTAX          INTEGER (5..1440)
    ACCESS          read-write
    STATUS          mandatory
    DESCRIPTION     
            "The size of the packet outage detection interval in
             minutes.  This object is only valid for IP trunk groups."
    DEFVAL          { 15 }
    ::= { sonusTgEntry 38 }

sonusTgMasterTgName OBJECT-TYPE
    SYNTAX          DisplayString (SIZE(0..23))
    ACCESS          read-write
    STATUS          mandatory
    DESCRIPTION     
            "This is the name of the Master trunk group that this trunk
             group is part of. "
    ::= { sonusTgEntry 39 }

sonusTgMtrgCallsPerReq OBJECT-TYPE
    SYNTAX          INTEGER (1..2000)
    ACCESS          read-write
    STATUS          mandatory
    DESCRIPTION     
            "This value determines the number of calls that will
             be requested when the TRM encounters the thresholds
             of exhaustion has been reached. This value is
             currently only used if the MTRG is of type IP.  This object
             acts as a threshold for requesting or freeing call allocation.
             When the number of available calls on a trunk group is
             less than this object, TRM requests more calls from MTRM.
             When the number of available calls on a trunk group is
             greater than 2 times this object, TRM frees calls that
             have been allocated by MTRM."
    DEFVAL          { 100 }
    ::= { sonusTgEntry 40 }

sonusTgMtrgBWPerReq OBJECT-TYPE
    SYNTAX          INTEGER (2480..248000)
    ACCESS          read-write
    STATUS          mandatory
    DESCRIPTION     
            "This value determines the amount of B/W in units of 1K bits/sec
             that will be requested when the TRM encounters the thresholds
             			of exhaustion has been reached. This value is only
             			used if the MTRG is of type IP.  This object acts 
             as a threshold for requesting or freeing bandwidth allocation.
             When the amount of available bandwidth on a trunk group is
             less than this object, TRM requests more bandwidth from MTRM.
             When the amount of available bandwidth on a trunk group is
             greater than 2 times this object, TRM frees bandwidth that
             has been allocated by MTRM."
    DEFVAL          { 12400 }
    ::= { sonusTgEntry 41 }

sonusTgClearPacketOutageDetection OBJECT-TYPE
    SYNTAX          INTEGER { noAction(1), clear(2) }
    ACCESS          read-write
    STATUS          mandatory
    DESCRIPTION     
            "Setting this object to clear, sets the sonusTgPacketOutageDetectionState
             to normal.  The available bandwidth will be set to the allocated 
             bandwidth.  If the trunk group is configured to be under the control
             of a master trunk group, then the the master trunk group will resume
             controlling the trunk group.  This is a momentary action object that
             gets set back to noAction after clearing the packet outage detection state.
             This object is only valid for IP trunk groups."
    DEFVAL          { 1 }
    ::= { sonusTgEntry 42 }

sonusTgMaxSustainedCallRate OBJECT-TYPE
    SYNTAX          INTEGER (0..65535)
    ACCESS          read-write
    STATUS          mandatory
    DESCRIPTION     
            "The maximum sustained call rate allowed in calls/second.  A value of
             0 means there is no limit on the call rate.
             This object is only valid for IP trunk groups."
    DEFVAL          { 0 }
    ::= { sonusTgEntry 43 }

sonusTgMaxCallBurstSize OBJECT-TYPE
    SYNTAX          INTEGER (0..65535)
    ACCESS          read-write
    STATUS          mandatory
    DESCRIPTION     
            "The maximum allowed burst of call attempts.  A value of 0
             means there is no burst limit.
             This object is only valid for IP trunk groups."
    DEFVAL          { 0 }
    ::= { sonusTgEntry 44 }

sonusTgMaxSustainedSIPRegRate OBJECT-TYPE
    SYNTAX          INTEGER (0..100)
    ACCESS          read-write
    STATUS          mandatory
    DESCRIPTION     
            "The maximum sustained rate on SIP registration allowed in 
             registrations/second.  A value of 0 means there is no limit 
             on the on SIP registration rate.
             This object is only valid for IP trunk groups."
    DEFVAL          { 0 }
    ::= { sonusTgEntry 45 }

sonusTgMaxSIPRegBurstSize OBJECT-TYPE
    SYNTAX          INTEGER (0..200)
    ACCESS          read-write
    STATUS          mandatory
    DESCRIPTION     
            "The maximum allowed burst of SIP registration attempts.  A value of 0
             means there is no burst limit.
             This object is only valid for IP trunk groups."
    DEFVAL          { 0 }
    ::= { sonusTgEntry 46 }

sonusTgHpcProfileName OBJECT-TYPE
    SYNTAX          SonusNameReference
    ACCESS          read-write
    STATUS          mandatory
    DESCRIPTION     
            "The name of the HPC trunk group profile."
    ::= { sonusTgEntry 47 }

sonusTgHpcSendEarlyAcm OBJECT-TYPE
    SYNTAX          INTEGER { on(1), off(2), useDefault(3) }
    ACCESS          read-write
    STATUS          mandatory
    DESCRIPTION     
            "When turned on, an ACM or SIP-183 will be sent when an HPC call
             is queued. If USEDEFAULT is selected, the sending of an early
             ACM or SIP-183 is controlled by the node-wide HPC configuration
             setting."
    DEFVAL          { useDefault }
    ::= { sonusTgEntry 48 }

sonusTgHpcIpOversubscriptionOverride OBJECT-TYPE
    SYNTAX          SonusAdminState
    ACCESS          read-write
    STATUS          mandatory
    DESCRIPTION     
            "If enabled, the IP oversubscription factor setting on this trunk group 
             overrides the oversubscription factor setting on the associated trunk
             group profile."
    DEFVAL          { disabled }
    ::= { sonusTgEntry 49 }

sonusTgHpcIpOversubscriptionFactor OBJECT-TYPE
    SYNTAX          Gauge (0..100)
    ACCESS          read-write
    STATUS          mandatory
    DESCRIPTION     
            "The percentage over the configured allowed
             resources for an IP trunk group that
             HPC calls can consume before being queued."
    DEFVAL          { 10 }
    ::= { sonusTgEntry 50 }

sonusTgLpTgProfIndex OBJECT-TYPE
    SYNTAX          Gauge (0..2048)
    ACCESS          read-write
    STATUS          mandatory
    DESCRIPTION     
            "The index of the local policy trunk group profile."
    DEFVAL          { 0 }
    ::= { sonusTgEntry 51 }

sonusTgEgressMaxSustainedCallRate OBJECT-TYPE
    SYNTAX          Gauge (0..65535)
    ACCESS          read-write
    STATUS          mandatory
    DESCRIPTION     
            "The maximum sustained call rate allowed in calls/second on egress trunk.
             A value of 0 means there is no limit on the call rate.
             This object is only valid for IP trunk groups."
    DEFVAL          { 0 }
    ::= { sonusTgEntry 52 }

sonusTgEgressMaxCallBurstSize OBJECT-TYPE
    SYNTAX          Gauge (0..65535)
    ACCESS          read-write
    STATUS          mandatory
    DESCRIPTION     
            "The maximum allowed burst of call attempts on egress trunk.
             A value of 0  means there is no burst limit.
             This object is only valid for IP trunk groups."
    DEFVAL          { 0 }
    ::= { sonusTgEntry 53 }

sonusTgEgressMaxSustainedSIPRegRate OBJECT-TYPE
    SYNTAX          Gauge (0..100)
    ACCESS          read-write
    STATUS          mandatory
    DESCRIPTION     
            "The maximum sustained rate on SIP registration allowed in 
             registrations/second on egress trunk.
             A value of 0 means there is no limit 
             on the on SIP registration rate.
             This object is only valid for IP trunk groups."
    DEFVAL          { 0 }
    ::= { sonusTgEntry 54 }

sonusTgEgressMaxSIPRegBurstSize OBJECT-TYPE
    SYNTAX          Gauge (0..200)
    ACCESS          read-write
    STATUS          mandatory
    DESCRIPTION     
            "The maximum allowed burst of SIP registration attempts on egress trunk. 
             A value of 0  means there is no burst limit.
             This object is only valid for IP trunk groups."
    DEFVAL          { 0 }
    ::= { sonusTgEntry 55 }

sonusTgEmerIpOversubscriptionFactor OBJECT-TYPE
    SYNTAX          Gauge (0..1000)
    ACCESS          read-write
    STATUS          mandatory
    DESCRIPTION     
            "The percentage over the configured allowed
             resources for an IP trunk group that
             Emergency calls can consume. Up to 10x can be allocated. "
    DEFVAL          { 10 }
    ::= { sonusTgEntry 56 }

sonusTgIngressNonPriorityThreshold OBJECT-TYPE
    SYNTAX          Gauge (0..200)
    ACCESS          read-write
    STATUS          mandatory
    DESCRIPTION     
            "The threshold is number of tokens reserved for priority calls when
             policing the call rate of non-priority calls.  A value of 0
             means there are no reserved tokens for priority calls.  The max threshold
             is also bound by ingress call rate burst size.  When tokens drop below 
             threshold, non-priority calls will be rejected.  This object is only valid
             for IP trunk groups."
    DEFVAL          { 0 }
    ::= { sonusTgEntry 57 }

sonusTgEgressNonPriorityThreshold OBJECT-TYPE
    SYNTAX          Gauge (0..200)
    ACCESS          read-write
    STATUS          mandatory
    DESCRIPTION     
            "The threshold is number of tokens reserved for priority calls when
             policing the call rate of non-priority calls.  A value of 0
             means there are no reserved tokens for priority calls.  The max threshold
             is also bound by egress call rate burst size.  When tokens drop below 
             threshold, non-priority calls will be rejected.  This object is only valid
             for IP trunk groups."
    DEFVAL          { 0 }
    ::= { sonusTgEntry 58 }

sonusTgIpRegistrationLimit OBJECT-TYPE
    SYNTAX          INTEGER (-1..2147483647)
    ACCESS          read-write
    STATUS          mandatory
    DESCRIPTION     
            "The number of registrations (RCBs) allowed on this IP trunk group."
    DEFVAL          { -1 }
    ::= { sonusTgEntry 59 }

sonusTgIpEstChild OBJECT-TYPE
    SYNTAX          INTEGER (1..256)
    ACCESS          read-write
    STATUS          mandatory
    DESCRIPTION     
            "The estimated number of child registrations
             (i.e., the estimated number of P-Associated-URIs in 200 OK)."
    DEFVAL          { 1 }
    ::= { sonusTgEntry 60 }

sonusTgAdditionalData OBJECT-TYPE
    SYNTAX          DisplayString (SIZE(1..63))
    ACCESS          read-write
    STATUS          mandatory
    DESCRIPTION     
            "Any additional data related to the trunk group. The data can be used to
             configure any meta data related to trunk group e.g. customer name.
             The Trunk Group related traps should carry this data so as to make the
              traps more descriptive of the Trunk Group."
    DEFVAL          { "" }
    ::= { sonusTgEntry 61 }

sonusTgMlppProfileName OBJECT-TYPE
    SYNTAX          SonusNameReference
    ACCESS          read-write
    STATUS          mandatory
    DESCRIPTION     
            "The name of the MLPP trunk group profile associated
             with this trunk group."
    ::= { sonusTgEntry 62 }

sonusTgResAllocation OBJECT-TYPE
    SYNTAX          INTEGER { localignored(1), localpreferred(2) }
    ACCESS          read-write
    STATUS          mandatory
    DESCRIPTION     
            "IP Trunk Group ressource allocation flag. "
    DEFVAL          { localignored }
    ::= { sonusTgEntry 63 }

sonusTgNormIpOversubscriptionFactor OBJECT-TYPE
    SYNTAX          Gauge (0..1000)
    ACCESS          read-write
    STATUS          mandatory
    DESCRIPTION     
            "The percentage over the configured allowed
             resources for an IP trunk group that
             Normal calls can consume. Up to 10x can be allocated. "
    DEFVAL          { 0 }
    ::= { sonusTgEntry 64 }

sonusTgBlockDirection OBJECT-TYPE
    SYNTAX          INTEGER { inComing(1), outGoing(2), bothWays(3), 
                        none(4) }
    ACCESS          read-write
    STATUS          mandatory
    DESCRIPTION     
            "The block direction for this trunk."
    DEFVAL          { none }
    ::= { sonusTgEntry 65 }

sonusTghonorSdpClockRate OBJECT-TYPE
    SYNTAX          SonusAdminState
    ACCESS          read-write
    STATUS          mandatory
    DESCRIPTION     
            "If disabled,then DTMF PT related to 8 KHz clock rate only shall be retrieved
             supporting the backward compatibility. If enabled DTMF PT related to
             16 KHz and other sampling rates of 24 KHz, 32 KHz etc. is supported."
    DEFVAL          { disabled }
    ::= { sonusTgEntry 66 }

sonusTgStatusTable OBJECT-TYPE
    SYNTAX          SEQUENCE OF SonusTgStatusEntry
    ACCESS          not-accessible
    STATUS          mandatory
    DESCRIPTION     
            "This table contains status information of a PSTN trunk group.
             There may not be any SG registered to a trunk group in which
             case all statistics will be zero."
    ::= { sonusTrunkObjects 3 }

sonusTgStatusEntry OBJECT-TYPE
    SYNTAX          SonusTgStatusEntry
    ACCESS          not-accessible
    STATUS          mandatory
    DESCRIPTION     
            "Each entry describes the current status of a PSTN trunk group."
    INDEX           { sonusTgStatusIndex }
    ::= { sonusTgStatusTable 1 }

SonusTgStatusEntry ::=
    SEQUENCE {
        sonusTgStatusIndex              INTEGER,
        sonusTgOperState                INTEGER,
        sonusTgPstnTotalAvailable       INTEGER,
        sonusTgPstnTotalInboundRsv      INTEGER,
        sonusTgPstnInboundUsage         INTEGER,
        sonusTgPstnOutboundUsage        INTEGER,
        sonusTgPstnTotalConfigured      INTEGER,
        sonusTgAccCurrentACL            INTEGER,
        sonusTgPriorityCallUsage        INTEGER,
        sonusTgPstnTotalOutCallRsv      INTEGER,
        sonusTgOneWayInTotalConfig      INTEGER,
        sonusTgOneWayInTotalAvail       INTEGER,
        sonusTgOneWayInUsage            INTEGER,
        sonusTgOneWayOutTotalConfig     INTEGER,
        sonusTgOneWayOutTotalAvail      INTEGER,
        sonusTgOneWayOutUsage           INTEGER,
        sonusTgTwoWayTotalConfig        INTEGER,
        sonusTgTwoWayTotalAvail         INTEGER,
        sonusTgTwoWayUsage              INTEGER,
        sonusTgBandwidthCurrentLimit    INTEGER,
        sonusTgBandwidthAvailable       INTEGER,
        sonusTgBandwidthInboundUsage    INTEGER,
        sonusTgBandwidthOutboundUsage   INTEGER,
        sonusTgMasterTgIndex            INTEGER,
        sonusTgMasterTgState            INTEGER,
        sonusTgMtrgBwAllocated          INTEGER,
        sonusTgMtrgCallsAllocated       INTEGER,
        sonusTgPacketOutageDetectionState INTEGER,
        sonusTgHpcOversubscribedCallsLimit  INTEGER,
        sonusTgHpcOversubscribedBandwidthLimit      INTEGER,
        sonusTgHpcOversubscribedCallsAvailable      INTEGER,
        sonusTgHpcOversubscribedBandwidthAvailable          INTEGER,
        sonusTgHpcOversubscribedCallsUsage  INTEGER,
        sonusTgHpcOversubscribedBandwidthUsage      INTEGER,
        sonusTgHpcCurrentQueuedCallCount INTEGER,
        sonusTgEmerOversubscribedCallsLimit   Gauge,
        sonusTgEmerOversubscribedBandwidthLimit       Gauge,
        sonusTgEmerOversubscribedCallsAvailable       Gauge,
        sonusTgEmerOversubscribedBandwidthAvailable           Gauge,
        sonusTgEmerOversubscribedCallsUsage   Gauge,
        sonusTgEmerOversubscribedBandwidthUsage       Gauge,
        sonusTgMlppTotalPreemptedCallCount  Gauge
    }

sonusTgStatusIndex OBJECT-TYPE
    SYNTAX          INTEGER
    ACCESS          read-only
    STATUS          mandatory
    DESCRIPTION     
            "A unique value for each trunk group between 1 and maximum 
             allowed."
    ::= { sonusTgStatusEntry 1 }

sonusTgOperState OBJECT-TYPE
    SYNTAX          INTEGER { inService(1), outOfService(2), 
                        oosPending(3) }
    ACCESS          read-only
    STATUS          mandatory
    DESCRIPTION     
            "Current operational state of the trunk group."
    ::= { sonusTgStatusEntry 2 }

sonusTgPstnTotalAvailable OBJECT-TYPE
    SYNTAX          INTEGER
    ACCESS          read-only
    STATUS          mandatory
    DESCRIPTION     
            "The sum of all available or unblocked channels for this trunk group.
             For GSX release 6.0, when the sonusTgType object is set to ipRoutable or
             ipResource, this object counts the total number of calls that can are available
             for use this trunk group."
    ::= { sonusTgStatusEntry 3 }

sonusTgPstnTotalInboundRsv OBJECT-TYPE
    SYNTAX          INTEGER
    ACCESS          read-only
    STATUS          mandatory
    DESCRIPTION     
            "This is meaningful for trunk groups that are configured for
             inbound or both directions only.  This is the reserved count 
             as specified by the percentage configured for this trunk group.
             For GSX release 6.0, when the sonusTgType object is set to ipRoutable or
             ipResource, this object shows the total number of calls that are reserved
             for inbound calls on this trunk group."
    ::= { sonusTgStatusEntry 4 }

sonusTgPstnInboundUsage OBJECT-TYPE
    SYNTAX          INTEGER
    ACCESS          read-only
    STATUS          mandatory
    DESCRIPTION     
            "This is only meaningful for trunk groups that are configured
             for inbound or both directions.  This reflects the current 
             inbound or incoming usage count of this trunk group.  For GSX release 6.0, 
             when the sonusTgType object is set to ipRoutable or ipResource, this object 
             reflects the total number of calls that are in use for inbound calls on 
             this trunk group."
    ::= { sonusTgStatusEntry 5 }

sonusTgPstnOutboundUsage OBJECT-TYPE
    SYNTAX          INTEGER
    ACCESS          read-only
    STATUS          mandatory
    DESCRIPTION     
            "This is only meaningful for PSTN trunk groups that are configured
             for outbound or both directions.  This reflects the current 
             outbound, outgoing or non-priority usage count of this trunk group.
             For GSX release 6.0, when the sonusTgType object is set to ipRoutable or 
             ipResource, this object reflects the total number of calls that are in use 
             for outbound calls on this trunk group."
    ::= { sonusTgStatusEntry 6 }

sonusTgPstnTotalConfigured OBJECT-TYPE
    SYNTAX          INTEGER
    ACCESS          read-only
    STATUS          mandatory
    DESCRIPTION     
            "The sum of all configured and registered PSTN channels for this trunk group.
             For GSX release 6.0, when the sonusTgType object is set to ipRoutable or 
             ipResource, this object reflects the total number of calls that are configured
             on this trunk group."
    ::= { sonusTgStatusEntry 7 }

sonusTgAccCurrentACL OBJECT-TYPE
    SYNTAX          INTEGER
    ACCESS          read-only
    STATUS          mandatory
    DESCRIPTION     
            "Current congestion level for the Trunk Group"
    ::= { sonusTgStatusEntry 8 }

sonusTgPriorityCallUsage OBJECT-TYPE
    SYNTAX          INTEGER
    ACCESS          read-only
    STATUS          mandatory
    DESCRIPTION     
            "This is only meaningful for trunk groups that are configured and
             when sonusTgCirResvState is enabled.  This reflects the current 
             priority usage count of this trunk group. For GSX release 6.0, when the 
             sonusTgType object is set to ipRoutable or ipResource, this object reflects 
             the total number of calls that are in use for priority calls on this trunk group."
    ::= { sonusTgStatusEntry 9 }

sonusTgPstnTotalOutCallRsv OBJECT-TYPE
    SYNTAX          INTEGER
    ACCESS          read-only
    STATUS          mandatory
    DESCRIPTION     
            "This is meaningful for trunk groups that are configured for
             ingoing call reservation.  This is the reserved count 
             as specified by the percentage configured for this trunk group.
             For GSX release 6.0, when the sonusTgType object is set to ipRoutable or 
             ipResource, this object reflects the total number of calls that are reserved
             for outbound calls on this trunk group."
    ::= { sonusTgStatusEntry 10 }

sonusTgOneWayInTotalConfig OBJECT-TYPE
    SYNTAX          INTEGER
    ACCESS          read-only
    STATUS          mandatory
    DESCRIPTION     
            "The sum of all configured and registered one way inbound PSTN channels for 
             this trunk group."
    ::= { sonusTgStatusEntry 11 }

sonusTgOneWayInTotalAvail OBJECT-TYPE
    SYNTAX          INTEGER
    ACCESS          read-only
    STATUS          mandatory
    DESCRIPTION     
            "The sum of all available or unblocked one way inbound PSTN channels for 
             this trunk group."
    ::= { sonusTgStatusEntry 12 }

sonusTgOneWayInUsage OBJECT-TYPE
    SYNTAX          INTEGER
    ACCESS          read-only
    STATUS          mandatory
    DESCRIPTION     
            "This is only meaningful for PSTN trunk groups that are configured
             for one way inbound direction.  This reflects the current one way
             inbound usage count of this trunk group."
    ::= { sonusTgStatusEntry 13 }

sonusTgOneWayOutTotalConfig OBJECT-TYPE
    SYNTAX          INTEGER
    ACCESS          read-only
    STATUS          mandatory
    DESCRIPTION     
            "The sum of all configured and registered one way outbound PSTN channels for 
             this trunk group."
    ::= { sonusTgStatusEntry 14 }

sonusTgOneWayOutTotalAvail OBJECT-TYPE
    SYNTAX          INTEGER
    ACCESS          read-only
    STATUS          mandatory
    DESCRIPTION     
            "The sum of all available or unblocked one way outbound PSTN channels for 
             this trunk group."
    ::= { sonusTgStatusEntry 15 }

sonusTgOneWayOutUsage OBJECT-TYPE
    SYNTAX          INTEGER
    ACCESS          read-only
    STATUS          mandatory
    DESCRIPTION     
            "This is only meaningful for PSTN trunk groups that are configured
             for one way outbound direction.  This reflects the current one way
             outbound usage count of this trunk group."
    ::= { sonusTgStatusEntry 16 }

sonusTgTwoWayTotalConfig OBJECT-TYPE
    SYNTAX          INTEGER
    ACCESS          read-only
    STATUS          mandatory
    DESCRIPTION     
            "The sum of all configured and registered two way PSTN channels for 
             this trunk group."
    ::= { sonusTgStatusEntry 17 }

sonusTgTwoWayTotalAvail OBJECT-TYPE
    SYNTAX          INTEGER
    ACCESS          read-only
    STATUS          mandatory
    DESCRIPTION     
            "The sum of all available or unblocked two way PSTN channels for 
             this trunk group."
    ::= { sonusTgStatusEntry 18 }

sonusTgTwoWayUsage OBJECT-TYPE
    SYNTAX          INTEGER
    ACCESS          read-only
    STATUS          mandatory
    DESCRIPTION     
            "This is only meaningful for PSTN trunk groups that are configured
             for two way.  This reflects the current two way usage count of this 
             trunk group."
    ::= { sonusTgStatusEntry 19 }

sonusTgBandwidthCurrentLimit OBJECT-TYPE
    SYNTAX          INTEGER
    ACCESS          read-only
    STATUS          mandatory
    DESCRIPTION     
            "This is the current bandwidth limit for this trunk group.
             It is initial set to the configured bandwidth limit but
             		 may be reduced due to packet outage detection events."
    ::= { sonusTgStatusEntry 20 }

sonusTgBandwidthAvailable OBJECT-TYPE
    SYNTAX          INTEGER
    ACCESS          read-only
    STATUS          mandatory
    DESCRIPTION     
            "This is how much bandwidth is available for allocation."
    ::= { sonusTgStatusEntry 21 }

sonusTgBandwidthInboundUsage OBJECT-TYPE
    SYNTAX          INTEGER
    ACCESS          read-only
    STATUS          mandatory
    DESCRIPTION     
            "This is how much bandwidth is in use for inbound traffic."
    ::= { sonusTgStatusEntry 22 }

sonusTgBandwidthOutboundUsage OBJECT-TYPE
    SYNTAX          INTEGER
    ACCESS          read-only
    STATUS          mandatory
    DESCRIPTION     
            "This is how much bandwidth is in use for outbound traffic."
    ::= { sonusTgStatusEntry 23 }

sonusTgMasterTgIndex OBJECT-TYPE
    SYNTAX          INTEGER
    ACCESS          read-only
    STATUS          mandatory
    DESCRIPTION     
            "The Master trunk group index."
    ::= { sonusTgStatusEntry 24 }

sonusTgMasterTgState OBJECT-TYPE
    SYNTAX          INTEGER { null(1), registration(2), awaitAudit(3), 
                        notMtrmReady(4), mtrmReady(5), trmReady(6) }
    ACCESS          read-only
    STATUS          mandatory
    DESCRIPTION     
            "This is the state of this trunk group relative to the master
             trunk group.  It is only valid if sonusTgMasterTgName is 
             configured.
                null            - sonusTgAdminState = disabled.
                registration    - A registration request has been sent
                                  to the master trunk group.
                awaitAudit      - The master trunk group has responded
                                  to the registration request and the
                                  trunk group is waiting for an audit 
                                  request.
                notMtrmReady    - The master trunk group is not ready
                                  to control the trunk group.  The trunk
                                  will accept calls using the local 
                                  MTRM configuration.
                mtrmReady       - The master trunk group has control of
                                  this trunk group."
    ::= { sonusTgStatusEntry 25 }

sonusTgMtrgBwAllocated OBJECT-TYPE
    SYNTAX          INTEGER
    ACCESS          read-only
    STATUS          mandatory
    DESCRIPTION     
            "This is how much bandwidth the master trunk group has allocated
             to this trunk group.  It is set to sonusTgIpBandwidthLimit when 
             sonusTgMasterTgState is not set to mtrmReady."
    ::= { sonusTgStatusEntry 26 }

sonusTgMtrgCallsAllocated OBJECT-TYPE
    SYNTAX          INTEGER
    ACCESS          read-only
    STATUS          mandatory
    DESCRIPTION     
            "This is how many calls the master trunk group has allocated
             to this trunk group.  It is set to sonusTgIpCallLimit when 
             sonusTgMasterTgState is not set to mtrmReady."
    ::= { sonusTgStatusEntry 27 }

sonusTgPacketOutageDetectionState OBJECT-TYPE
    SYNTAX          INTEGER { normal(1), packetOutageState(2) }
    ACCESS          read-only
    STATUS          mandatory
    DESCRIPTION     
            "This object indicates the packet outage detection state.
             normal              - No packet outage has been declared.
                                   sonusTgBandwidthCurrentLimit = 
                                   sonusTgMtrgBwAllocated.
             packetOutageState   - Packet outage has been declared.
                                   sonusTgBandwidthCurrentLimit has been 
                                   reduced by 
                                   sonusTgIpPacketOutageDetectionBandwidthLimitReduction.
                                   The trunk group will no longer request or free bandwidth
                                   under the control of a master trunk group."
    ::= { sonusTgStatusEntry 28 }

sonusTgHpcOversubscribedCallsLimit OBJECT-TYPE
    SYNTAX          INTEGER
    ACCESS          read-only
    STATUS          mandatory
    DESCRIPTION     
            "TBD."
    ::= { sonusTgStatusEntry 29 }

sonusTgHpcOversubscribedBandwidthLimit OBJECT-TYPE
    SYNTAX          INTEGER
    ACCESS          read-only
    STATUS          mandatory
    DESCRIPTION     
            "TBD."
    ::= { sonusTgStatusEntry 30 }

sonusTgHpcOversubscribedCallsAvailable OBJECT-TYPE
    SYNTAX          INTEGER
    ACCESS          read-only
    STATUS          mandatory
    DESCRIPTION     
            "TBD."
    ::= { sonusTgStatusEntry 31 }

sonusTgHpcOversubscribedBandwidthAvailable OBJECT-TYPE
    SYNTAX          INTEGER
    ACCESS          read-only
    STATUS          mandatory
    DESCRIPTION     
            "TBD."
    ::= { sonusTgStatusEntry 32 }

sonusTgHpcOversubscribedCallsUsage OBJECT-TYPE
    SYNTAX          INTEGER
    ACCESS          read-only
    STATUS          mandatory
    DESCRIPTION     
            "TBD."
    ::= { sonusTgStatusEntry 33 }

sonusTgHpcOversubscribedBandwidthUsage OBJECT-TYPE
    SYNTAX          INTEGER
    ACCESS          read-only
    STATUS          mandatory
    DESCRIPTION     
            "TBD."
    ::= { sonusTgStatusEntry 34 }

sonusTgHpcCurrentQueuedCallCount OBJECT-TYPE
    SYNTAX          INTEGER
    ACCESS          read-only
    STATUS          mandatory
    DESCRIPTION     
            "TBD."
    ::= { sonusTgStatusEntry 35 }

sonusTgEmerOversubscribedCallsLimit OBJECT-TYPE
    SYNTAX          Gauge
    ACCESS          read-only
    STATUS          mandatory
    DESCRIPTION     
            "Oversubscription call limit is computed as
             emergency oversubscription factor * normal call limit."
    ::= { sonusTgStatusEntry 36 }

sonusTgEmerOversubscribedBandwidthLimit OBJECT-TYPE
    SYNTAX          Gauge
    ACCESS          read-only
    STATUS          mandatory
    DESCRIPTION     
            "Oversubscription bandwidth limit is computed as
             emergency oversubscription factor * normal bandwidth limit."
    ::= { sonusTgStatusEntry 37 }

sonusTgEmerOversubscribedCallsAvailable OBJECT-TYPE
    SYNTAX          Gauge
    ACCESS          read-only
    STATUS          mandatory
    DESCRIPTION     
            "Oversubscribed calls available = 
             oversubscribed call limit - oversubscribed call used."
    ::= { sonusTgStatusEntry 38 }

sonusTgEmerOversubscribedBandwidthAvailable OBJECT-TYPE
    SYNTAX          Gauge
    ACCESS          read-only
    STATUS          mandatory
    DESCRIPTION     
            "Oversubscribed bandwidth available = 
             oversubscribed bandwidth limit - oversubscribed bandwidth used."
    ::= { sonusTgStatusEntry 39 }

sonusTgEmerOversubscribedCallsUsage OBJECT-TYPE
    SYNTAX          Gauge
    ACCESS          read-only
    STATUS          mandatory
    DESCRIPTION     
            "Oversubscribed calls used = number of active emergency
             oversubscribed calls."
    ::= { sonusTgStatusEntry 40 }

sonusTgEmerOversubscribedBandwidthUsage OBJECT-TYPE
    SYNTAX          Gauge
    ACCESS          read-only
    STATUS          mandatory
    DESCRIPTION     
            "Oversubscribed bandwidth used = amount of active emergency
             oversubscribed bandwidth."
    ::= { sonusTgStatusEntry 41 }

sonusTgMlppTotalPreemptedCallCount OBJECT-TYPE
    SYNTAX          Gauge
    ACCESS          read-only
    STATUS          mandatory
    DESCRIPTION     
            "Total number of calls which were preempted on this trunk group."
    ::= { sonusTgStatusEntry 42 }

sonusTgSgTable OBJECT-TYPE
    SYNTAX          SEQUENCE OF SonusTgSgEntry
    ACCESS          not-accessible
    STATUS          mandatory
    DESCRIPTION     
            "This is a virtual table containing a list of service groups
             that belong to the same trunk group.   This is a doubly
             indexed table so that further details about each service
             group may be queried by name."
    ::= { sonusTrunkObjects 4 }

sonusTgSgEntry OBJECT-TYPE
    SYNTAX          SonusTgSgEntry
    ACCESS          not-accessible
    STATUS          mandatory
    DESCRIPTION     
            "Each entry lists the name and order of each service group."
    INDEX           { sonusTgSgTgIndex, sonusTgSgIndex }
    ::= { sonusTgSgTable 1 }

SonusTgSgEntry ::=
    SEQUENCE {
        sonusTgSgTgIndex                INTEGER,
        sonusTgSgIndex                  INTEGER,
        sonusTgSgName                   DisplayString,
        sonusTgSgType                   INTEGER
    }

sonusTgSgTgIndex OBJECT-TYPE
    SYNTAX          INTEGER
    ACCESS          read-only
    STATUS          mandatory
    DESCRIPTION     
            "The Trunk Group index that has the following set of Service Groups."
    ::= { sonusTgSgEntry 1 }

sonusTgSgIndex OBJECT-TYPE
    SYNTAX          INTEGER
    ACCESS          read-only
    STATUS          mandatory
    DESCRIPTION     
            "A unique value for each service group in this trunk group"
    ::= { sonusTgSgEntry 2 }

sonusTgSgName OBJECT-TYPE
    SYNTAX          DisplayString (SIZE(0..23))
    ACCESS          read-only
    STATUS          mandatory
    DESCRIPTION     
            "The name of the service group."
    ::= { sonusTgSgEntry 3 }

sonusTgSgType OBJECT-TYPE
    SYNTAX          INTEGER { ss7(1), cas(2), isdn(3), h323(4), 
                        gateway(5), dedicated(6), ras(7), mgcp(8), 
                        asg(9), staticpstn(10), staticip(11), sip(12) }
    ACCESS          read-only
    STATUS          mandatory
    DESCRIPTION     
            "The type of the service group."
    ::= { sonusTgSgEntry 4 }

sonusTgProfileObjects OBJECT IDENTIFIER
    ::= { sonusTrunkObjects 5 }

sonusTgProfileNextIndex OBJECT-TYPE
    SYNTAX          INTEGER
    ACCESS          read-only
    STATUS          mandatory
    DESCRIPTION     
            "The next valid index to use when creating a new sonusTgProfileEntry"
    ::= { sonusTgProfileObjects 5 }

sonusTgProfileTable OBJECT-TYPE
    SYNTAX          SEQUENCE OF SonusTgProfileEntry
    ACCESS          not-accessible
    STATUS          mandatory
    DESCRIPTION     
            "A list of trunk group entries."
    ::= { sonusTgProfileObjects 6 }

sonusTgProfileEntry OBJECT-TYPE
    SYNTAX          SonusTgProfileEntry
    ACCESS          not-accessible
    STATUS          mandatory
    DESCRIPTION     
            "Each sonusTgProfileEntry containing configuration objects.
             Rules & Behaviors:
                  A sonusTgProfileEntry cannot be deleted when it is enabled.
                  When disabling the trunk group entry, it must not have 
                  any associated SGs.  All SGs must be removed before
                  disabling the trunk group.
                  A sonusTgProfileEntry cannot be modified when it is enabled."
    INDEX           { sonusTgProfileIndex }
    ::= { sonusTgProfileTable 1 }

SonusTgProfileEntry ::=
    SEQUENCE {
        sonusTgProfileIndex             INTEGER,
        sonusTgProfileName              SonusName,
        sonusTgProfileSgSelect          INTEGER,
        sonusTgProfileAdminState        INTEGER,
        sonusTgProfileInboundReserved   INTEGER,
        sonusTgProfileLnpTranslate      SonusBoolean,
        sonusTgProfile800Translate      SonusBoolean,
        sonusTgProfileCallingNumVerify  SonusBoolean,
        sonusTgProfileIsupOnly          SonusBoolean,
        sonusTgProfileCarrier           DisplayString,
        sonusTgProfileIsupNode          DisplayString,
        sonusTgProfSgSelectState        INTEGER,
        sonusTgProfInboundReservedState INTEGER,
        sonusTgProfLnpTranslateState    INTEGER,
        sonusTgProf800TranslateState    INTEGER,
        sonusTgProfCallingNumVerifyState INTEGER,
        sonusTgProfIsupOnlyState        INTEGER,
        sonusTgProfCarrierState         INTEGER,
        sonusTgProfIsupNodeState        INTEGER,
        sonusTgProfileRowStatus         RowStatus,
        sonusTgProfileSfgType           INTEGER,
        sonusTgProfileSilcState         INTEGER,
        sonusTgProfileSilcMC1Percent    INTEGER,
        sonusTgProfileSilcMC2Percent    INTEGER
    }

sonusTgProfileIndex OBJECT-TYPE
    SYNTAX          INTEGER
    ACCESS          read-only
    STATUS          mandatory
    DESCRIPTION     
            "A unique value for each trunk group profile that is between 1
             and maximum allowed"
    ::= { sonusTgProfileEntry 1 }

sonusTgProfileName OBJECT-TYPE
    SYNTAX          SonusName
    ACCESS          read-write
    STATUS          mandatory
    DESCRIPTION     
            "The name of this trunk group Profile."
    ::= { sonusTgProfileEntry 2 }

sonusTgProfileSgSelect OBJECT-TYPE
    SYNTAX          INTEGER { leastcost(1), configured(2), 
                        circularforward(3), circularbackward(4) }
    ACCESS          read-write
    STATUS          mandatory
    DESCRIPTION     
            "Selection for hunting within a PSTN trunk group that has 
             more than 1 associated service group(SG).
             It is based on cost associated with each SG,
             how the SG is ordered during configuration (for circular also).
             		 If either circular option is chosen, then SG hunt algorithm
             		 is ignored."
    DEFVAL          { leastcost }
    ::= { sonusTgProfileEntry 3 }

sonusTgProfileAdminState OBJECT-TYPE
    SYNTAX          INTEGER { disabled(1), enabled(2) }
    ACCESS          read-write
    STATUS          mandatory
    DESCRIPTION     
            "Administrator state to use a trunk group Profile. All trunk
             group profiles are created with its state disabled.  When 
             disabled, the profile must be enabled to allowed to be used."
    DEFVAL          { disabled }
    ::= { sonusTgProfileEntry 4 }

sonusTgProfileInboundReserved OBJECT-TYPE
    SYNTAX          INTEGER (0..100)
    ACCESS          read-write
    STATUS          mandatory
    DESCRIPTION     
            "This is only meaninful for PSTN Trunk Groups.  This the
             percent of channels reserved for handling inbound calls.
             Default is 0% and valid for both direction type trunks.
             The amount reserved is round off to next number. For
             example, 50% of 23 hannels is 12.5 or 13 channels.  
             Percentage selection allowed in 5% increments."
    ::= { sonusTgProfileEntry 5 }

sonusTgProfileLnpTranslate OBJECT-TYPE
    SYNTAX          SonusBoolean
    ACCESS          read-write
    STATUS          obsolete
    DESCRIPTION     
            "This is only meaningful for PSTN trunk groups that may require
             LNP translation for the called number.
             This object was obsoleted in release 5.0."
    ::= { sonusTgProfileEntry 6 }

sonusTgProfile800Translate OBJECT-TYPE
    SYNTAX          SonusBoolean
    ACCESS          read-write
    STATUS          obsolete
    DESCRIPTION     
            "This is only meaningful for PSTN trunk groups that may require
             800 number translation for the called number.
             This object was obsoleted in release 5.0."
    ::= { sonusTgProfileEntry 7 }

sonusTgProfileCallingNumVerify OBJECT-TYPE
    SYNTAX          SonusBoolean
    ACCESS          read-write
    STATUS          obsolete
    DESCRIPTION     
            "This is only meaningful for PSTN trunk groups that requires
             verification for the calling number.
             This object was obsoleted in release 5.0."
    ::= { sonusTgProfileEntry 8 }

sonusTgProfileIsupOnly OBJECT-TYPE
    SYNTAX          SonusBoolean
    ACCESS          read-write
    STATUS          obsolete
    DESCRIPTION     
            "This is only meaningful for PSTN trunk groups that is either an
             ISUP only or mixed of ISUP and other PSTN types.
             This object was obsoleted in release 5.0."
    ::= { sonusTgProfileEntry 9 }

sonusTgProfileCarrier OBJECT-TYPE
    SYNTAX          DisplayString (SIZE(0..23))
    ACCESS          read-write
    STATUS          mandatory
    DESCRIPTION     
            "This is only meaningful for PSTN trunk groups and is specific
             to Isup only.  This is the name of the Isup that this trunk 
             group is bound to. "
    ::= { sonusTgProfileEntry 10 }

sonusTgProfileIsupNode OBJECT-TYPE
    SYNTAX          DisplayString (SIZE(0..23))
    ACCESS          read-write
    STATUS          mandatory
    DESCRIPTION     
            "This is only meaningful for PSTN trunk groups and is specific
             to Isup only.  This is the name of the Isup that this trunk 
             group is bound to. "
    ::= { sonusTgProfileEntry 11 }

sonusTgProfSgSelectState OBJECT-TYPE
    SYNTAX          INTEGER { disabled(1), enabled(2) }
    ACCESS          read-write
    STATUS          mandatory
    DESCRIPTION     
            "Indicates whether sonusTgProfileSgSelect object is present in this profile"
    ::= { sonusTgProfileEntry 12 }

sonusTgProfInboundReservedState OBJECT-TYPE
    SYNTAX          INTEGER { disabled(1), enabled(2) }
    ACCESS          read-write
    STATUS          mandatory
    DESCRIPTION     
            "Indicates whether sonusTgProfileInboundReserved object is present in this profile"
    ::= { sonusTgProfileEntry 13 }

sonusTgProfLnpTranslateState OBJECT-TYPE
    SYNTAX          INTEGER { disabled(1), enabled(2) }
    ACCESS          read-write
    STATUS          obsolete
    DESCRIPTION     
            "Indicates whether sonusTgProfileLnpTranslate object is present in this profile
             This object was obsoleted in release 5.0."
    ::= { sonusTgProfileEntry 14 }

sonusTgProf800TranslateState OBJECT-TYPE
    SYNTAX          INTEGER { disabled(1), enabled(2) }
    ACCESS          read-write
    STATUS          obsolete
    DESCRIPTION     
            "Indicates whether sonusTgProfile800Translate object is present in this profile
             This object was obsoleted in release 5.0."
    ::= { sonusTgProfileEntry 15 }

sonusTgProfCallingNumVerifyState OBJECT-TYPE
    SYNTAX          INTEGER { disabled(1), enabled(2) }
    ACCESS          read-write
    STATUS          obsolete
    DESCRIPTION     
            "Indicates whether sonusTgProfileCallingNumVerify object is present in this profile
             This object was obsoleted in release 5.0."
    ::= { sonusTgProfileEntry 16 }

sonusTgProfIsupOnlyState OBJECT-TYPE
    SYNTAX          INTEGER { disabled(1), enabled(2) }
    ACCESS          read-write
    STATUS          obsolete
    DESCRIPTION     
            "Indicates whether sonusTgProfileIsupOnly object is present in this profile
             This object was obsoleted in release 5.0."
    ::= { sonusTgProfileEntry 17 }

sonusTgProfCarrierState OBJECT-TYPE
    SYNTAX          INTEGER { disabled(1), enabled(2) }
    ACCESS          read-write
    STATUS          mandatory
    DESCRIPTION     
            "Indicates whether sonusTgProfileCarrier object is present in this profile"
    ::= { sonusTgProfileEntry 18 }

sonusTgProfIsupNodeState OBJECT-TYPE
    SYNTAX          INTEGER { disabled(1), enabled(2) }
    ACCESS          read-write
    STATUS          mandatory
    DESCRIPTION     
            "Indicates whether sonusTgProfileIsupNode object is present in this profile"
    ::= { sonusTgProfileEntry 19 }

sonusTgProfileRowStatus OBJECT-TYPE
    SYNTAX          RowStatus
    ACCESS          read-write
    STATUS          mandatory
    DESCRIPTION     
            "This is for SNMP use."
    ::= { sonusTgProfileEntry 20 }

sonusTgProfileSfgType OBJECT-TYPE
    SYNTAX          INTEGER { none(1), ni2(2), dms(3), user(4) }
    ACCESS          read-write
    STATUS          mandatory
    DESCRIPTION     
            "The type of simulated facility group used by this trunk group."
    DEFVAL          { 1 }
    ::= { sonusTgProfileEntry 21 }

sonusTgProfileSilcState OBJECT-TYPE
    SYNTAX          INTEGER { disabled(1), enabled(2) }
    ACCESS          read-write
    STATUS          mandatory
    DESCRIPTION     
            "Administrative state to enable/disable the SILC traffic control."
    DEFVAL          { 1 }
    ::= { sonusTgProfileEntry 22 }

sonusTgProfileSilcMC1Percent OBJECT-TYPE
    SYNTAX          INTEGER (0..100)
    ACCESS          read-write
    STATUS          mandatory
    DESCRIPTION     
            "The percentage of calls to accept when in machine congestion level 1."
    DEFVAL          { 75 }
    ::= { sonusTgProfileEntry 23 }

sonusTgProfileSilcMC2Percent OBJECT-TYPE
    SYNTAX          INTEGER (0..100)
    ACCESS          read-write
    STATUS          mandatory
    DESCRIPTION     
            "The percentage of calls to accept when in machine congestion level 2."
    DEFVAL          { 25 }
    ::= { sonusTgProfileEntry 24 }

sonusGatewayObjects OBJECT IDENTIFIER
    ::= { sonusTrunkGroupResourcesMIBObjects 2 }

sonusGatewayConfigObjects OBJECT IDENTIFIER
    ::= { sonusGatewayObjects 1 }

sonusTgMaxGateways OBJECT-TYPE
    SYNTAX          INTEGER (1..500)
    ACCESS          read-write
    STATUS          mandatory
    DESCRIPTION     
            "Maximum allowable destination or remote gateways in the configuration."
    DEFVAL          { 500 }
    ::= { sonusGatewayConfigObjects 1 }

sonusDestGatewayObjects OBJECT IDENTIFIER
    ::= { sonusGatewayObjects 2 }

sonusGatewayNextIndex OBJECT-TYPE
    SYNTAX          INTEGER
    ACCESS          read-only
    STATUS          mandatory
    DESCRIPTION     
            "The next valid index to use when creating a new sonusGatewayEntry"
    ::= { sonusDestGatewayObjects 1 }

sonusGatewayTable OBJECT-TYPE
    SYNTAX          SEQUENCE OF SonusGatewayEntry
    ACCESS          not-accessible
    STATUS          mandatory
    DESCRIPTION     
            "This is a table containing a list of IP telephony gateways 
             in the network."
    ::= { sonusDestGatewayObjects 2 }

sonusGatewayEntry OBJECT-TYPE
    SYNTAX          SonusGatewayEntry
    ACCESS          not-accessible
    STATUS          mandatory
    DESCRIPTION     
            "Each entry lists the name and order of each gateway."
    INDEX           { sonusGatewayIndex }
    ::= { sonusGatewayTable 1 }

SonusGatewayEntry ::=
    SEQUENCE {
        sonusGatewayIndex               INTEGER,
        sonusGatewayName                SonusName,
        sonusGatewayProfName            DisplayString,
        sonusGatewayType                INTEGER,
        sonusGatewayIpAddress           IpAddress,
        sonusGatewayPortNum             INTEGER,
        sonusGatewayMaxConn             INTEGER,
        sonusGatewayAdminState          INTEGER,
        sonusGatewayRowStatus           RowStatus
    }

sonusGatewayIndex OBJECT-TYPE
    SYNTAX          INTEGER
    ACCESS          read-only
    STATUS          mandatory
    DESCRIPTION     
            "A unique value for each gateway between 1 and maximum 
             allowed."
    ::= { sonusGatewayEntry 1 }

sonusGatewayName OBJECT-TYPE
    SYNTAX          SonusName
    ACCESS          read-write
    STATUS          mandatory
    DESCRIPTION     
            "The name of the IP Telephony gateway."
    ::= { sonusGatewayEntry 2 }

sonusGatewayProfName OBJECT-TYPE
    SYNTAX          DisplayString (SIZE(0..23))
    ACCESS          read-write
    STATUS          mandatory
    DESCRIPTION     
            "The name of the profile applied to this gateway entry. "
    ::= { sonusGatewayEntry 3 }

sonusGatewayType OBJECT-TYPE
    SYNTAX          INTEGER { gsxGateway(1), h323(2), sip(3) }
    ACCESS          read-write
    STATUS          mandatory
    DESCRIPTION     
            "The type of gateway."
    DEFVAL          { gsxGateway }
    ::= { sonusGatewayEntry 4 }

sonusGatewayIpAddress OBJECT-TYPE
    SYNTAX          IpAddress
    ACCESS          read-write
    STATUS          mandatory
    DESCRIPTION     
            "This is signaling Ip address of the gateway."
    ::= { sonusGatewayEntry 5 }

sonusGatewayPortNum OBJECT-TYPE
    SYNTAX          INTEGER (1..65535)
    ACCESS          read-write
    STATUS          mandatory
    DESCRIPTION     
            "This is the port number assigned for the signaling Ip address
             of the gateway (default is Sonus registered port 2569)."
    ::= { sonusGatewayEntry 6 }

sonusGatewayMaxConn OBJECT-TYPE
    SYNTAX          INTEGER (1..20000)
    ACCESS          read-write
    STATUS          obsolete
    DESCRIPTION     
            "This is the maximum connections allowed for this gateway to 
             the remote gateway specified by the sonusGatewayName. This object is 
             not used and was made obsolete in GSX release 5.1."
    DEFVAL          { 20000 }
    ::= { sonusGatewayEntry 7 }

sonusGatewayAdminState OBJECT-TYPE
    SYNTAX          INTEGER { disabled(1), enabled(2) }
    ACCESS          read-write
    STATUS          mandatory
    DESCRIPTION     
            "Allow administrator to disable or enable the connection from 
             this gateway to the remote gateway. All connections to the
             remote gateways are created with its state disabled.  Once 
             disabled, the gateway must be enabled to allow calls to 
             proceed again."
    DEFVAL          { disabled }
    ::= { sonusGatewayEntry 8 }

sonusGatewayRowStatus OBJECT-TYPE
    SYNTAX          RowStatus
    ACCESS          read-write
    STATUS          mandatory
    DESCRIPTION     
            "This is for SNMP use."
    ::= { sonusGatewayEntry 9 }

sonusDestGatewayStatusObjects OBJECT IDENTIFIER
    ::= { sonusGatewayObjects 3 }

sonusGwStatusTable OBJECT-TYPE
    SYNTAX          SEQUENCE OF SonusGwStatusEntry
    ACCESS          not-accessible
    STATUS          obsolete
    DESCRIPTION     
            "This is a table containing a list of IP telephony gateways 
             in the network. This table is 
             not used and was made obsolete in GSX release 5.1."
    ::= { sonusDestGatewayStatusObjects 3 }

sonusGwStatusEntry OBJECT-TYPE
    SYNTAX          SonusGwStatusEntry
    ACCESS          not-accessible
    STATUS          obsolete
    DESCRIPTION     
            "Each entry lists the current connections and order of each gateway. This object is 
             not used and was made obsolete in GSX release 5.1."
    INDEX           { sonusGwStatusIndex }
    ::= { sonusGwStatusTable 1 }

SonusGwStatusEntry ::=
    SEQUENCE {
        sonusGwStatusIndex              INTEGER,
        sonusGwCurrConnections          INTEGER
    }

sonusGwStatusIndex OBJECT-TYPE
    SYNTAX          INTEGER
    ACCESS          read-only
    STATUS          obsolete
    DESCRIPTION     
            "A unique value for each gateway between 1 and maximum 
             allowed. This object is 
             not used and was made obsolete in GSX release 5.1."
    ::= { sonusGwStatusEntry 1 }

sonusGwCurrConnections OBJECT-TYPE
    SYNTAX          INTEGER
    ACCESS          read-only
    STATUS          obsolete
    DESCRIPTION     
            "The Current number of connections between this gateway and
             the remote gateway. This object is 
             not used and was made obsolete in GSX release 5.1."
    ::= { sonusGwStatusEntry 2 }

sonusCarrierObjects OBJECT IDENTIFIER
    ::= { sonusTrunkGroupResourcesMIBObjects 3 }

sonusCarrierConfigObjects OBJECT IDENTIFIER
    ::= { sonusCarrierObjects 1 }

sonusTgMaxCarrierCodes OBJECT-TYPE
    SYNTAX          INTEGER (1..65535)
    ACCESS          read-write
    STATUS          mandatory
    DESCRIPTION     
            "Maximum number of Carrier Codes for this gateway."
    DEFVAL          { 500 }
    ::= { sonusCarrierConfigObjects 1 }

sonusCarrierCodeObjects OBJECT IDENTIFIER
    ::= { sonusCarrierObjects 2 }

sonusCarrierCodeNextIndex OBJECT-TYPE
    SYNTAX          INTEGER
    ACCESS          read-only
    STATUS          mandatory
    DESCRIPTION     
            "The next valid index to use when creating a new sonusCarrierCodeEntry"
    ::= { sonusCarrierCodeObjects 1 }

sonusCarrierCodeTable OBJECT-TYPE
    SYNTAX          SEQUENCE OF SonusCarrierCodeEntry
    ACCESS          not-accessible
    STATUS          mandatory
    DESCRIPTION     
            "This is a table containing a list of IP telephony gateways 
             in the network."
    ::= { sonusCarrierCodeObjects 2 }

sonusCarrierCodeEntry OBJECT-TYPE
    SYNTAX          SonusCarrierCodeEntry
    ACCESS          not-accessible
    STATUS          mandatory
    DESCRIPTION     
            "Each entry lists the name and order of each gateway."
    INDEX           { sonusCarrierCodeIndex }
    ::= { sonusCarrierCodeTable 1 }

SonusCarrierCodeEntry ::=
    SEQUENCE {
        sonusCarrierCodeIndex           INTEGER,
        sonusCarrierCodeName            SonusName,
        sonusCarrierCode                DisplayString,
        sonusCarrierCodeAdminState      INTEGER,
        sonusCarrierCodeRowStatus       RowStatus,
        sonusCarrierCodeNetworkIdType   INTEGER,
        sonusCarrierCodeNetworkIdPlan   INTEGER
    }

sonusCarrierCodeIndex OBJECT-TYPE
    SYNTAX          INTEGER
    ACCESS          read-only
    STATUS          mandatory
    DESCRIPTION     
            "A unique value for each carrier code between 1 and maximum 
             allowed."
    ::= { sonusCarrierCodeEntry 1 }

sonusCarrierCodeName OBJECT-TYPE
    SYNTAX          SonusName
    ACCESS          read-write
    STATUS          mandatory
    DESCRIPTION     
            "The name assigned to this carrier code."
    ::= { sonusCarrierCodeEntry 2 }

sonusCarrierCode OBJECT-TYPE
    SYNTAX          DisplayString (SIZE(1..4))
    ACCESS          read-write
    STATUS          mandatory
    DESCRIPTION     
            "This is the carrier code specified by the sonusCarrierCodeName.
             There are a maximum of up to 4 digits."
    ::= { sonusCarrierCodeEntry 3 }

sonusCarrierCodeAdminState OBJECT-TYPE
    SYNTAX          INTEGER { disabled(1), enabled(2) }
    ACCESS          read-write
    STATUS          mandatory
    DESCRIPTION     
            "Allow administrator to disable or enable this carrier code.  Once 
             disabled, this carrier code must be enabled to allow calls to 
             proceed again."
    DEFVAL          { disabled }
    ::= { sonusCarrierCodeEntry 4 }

sonusCarrierCodeRowStatus OBJECT-TYPE
    SYNTAX          RowStatus
    ACCESS          read-write
    STATUS          mandatory
    DESCRIPTION     
            "This is for SNMP use."
    ::= { sonusCarrierCodeEntry 5 }

sonusCarrierCodeNetworkIdType OBJECT-TYPE
    SYNTAX          INTEGER { ccitt(1), national(2), other(3) }
    ACCESS          read-write
    STATUS          mandatory
    DESCRIPTION     
            "The type of network identification for this carrier code"
    DEFVAL          { national }
    ::= { sonusCarrierCodeEntry 6 }

sonusCarrierCodeNetworkIdPlan OBJECT-TYPE
    SYNTAX          INTEGER { ccittunknown(1), ccittpublicdatanetwork(2), 
                        ccittlandmobilenetwork(3), ccittreserved1(4), 
                        ccittreserved2(5), nationalunknown(6), 
                        national3digitcarriercode(7), 
                        national4digitcarriercode(8), 
                        nationalreserved1(9), nationalreserved2(10) }
    ACCESS          read-write
    STATUS          mandatory
    DESCRIPTION     
            "The network identification plan for this carrier code"
    DEFVAL          { national4digitcarriercode }
    ::= { sonusCarrierCodeEntry 7 }

sonusSimulatedFacilityObjects OBJECT IDENTIFIER
    ::= { sonusTrunkGroupResourcesMIBObjects 4 }

sonusSfgTable OBJECT-TYPE
    SYNTAX          SEQUENCE OF SonusSfgEntry
    ACCESS          not-accessible
    STATUS          mandatory
    DESCRIPTION     
            "A list of simulated facility group entries."
    ::= { sonusSimulatedFacilityObjects 1 }

sonusSfgEntry OBJECT-TYPE
    SYNTAX          SonusSfgEntry
    ACCESS          not-accessible
    STATUS          mandatory
    DESCRIPTION     
            "Each sonusSfgEntry containing configuration objects.
             Rules & Behaviors:
                  A sonusSfgEntry can only be created for an existing trunk group.
                  All SFGs must be removed before deleting the trunk group."
    INDEX           { sonusSfgTgIndex, sonusSfgIndex }
    ::= { sonusSfgTable 1 }

SonusSfgEntry ::=
    SEQUENCE {
        sonusSfgTgIndex                 INTEGER,
        sonusSfgIndex                   INTEGER,
        sonusSfgServiceType             INTEGER,
        sonusSfgCarrierCode             DisplayString,
        sonusSfgFacilityCode            OCTET STRING,
        sonusSfgServiceIdentifier       INTEGER,
        sonusSfgDirection               INTEGER,
        sonusSfgBearerCap               OCTET STRING,
        sonusSfgMaxAllocation           INTEGER,
        sonusSfgDirNumber               DisplayString,
        sonusSfgOverflowSfg             INTEGER,
        sonusSfgAdminState              INTEGER,
        sonusSfgRowStatus               RowStatus
    }

sonusSfgTgIndex OBJECT-TYPE
    SYNTAX          INTEGER
    ACCESS          not-accessible
    STATUS          mandatory
    DESCRIPTION     
            "The trunk group index to which this simulated facilty group is
             associated"
    ::= { sonusSfgEntry 1 }

sonusSfgIndex OBJECT-TYPE
    SYNTAX          INTEGER (1..127)
    ACCESS          not-accessible
    STATUS          mandatory
    DESCRIPTION     
            "A unique value for each simulated facility group that is between 1
             and maximum allowed"
    ::= { sonusSfgEntry 2 }

sonusSfgServiceType OBJECT-TYPE
    SYNTAX          INTEGER { public(1), private(2), inWats(3), 
                        outWats(4), user(5) }
    ACCESS          read-write
    STATUS          mandatory
    DESCRIPTION     
            "The type of service defined for this simulated facility group.
             public  - This SFG is used for calls using a public numbering plan.
             private - This SFG is used for calls using a private numbering plan.
             inWats  - This SFG is used calls requesting an INWATS service.
             outWats - This SFG is used calls requesting an OUTWATS service.
             user    - This SFG is used for calls acting as the user side of a 
                       user-network interface."
    ::= { sonusSfgEntry 3 }

sonusSfgCarrierCode OBJECT-TYPE
    SYNTAX          DisplayString (SIZE(0..5))
    ACCESS          read-write
    STATUS          mandatory
    DESCRIPTION     
            "The network identification plan for this carrier code.  If present, 
             this SFG is used for calls with this carrier code.  If not present,
             this SFG is used for calls with all carrier codes.  Only IA5 characters 
             0 through 9 are valid."
    ::= { sonusSfgEntry 4 }

sonusSfgFacilityCode OBJECT-TYPE
    SYNTAX          OCTET STRING (SIZE(1))
    ACCESS          read-write
    STATUS          mandatory
    DESCRIPTION     
            "This is the facility coding value found in the NSF IE.  For incoming calls it 
             is used for service selection.  For outgoing calls it is used to code the NSF IE."
    ::= { sonusSfgEntry 5 }

sonusSfgServiceIdentifier OBJECT-TYPE
    SYNTAX          INTEGER (0..32767)
    ACCESS          read-write
    STATUS          mandatory
    DESCRIPTION     
            "The service identifier value used for the network specific facilites information 
             element.  this SFG is used for calls with this service parameter value.
             If not present, this SFG is used for calls with all service parameter values."
    ::= { sonusSfgEntry 6 }

sonusSfgDirection OBJECT-TYPE
    SYNTAX          INTEGER { twoWay(1), oneWayIn(2), oneWayOut(3) }
    ACCESS          read-write
    STATUS          mandatory
    DESCRIPTION     
            "The call direction used by this SFG.
             twoWay    - This SFG is used for calls in either direction.
             oneWayIn  - This SFG is used for calls in the inbound direction (.ie terminating service).
             oneWayOut - This SFG is used for calls in the outbound direction (.ie originating service)."
    ::= { sonusSfgEntry 7 }

sonusSfgBearerCap OBJECT-TYPE
    SYNTAX          OCTET STRING
--                       { speech(0), audio31k(1), data56k(2), 
--                         data64k(3) }
    ACCESS          read-write
    STATUS          mandatory
    DESCRIPTION     
            "The bearer capability used for this SFG. This SFG is used for calls with 
             the enabled bearer capabilities. If there is no bearer capability enabled,
             then bearer capability is not checked and this SFG is used for all
             bearer capabilities."
    DEFVAL          { 240 }
    ::= { sonusSfgEntry 8 }

sonusSfgMaxAllocation OBJECT-TYPE
    SYNTAX          INTEGER
    ACCESS          read-write
    STATUS          mandatory
    DESCRIPTION     
            "The maximum number of calls that can use this SFG."
    DEFVAL          { 9999 }
    ::= { sonusSfgEntry 9 }

sonusSfgDirNumber OBJECT-TYPE
    SYNTAX          DisplayString (SIZE(0..23))
    ACCESS          read-write
    STATUS          mandatory
    DESCRIPTION     
            "The directory number used for this SFG.  It can be used to provide an OUTWATS 
             billing numberor a number to be matched for an INWATS service."
    ::= { sonusSfgEntry 10 }

sonusSfgOverflowSfg OBJECT-TYPE
    SYNTAX          INTEGER (0..127)
    ACCESS          read-write
    STATUS          mandatory
    DESCRIPTION     
            "The SFG to use when this SFG reaches its maximum allocation.  If set to 0,
             then new calls are rejected when this SFG reaches its maximum allocation.
             If the specified SFG does not exist, then new calls are rejected when this 
             SFG reaches its maximum allocation."
    ::= { sonusSfgEntry 11 }

sonusSfgAdminState OBJECT-TYPE
    SYNTAX          INTEGER { disabled(1), enabled(2) }
    ACCESS          read-write
    STATUS          mandatory
    DESCRIPTION     
            "Administrative state to disable or enable a  SFG. All
             SFGs are created with its state disabled."
    DEFVAL          { disabled }
    ::= { sonusSfgEntry 12 }

sonusSfgRowStatus OBJECT-TYPE
    SYNTAX          RowStatus
    ACCESS          read-write
    STATUS          mandatory
    DESCRIPTION     
            "This object is used to create a new row or modify or delete an
             existing row in this table."
    ::= { sonusSfgEntry 13 }

sonusSfgStatTable OBJECT-TYPE
    SYNTAX          SEQUENCE OF SonusSfgStatEntry
    ACCESS          not-accessible
    STATUS          mandatory
    DESCRIPTION     
            "A list of simulated facility group statistics entries."
    ::= { sonusSimulatedFacilityObjects 2 }

sonusSfgStatEntry OBJECT-TYPE
    SYNTAX          SonusSfgStatEntry
    ACCESS          not-accessible
    STATUS          mandatory
    DESCRIPTION     
            "Each sonusSfgStatEntry contains objects for the SFG."
    INDEX           { sonusSfgStatTgIndex, sonusSfgStatIndex }
    ::= { sonusSfgStatTable 1 }

SonusSfgStatEntry ::=
    SEQUENCE {
        sonusSfgStatTgIndex             INTEGER,
        sonusSfgStatIndex               INTEGER,
        sonusSfgStatCurrentUsage        INTEGER,
        sonusSfgStatTotalAttempts       INTEGER,
        sonusSfgStatTotalFailures       INTEGER
    }

sonusSfgStatTgIndex OBJECT-TYPE
    SYNTAX          INTEGER
    ACCESS          not-accessible
    STATUS          mandatory
    DESCRIPTION     
            "The trunk group index to which this simulated facilty group is
             associated"
    ::= { sonusSfgStatEntry 1 }

sonusSfgStatIndex OBJECT-TYPE
    SYNTAX          INTEGER (1..127)
    ACCESS          not-accessible
    STATUS          mandatory
    DESCRIPTION     
            "A unique value for each simulated facility group that is between 1
             and maximum allowed"
    ::= { sonusSfgStatEntry 2 }

sonusSfgStatCurrentUsage OBJECT-TYPE
    SYNTAX          INTEGER
    ACCESS          read-only
    STATUS          mandatory
    DESCRIPTION     
            "The number of calls currently using this SFG."
    ::= { sonusSfgStatEntry 3 }

sonusSfgStatTotalAttempts OBJECT-TYPE
    SYNTAX          INTEGER
    ACCESS          read-only
    STATUS          mandatory
    DESCRIPTION     
            "The total number of call attempts for this SFG."
    ::= { sonusSfgStatEntry 4 }

sonusSfgStatTotalFailures OBJECT-TYPE
    SYNTAX          INTEGER
    ACCESS          read-only
    STATUS          mandatory
    DESCRIPTION     
            "The total number of call attempts that failed
             for this SFG."
    ::= { sonusSfgStatEntry 5 }

sonusTrunkMemberStatusObjects OBJECT IDENTIFIER
    ::= { sonusTrunkGroupResourcesMIBObjects 5 }

sonusTrunkMemberStatusTable OBJECT-TYPE
    SYNTAX          SEQUENCE OF SonusTrunkMemberStatusTableEntry
    ACCESS          not-accessible
    STATUS          mandatory
    DESCRIPTION     
            "This table contains status of assigned trunk member values."
    ::= { sonusTrunkMemberStatusObjects 1 }

sonusTrunkMemberStatusTableEntry OBJECT-TYPE
    SYNTAX          SonusTrunkMemberStatusTableEntry
    ACCESS          not-accessible
    STATUS          mandatory
    DESCRIPTION     
            "Status of an assigned trunk member."
    INDEX           { sonusTrunkMemberStatusTgIndex, 
                      sonusTrunkMemberStatusValue }
    ::= { sonusTrunkMemberStatusTable 1 }

SonusTrunkMemberStatusTableEntry ::=
    SEQUENCE {
        sonusTrunkMemberStatusTgIndex   INTEGER,
        sonusTrunkMemberStatusValue     INTEGER,
        sonusTrunkMemberStatusTgName    DisplayString,
        sonusTrunkMemberStatusServiceType DisplayString,
        sonusTrunkMemberStatusServiceName DisplayString,
        sonusTrunkMemberStatusReference DisplayString
    }

sonusTrunkMemberStatusTgIndex OBJECT-TYPE
    SYNTAX          INTEGER
    ACCESS          read-only
    STATUS          mandatory
    DESCRIPTION     
            "Trunk group Index for this Trunk Member"
    ::= { sonusTrunkMemberStatusTableEntry 1 }

sonusTrunkMemberStatusValue OBJECT-TYPE
    SYNTAX          INTEGER
    ACCESS          read-only
    STATUS          mandatory
    DESCRIPTION     
            "Value assigned to this Trunk Member"
    ::= { sonusTrunkMemberStatusTableEntry 2 }

sonusTrunkMemberStatusTgName OBJECT-TYPE
    SYNTAX          DisplayString (SIZE(0..23))
    ACCESS          read-only
    STATUS          mandatory
    DESCRIPTION     
            "Trunk group name for this Trunk Member"
    ::= { sonusTrunkMemberStatusTableEntry 3 }

sonusTrunkMemberStatusServiceType OBJECT-TYPE
    SYNTAX          DisplayString (SIZE(0..23))
    ACCESS          read-only
    STATUS          mandatory
    DESCRIPTION     
            "Service type (ISUP, ISDN, CAS) for this Trunk Member"
    ::= { sonusTrunkMemberStatusTableEntry 4 }

sonusTrunkMemberStatusServiceName OBJECT-TYPE
    SYNTAX          DisplayString (SIZE(0..23))
    ACCESS          read-only
    STATUS          mandatory
    DESCRIPTION     
            "Service group name for this Trunk Member"
    ::= { sonusTrunkMemberStatusTableEntry 5 }

sonusTrunkMemberStatusReference OBJECT-TYPE
    SYNTAX          DisplayString (SIZE(0..23))
    ACCESS          read-only
    STATUS          mandatory
    DESCRIPTION     
            "String reference to the specific circuit using the trunk member.
             For ISUP its the CIC number;
             For ISDN its the BChannel & interface
             For CAS  its the Ds1-PortName & channel reference"
    ::= { sonusTrunkMemberStatusTableEntry 6 }

sonusP2pObjects OBJECT IDENTIFIER
    ::= { sonusTrunkGroupResourcesMIBObjects 6 }

sonusP2pConfigObjects OBJECT IDENTIFIER
    ::= { sonusP2pObjects 1 }

sonusP2pRouteAdminState OBJECT-TYPE
    SYNTAX          INTEGER { disabled(1), enabled(2) }
    ACCESS          read-write
    STATUS          mandatory
    DESCRIPTION     
            "Configures the packet-to-packet routing admin state on this node.
             When disabled, all routes that result in packet-to-packet
             call scenarios will be skipped. The default state is DISABLED "
    DEFVAL          { disabled }
    ::= { sonusP2pConfigObjects 1 }

sonusNetworkSelectorObjects OBJECT IDENTIFIER
    ::= { sonusTrunkGroupResourcesMIBObjects 7 }

sonusIpNetworkSelectorTableObjects OBJECT IDENTIFIER
    ::= { sonusNetworkSelectorObjects 1 }

sonusIpNetworkSelectorTableNextIndex OBJECT-TYPE
    SYNTAX          INTEGER
    ACCESS          read-only
    STATUS          mandatory
    DESCRIPTION     
            "The next valid index to use when creating a new sonusIpNetworkSelectorTable"
    ::= { sonusIpNetworkSelectorTableObjects 1 }

sonusIpNetworkSelectorTableTable OBJECT-TYPE
    SYNTAX          SEQUENCE OF SonusIpNetworkSelectorTableEntry
    ACCESS          not-accessible
    STATUS          mandatory
    DESCRIPTION     
            "This mib table is used to create a name for a network selector table."
    ::= { sonusIpNetworkSelectorTableObjects 2 }

sonusIpNetworkSelectorTableEntry OBJECT-TYPE
    SYNTAX          SonusIpNetworkSelectorTableEntry
    ACCESS          not-accessible
    STATUS          mandatory
    DESCRIPTION     
            "This mib table is used to create a name for a network selector table."
    INDEX           { sonusIpNetworkSelectorTableIndex }
    ::= { sonusIpNetworkSelectorTableTable 1 }

SonusIpNetworkSelectorTableEntry ::=
    SEQUENCE {
        sonusIpNetworkSelectorTableIndex INTEGER,
        sonusIpNetworkSelectorTableName SonusName,
        sonusIpNetworkSelectorTableRowStatus    RowStatus,
        sonusIpNetworkSelectorTableUsage INTEGER
    }

sonusIpNetworkSelectorTableIndex OBJECT-TYPE
    SYNTAX          INTEGER
    ACCESS          read-only
    STATUS          mandatory
    DESCRIPTION     
            "A unique index for this network selector table name."
    ::= { sonusIpNetworkSelectorTableEntry 1 }

sonusIpNetworkSelectorTableName OBJECT-TYPE
    SYNTAX          SonusName
    ACCESS          read-write
    STATUS          mandatory
    DESCRIPTION     
            "The name of the network selector table."
    ::= { sonusIpNetworkSelectorTableEntry 2 }

sonusIpNetworkSelectorTableRowStatus OBJECT-TYPE
    SYNTAX          RowStatus
    ACCESS          read-write
    STATUS          mandatory
    DESCRIPTION     
            "This is for SNMP use."
    ::= { sonusIpNetworkSelectorTableEntry 3 }

sonusIpNetworkSelectorTableUsage OBJECT-TYPE
    SYNTAX          INTEGER { none(0), selector(1), naptq(2) }
    ACCESS          read-only
    STATUS          obsolete
    DESCRIPTION     
            "How this table is used, by trm as ip network 
             selector or SIPSG as napt qualification table"
    ::= { sonusIpNetworkSelectorTableEntry 4 }

sonusIpNetworkSelectorNumberObjects OBJECT IDENTIFIER
    ::= { sonusNetworkSelectorObjects 2 }

sonusIpNetworkSelectorNumberTable OBJECT-TYPE
    SYNTAX          SEQUENCE OF SonusIpNetworkSelectorNumberEntry
    ACCESS          not-accessible
    STATUS          mandatory
    DESCRIPTION     
            "This mib table is for Network Selector Table Entries."
    ::= { sonusIpNetworkSelectorNumberObjects 2 }

sonusIpNetworkSelectorNumberEntry OBJECT-TYPE
    SYNTAX          SonusIpNetworkSelectorNumberEntry
    ACCESS          not-accessible
    STATUS          mandatory
    DESCRIPTION     
            "This mib table is for Network Selector Table Entries."
    INDEX           { sonusIpNetworkSelectorNumberTableIndex, 
                      sonusIpNetworkSelectorNumberAddress, 
                      sonusIpNetworkSelectorNumberMask, 
                      sonusIpNetworkSelectorNumberIp6Address, 
                      sonusIpNetworkSelectorNumberIp6PrefixLen, 
                      sonusIpNetworkSelectorNumberIpVersion }
    ::= { sonusIpNetworkSelectorNumberTable 1 }

SonusIpNetworkSelectorNumberEntry ::=
    SEQUENCE {
        sonusIpNetworkSelectorNumberTableIndex      INTEGER,
        sonusIpNetworkSelectorNumberAddress   IpAddress,
        sonusIpNetworkSelectorNumberMask IpAddress,
        sonusIpNetworkSelectorNumberRowStatus     RowStatus,
        sonusIpNetworkSelectorNumberIp6Address      Ipv6Address,
        sonusIpNetworkSelectorNumberIp6PrefixLen        INTEGER,
        sonusIpNetworkSelectorNumberIpVersion     INTEGER
    }

sonusIpNetworkSelectorNumberTableIndex OBJECT-TYPE
    SYNTAX          INTEGER
    ACCESS          read-only
    STATUS          mandatory
    DESCRIPTION     
            "Unique Network Selector Table index."
    ::= { sonusIpNetworkSelectorNumberEntry 1 }

sonusIpNetworkSelectorNumberAddress OBJECT-TYPE
    SYNTAX          IpAddress
    ACCESS          read-only
    STATUS          mandatory
    DESCRIPTION     
            "Ip Address."
    ::= { sonusIpNetworkSelectorNumberEntry 2 }

sonusIpNetworkSelectorNumberMask OBJECT-TYPE
    SYNTAX          IpAddress
    ACCESS          read-only
    STATUS          mandatory
    DESCRIPTION     
            "Ip Mask."
    ::= { sonusIpNetworkSelectorNumberEntry 3 }

sonusIpNetworkSelectorNumberRowStatus OBJECT-TYPE
    SYNTAX          RowStatus
    ACCESS          read-write
    STATUS          mandatory
    DESCRIPTION     
            "This is for SNMP use."
    ::= { sonusIpNetworkSelectorNumberEntry 4 }

sonusIpNetworkSelectorNumberIp6Address OBJECT-TYPE
    SYNTAX          Ipv6Address
    ACCESS          read-only
    STATUS          mandatory
    DESCRIPTION     
            "Ipv6 Address"
    ::= { sonusIpNetworkSelectorNumberEntry 5 }

sonusIpNetworkSelectorNumberIp6PrefixLen OBJECT-TYPE
    SYNTAX          INTEGER
    ACCESS          read-write
    STATUS          mandatory
    DESCRIPTION     
            "Ipv6 Prefix Length"
    ::= { sonusIpNetworkSelectorNumberEntry 6 }

sonusIpNetworkSelectorNumberIpVersion OBJECT-TYPE
    SYNTAX          INTEGER { afInet(2), afInet6(24) }
    ACCESS          read-only
    STATUS          mandatory
    DESCRIPTION     
            "IP address version of the peer of this connection"
    ::= { sonusIpNetworkSelectorNumberEntry 7 }

sonusIpTgSelectionObjects OBJECT IDENTIFIER
    ::= { sonusTrunkGroupResourcesMIBObjects 8 }

sonusIpTgSelectionTable OBJECT-TYPE
    SYNTAX          SEQUENCE OF SonusIpTgSelectionEntry
    ACCESS          not-accessible
    STATUS          deprecated
    DESCRIPTION     
            "This table is used to show the the ingress and
             egress IP trunk group selection table."
    ::= { sonusIpTgSelectionObjects 1 }

sonusIpTgSelectionEntry OBJECT-TYPE
    SYNTAX          SonusIpTgSelectionEntry
    ACCESS          not-accessible
    STATUS          deprecated
    DESCRIPTION     
            "Each entry includes 4 indexes and an IP TG name.
             An IP TG is selected for a call by considering
             the SG type and call direction, and then using the
             network number and mask to do a longest prefix
             match."
    INDEX           { sonusIpTgSelectionSgType, 
                      sonusIpTgSelectionDirection, 
                      sonusIpTgSelectionNetworkNumber, 
                      sonusIpTgSelectionNetworkMask }
    ::= { sonusIpTgSelectionTable 1 }

SonusIpTgSelectionEntry ::=
    SEQUENCE {
        sonusIpTgSelectionSgType        INTEGER,
        sonusIpTgSelectionDirection     INTEGER,
        sonusIpTgSelectionNetworkNumber IpAddress,
        sonusIpTgSelectionNetworkMask   IpAddress,
        sonusIpTgSelectionTgName        SonusNameReference
    }

sonusIpTgSelectionSgType OBJECT-TYPE
    SYNTAX          INTEGER { h323(4), gateway(5), sip(12) }
    ACCESS          read-only
    STATUS          deprecated
    DESCRIPTION     
            "The type of IP service group."
    ::= { sonusIpTgSelectionEntry 1 }

sonusIpTgSelectionDirection OBJECT-TYPE
    SYNTAX          INTEGER { ingress(1), egress(2) }
    ACCESS          read-only
    STATUS          deprecated
    DESCRIPTION     
            "The direction of the call with respect to the GSX."
    ::= { sonusIpTgSelectionEntry 2 }

sonusIpTgSelectionNetworkNumber OBJECT-TYPE
    SYNTAX          IpAddress
    ACCESS          read-only
    STATUS          deprecated
    DESCRIPTION     
            "Network number."
    ::= { sonusIpTgSelectionEntry 3 }

sonusIpTgSelectionNetworkMask OBJECT-TYPE
    SYNTAX          IpAddress
    ACCESS          read-only
    STATUS          deprecated
    DESCRIPTION     
            "Network mask."
    ::= { sonusIpTgSelectionEntry 4 }

sonusIpTgSelectionTgName OBJECT-TYPE
    SYNTAX          SonusNameReference
    ACCESS          read-only
    STATUS          deprecated
    DESCRIPTION     
            "The name of the trunk group."
    ::= { sonusIpTgSelectionEntry 5 }

sonusNewIpTgSelectionTable OBJECT-TYPE
    SYNTAX          SEQUENCE OF SonusNewIpTgSelectionEntry
    ACCESS          not-accessible
    STATUS          mandatory
    DESCRIPTION     
            "This table is used to show the the ingress and
             egress IP trunk group selection table."
    ::= { sonusIpTgSelectionObjects 2 }

sonusNewIpTgSelectionEntry OBJECT-TYPE
    SYNTAX          SonusNewIpTgSelectionEntry
    ACCESS          not-accessible
    STATUS          mandatory
    DESCRIPTION     
            "Each entry includes 5 indexes and an IP TG name.
             An IP TG is selected for a call by considering
             the SG type, signaling port ID and call direction, 
             and then using the network number and mask to do
             a longest prefix match."
    INDEX           { sonusNewIpTgSelectionSgType, 
                      sonusNewIpTgSelectionSigZoneId, 
                      sonusNewIpTgSelectionDirection, 
                      sonusNewIpTgSelectionNetworkNumber, 
                      sonusNewIpTgSelectionNetworkMask, 
                      sonusNewIpTgSelectionNetworkNumberIp6, 
                      sonusNewIpTgSelectionNetworkNumberIp6PrefixLen, 
                      sonusNewIpTgSelectionNetworkNumberIpVersion }
    ::= { sonusNewIpTgSelectionTable 1 }

SonusNewIpTgSelectionEntry ::=
    SEQUENCE {
        sonusNewIpTgSelectionSgType     INTEGER,
        sonusNewIpTgSelectionSigZoneId  INTEGER,
        sonusNewIpTgSelectionDirection  INTEGER,
        sonusNewIpTgSelectionNetworkNumber  IpAddress,
        sonusNewIpTgSelectionNetworkMask IpAddress,
        sonusNewIpTgSelectionTgName     SonusNameReference,
        sonusNewIpTgSelectionNetworkNumberIp6     Ipv6Address,
        sonusNewIpTgSelectionNetworkNumberIp6PrefixLen              INTEGER,
        sonusNewIpTgSelectionNetworkNumberIpVersion           INTEGER
    }

sonusNewIpTgSelectionSgType OBJECT-TYPE
    SYNTAX          INTEGER { h323(4), gateway(5), sip(12) }
    ACCESS          read-only
    STATUS          mandatory
    DESCRIPTION     
            "The type of IP service group."
    ::= { sonusNewIpTgSelectionEntry 1 }

sonusNewIpTgSelectionSigZoneId OBJECT-TYPE
    SYNTAX          INTEGER
    ACCESS          read-only
    STATUS          mandatory
    DESCRIPTION     
            "The signaling zone ID of IP service group."
    ::= { sonusNewIpTgSelectionEntry 2 }

sonusNewIpTgSelectionDirection OBJECT-TYPE
    SYNTAX          INTEGER { ingress(1), egress(2) }
    ACCESS          read-only
    STATUS          mandatory
    DESCRIPTION     
            "The direction of the call with respect to the GSX."
    ::= { sonusNewIpTgSelectionEntry 3 }

sonusNewIpTgSelectionNetworkNumber OBJECT-TYPE
    SYNTAX          IpAddress
    ACCESS          read-only
    STATUS          mandatory
    DESCRIPTION     
            "Network number."
    ::= { sonusNewIpTgSelectionEntry 4 }

sonusNewIpTgSelectionNetworkMask OBJECT-TYPE
    SYNTAX          IpAddress
    ACCESS          read-only
    STATUS          mandatory
    DESCRIPTION     
            "Network mask."
    ::= { sonusNewIpTgSelectionEntry 5 }

sonusNewIpTgSelectionTgName OBJECT-TYPE
    SYNTAX          SonusNameReference
    ACCESS          read-only
    STATUS          mandatory
    DESCRIPTION     
            "The name of the trunk group."
    ::= { sonusNewIpTgSelectionEntry 6 }

sonusNewIpTgSelectionNetworkNumberIp6 OBJECT-TYPE
    SYNTAX          Ipv6Address
    ACCESS          read-only
    STATUS          mandatory
    DESCRIPTION     
            "Ipv6 Address"
    ::= { sonusNewIpTgSelectionEntry 7 }

sonusNewIpTgSelectionNetworkNumberIp6PrefixLen OBJECT-TYPE
    SYNTAX          INTEGER
    ACCESS          read-only
    STATUS          mandatory
    DESCRIPTION     
            "Ipv6 Prefix Length"
    ::= { sonusNewIpTgSelectionEntry 8 }

sonusNewIpTgSelectionNetworkNumberIpVersion OBJECT-TYPE
    SYNTAX          INTEGER { afInet(2), afInet6(24) }
    ACCESS          read-only
    STATUS          mandatory
    DESCRIPTION     
            "IP address version of the peer of this connection"
    ::= { sonusNewIpTgSelectionEntry 9 }

sonusHpcObjects OBJECT IDENTIFIER
    ::= { sonusTrunkGroupResourcesMIBObjects 9 }

sonusHpcTable OBJECT-TYPE
    SYNTAX          SEQUENCE OF SonusHpcEntry
    ACCESS          not-accessible
    STATUS          mandatory
    DESCRIPTION     
            "A list of HPC shelf-wide admin entries."
    ::= { sonusHpcObjects 2 }

sonusHpcEntry OBJECT-TYPE
    SYNTAX          SonusHpcEntry
    ACCESS          not-accessible
    STATUS          mandatory
    DESCRIPTION     
            "An HPC shelf-wide admin entry."
    INDEX           { sonusHpcShelfIndex }
    ::= { sonusHpcTable 1 }

SonusHpcEntry ::=
    SEQUENCE {
        sonusHpcShelfIndex              SonusShelfIndex,
        sonusHpcQueueLength             Gauge,
        sonusHpcEarlyAcmMode            INTEGER,
        sonusHpcRowStatus               RowStatus,
        sonusHpcUdpSignalingHpcDscp     INTEGER,
        sonusHpcUdpSignalingNonHpcDscp  INTEGER,
        sonusHpcUdpSignalingHpcCosValue INTEGER,
        sonusHpcUdpSignalingNonHpcCosValue  INTEGER
    }

sonusHpcShelfIndex OBJECT-TYPE
    SYNTAX          SonusShelfIndex
    ACCESS          not-accessible
    STATUS          mandatory
    DESCRIPTION     
            "Index of this table entry. This is equivalent to the GSX
             shelf index, i.e. one entry per GSX shelf."
    ::= { sonusHpcEntry 1 }

sonusHpcQueueLength OBJECT-TYPE
    SYNTAX          Gauge (1..1024)
    ACCESS          read-write
    STATUS          mandatory
    DESCRIPTION     
            "The maximum number of HPC calls that can be simultaneously queued
             on this GSX shelf."
    DEFVAL          { 256 }
    ::= { sonusHpcEntry 2 }

sonusHpcEarlyAcmMode OBJECT-TYPE
    SYNTAX          INTEGER { on(1), off(2) }
    ACCESS          read-write
    STATUS          mandatory
    DESCRIPTION     
            "When turned on, an ACM or SIP-183 will be sent when an HPC call
             is queued. This setting can be overridden by the HPC setting in
             a trunk group."
    DEFVAL          { off }
    ::= { sonusHpcEntry 3 }

sonusHpcRowStatus OBJECT-TYPE
    SYNTAX          RowStatus
    ACCESS          read-write
    STATUS          mandatory
    DESCRIPTION     
            "This is for SNMP use."
    ::= { sonusHpcEntry 4 }

sonusHpcUdpSignalingHpcDscp OBJECT-TYPE
    SYNTAX          INTEGER (0..63)
    ACCESS          read-write
    STATUS          mandatory
    DESCRIPTION     
            "Specifies the Diffserv Code Point (DSCP) value to be set in the 
             IP header of UDP packets transmitted as signaling for HPC calls.  
             This value is placed in the high-order 6 bits of the Type of Service 
             field.  It is also used to identify received signaling packets that 
             merit preferential treatment.  On input the high-order 6 bits of TOS 
             are matched to this value and the low-order 2 bits are disregarded."
    DEFVAL          { 0 }
    ::= { sonusHpcEntry 5 }

sonusHpcUdpSignalingNonHpcDscp OBJECT-TYPE
    SYNTAX          INTEGER (0..63)
    ACCESS          read-write
    STATUS          mandatory
    DESCRIPTION     
            "Specifies the Diffserv Code Point (DSCP) value to be set in the IP header 
             of UDP packets transmitted as signaling for non-HPC calls.  This value is 
             	 placed in the high-order 6 bits of the Type of Service field."
    DEFVAL          { 0 }
    ::= { sonusHpcEntry 6 }

sonusHpcUdpSignalingHpcCosValue OBJECT-TYPE
    SYNTAX          INTEGER (0..7)
    ACCESS          read-write
    STATUS          mandatory
    DESCRIPTION     
            " Specifies the Class of Service (COS) value to be set in the IEEE 802.1D User 
             Priority field of UDP packets transmitted as signaling for HPC calls.  Only has 
             an effect if the network interface supports 802.1Q tagged Ethernet frames.  
             The default value zero corresponds to best effort."
    DEFVAL          { 0 }
    ::= { sonusHpcEntry 7 }

sonusHpcUdpSignalingNonHpcCosValue OBJECT-TYPE
    SYNTAX          INTEGER (0..7)
    ACCESS          read-write
    STATUS          mandatory
    DESCRIPTION     
            " Specifies the Class of Service (COS) value to be set in the IEEE 802.1D User Priority 
             field of UDP packets transmitted as signaling for non-HPC calls.  Only has an effect 
             if the network interface supports 802.1Q tagged Ethernet frames.  
             The default value zero corresponds to best effort."
    DEFVAL          { 0 }
    ::= { sonusHpcEntry 8 }

sonusHpcStatTable OBJECT-TYPE
    SYNTAX          SEQUENCE OF SonusHpcStatEntry
    ACCESS          not-accessible
    STATUS          mandatory
    DESCRIPTION     
            "Table of shelf-wide HPC status."
    ::= { sonusHpcObjects 3 }

sonusHpcStatEntry OBJECT-TYPE
    SYNTAX          SonusHpcStatEntry
    ACCESS          not-accessible
    STATUS          mandatory
    DESCRIPTION     
            "Entry of shelf-wide HPC status."
    INDEX           { sonusHpcStatShelfIndex }
    ::= { sonusHpcStatTable 1 }

SonusHpcStatEntry ::=
    SEQUENCE {
        sonusHpcStatShelfIndex          SonusShelfIndex,
        sonusHpcStatTotalQueuedCallCount Gauge
    }

sonusHpcStatShelfIndex OBJECT-TYPE
    SYNTAX          SonusShelfIndex
    ACCESS          read-only
    STATUS          mandatory
    DESCRIPTION     
            "GSX Shelf Index of this HPC status."
    ::= { sonusHpcStatEntry 1 }

sonusHpcStatTotalQueuedCallCount OBJECT-TYPE
    SYNTAX          Gauge
    ACCESS          read-only
    STATUS          mandatory
    DESCRIPTION     
            "Total number of queued HPC calls on this shelf."
    ::= { sonusHpcStatEntry 2 }

sonusTgHpcProfObjects OBJECT IDENTIFIER
    ::= { sonusTrunkGroupResourcesMIBObjects 10 }

sonusHpcTgProfileNextIndex OBJECT-TYPE
    SYNTAX          Gauge
    ACCESS          not-accessible
    STATUS          mandatory
    DESCRIPTION     
            "The next valid index to use when creating a new sonusHpcTgProfileEntry"
    ::= { sonusTgHpcProfObjects 1 }

sonusHpcTgProfileTable OBJECT-TYPE
    SYNTAX          SEQUENCE OF SonusHpcTgProfileEntry
    ACCESS          not-accessible
    STATUS          mandatory
    DESCRIPTION     
            "A list of HPC trunk group profiles."
    ::= { sonusTgHpcProfObjects 2 }

sonusHpcTgProfileEntry OBJECT-TYPE
    SYNTAX          SonusHpcTgProfileEntry
    ACCESS          not-accessible
    STATUS          mandatory
    DESCRIPTION     
            "An HPC trunk group profile admin entry."
    INDEX           { sonusHpcTgProfileIndex }
    ::= { sonusHpcTgProfileTable 1 }

SonusHpcTgProfileEntry ::=
    SEQUENCE {
        sonusHpcTgProfileIndex          Gauge,
        sonusHpcTgProfileQueueLength    Gauge,
        sonusHpcTgProfileName           SonusName,
        sonusHpcTgProfileAnnouncementName SonusNameReference,
        sonusHpcTgProfileState          SonusAdminState,
        sonusHpcTgProfileTrunkGroupType INTEGER,
        sonusHpcTgProfileAnnouncementDelay  Gauge,
        sonusHpcTgProfileOversubscriptionFactor       Gauge,
        sonusHpcTgProfileTimeout        Gauge,
        sonusHpcTgProfileRowStatus      RowStatus,
        sonusHpcTgProfileUsePrecedence  SonusAdminState
    }

sonusHpcTgProfileIndex OBJECT-TYPE
    SYNTAX          Gauge
    ACCESS          not-accessible
    STATUS          mandatory
    DESCRIPTION     
            "Index of this table entry."
    ::= { sonusHpcTgProfileEntry 1 }

sonusHpcTgProfileQueueLength OBJECT-TYPE
    SYNTAX          Gauge (1..256)
    ACCESS          read-write
    STATUS          mandatory
    DESCRIPTION     
            "The maximum number of HPC calls that can be simultaneously queued
             on each trunk group that is associated with this profile."
    DEFVAL          { 5 }
    ::= { sonusHpcTgProfileEntry 2 }

sonusHpcTgProfileName OBJECT-TYPE
    SYNTAX          SonusName
    ACCESS          read-write
    STATUS          mandatory
    DESCRIPTION     
            "The name of this HPC trunk group Profile."
    ::= { sonusHpcTgProfileEntry 3 }

sonusHpcTgProfileAnnouncementName OBJECT-TYPE
    SYNTAX          SonusNameReference
    ACCESS          read-write
    STATUS          mandatory
    DESCRIPTION     
            "The name of the announcement used in the call queued announcement."
    ::= { sonusHpcTgProfileEntry 4 }

sonusHpcTgProfileState OBJECT-TYPE
    SYNTAX          SonusAdminState
    ACCESS          read-write
    STATUS          mandatory
    DESCRIPTION     
            "This enables and disables the HPC queuing of the trunk groups associated
             with this profile."
    DEFVAL          { disabled }
    ::= { sonusHpcTgProfileEntry 5 }

sonusHpcTgProfileTrunkGroupType OBJECT-TYPE
    SYNTAX          INTEGER { callqueuing(1), egressqueuing(2), 
                        intipqueuing(3), extipqueuing(4) }
    ACCESS          read-write
    STATUS          mandatory
    DESCRIPTION     
            "This indicates the type of HPC trunk group types: Call Queuing,
             Egress Queuing, Internal IP queuing or External IP Queuing."
    DEFVAL          { callqueuing }
    ::= { sonusHpcTgProfileEntry 6 }

sonusHpcTgProfileAnnouncementDelay OBJECT-TYPE
    SYNTAX          Gauge (1..90)
    ACCESS          read-write
    STATUS          mandatory
    DESCRIPTION     
            "The delay between two successive announcements in seconds."
    DEFVAL          { 15 }
    ::= { sonusHpcTgProfileEntry 7 }

sonusHpcTgProfileOversubscriptionFactor OBJECT-TYPE
    SYNTAX          Gauge (0..100)
    ACCESS          read-write
    STATUS          mandatory
    DESCRIPTION     
            "The percentage over the configured allowed resources for an IP trunk group that
             HPC calls can consume before being queued. This can be overriden by the
             HPC setting of the trunk group."
    DEFVAL          { 10 }
    ::= { sonusHpcTgProfileEntry 8 }

sonusHpcTgProfileTimeout OBJECT-TYPE
    SYNTAX          Gauge (1..90)
    ACCESS          read-write
    STATUS          mandatory
    DESCRIPTION     
            "The maximum time (seconds) an HPC call can be queued before the attempt to
             connect a call on the trunk group associated with this profile is abandoned."
    DEFVAL          { 15 }
    ::= { sonusHpcTgProfileEntry 9 }

sonusHpcTgProfileRowStatus OBJECT-TYPE
    SYNTAX          RowStatus
    ACCESS          read-write
    STATUS          mandatory
    DESCRIPTION     
            "This is for SNMP use."
    ::= { sonusHpcTgProfileEntry 10 }

sonusHpcTgProfileUsePrecedence OBJECT-TYPE
    SYNTAX          SonusAdminState
    ACCESS          read-write
    STATUS          mandatory
    DESCRIPTION     
            "This enables and disables using precedence(MLPP/WPS) from ingress 
             side to be sent on egress side."
    DEFVAL          { disabled }
    ::= { sonusHpcTgProfileEntry 11 }

sonusHpcLimitObjects OBJECT IDENTIFIER
    ::= { sonusTrunkGroupResourcesMIBObjects 11 }

sonusHpcLimitNextIndex OBJECT-TYPE
    SYNTAX          Gauge
    ACCESS          read-only
    STATUS          mandatory
    DESCRIPTION     
            "The next valid index to use when creating a new sonusHpcLimitEntry."
    ::= { sonusHpcLimitObjects 1 }

sonusHpcLimitTable OBJECT-TYPE
    SYNTAX          SEQUENCE OF SonusHpcLimitEntry
    ACCESS          not-accessible
    STATUS          mandatory
    DESCRIPTION     
            "A list of HPC Limit entries."
    ::= { sonusHpcLimitObjects 2 }

sonusHpcLimitEntry OBJECT-TYPE
    SYNTAX          SonusHpcLimitEntry
    ACCESS          not-accessible
    STATUS          mandatory
    DESCRIPTION     
            "A HPC Limit admin entry."
    INDEX           { sonusHpcLimitIndex }
    ::= { sonusHpcLimitTable 1 }

SonusHpcLimitEntry ::=
    SEQUENCE {
        sonusHpcLimitIndex              Gauge,
        sonusHpcLimitName               SonusName,
        sonusHpcLimitSignalingZoneName  SonusNameReference,
        sonusHpcLimitSignalingIpAddress IpAddress,
        sonusHpcLimitMaxIngressCallRate Gauge,
        sonusHpcLimitMaxSimultaneousCalls Gauge,
        sonusHpcLimitState              SonusAdminState,
        sonusHpcLimitRowStatus          RowStatus,
        sonusHpcLimitSignalingIp6Address Ipv6Address,
        sonusHpcLimitSignalingIpVersion INTEGER
    }

sonusHpcLimitIndex OBJECT-TYPE
    SYNTAX          Gauge
    ACCESS          read-only
    STATUS          mandatory
    DESCRIPTION     
            "Index of this Hpc Limit table entry."
    ::= { sonusHpcLimitEntry 1 }

sonusHpcLimitName OBJECT-TYPE
    SYNTAX          SonusName
    ACCESS          read-write
    STATUS          mandatory
    DESCRIPTION     
            "The name used in CLI to reference the HPC limit entry."
    ::= { sonusHpcLimitEntry 2 }

sonusHpcLimitSignalingZoneName OBJECT-TYPE
    SYNTAX          SonusNameReference
    ACCESS          read-write
    STATUS          mandatory
    DESCRIPTION     
            "The signaling zone that contains a SIP peer subject to limits on HPC calls."
    DEFVAL          { "INTERNAL" }
    ::= { sonusHpcLimitEntry 3 }

sonusHpcLimitSignalingIpAddress OBJECT-TYPE
    SYNTAX          IpAddress
    ACCESS          read-write
    STATUS          mandatory
    DESCRIPTION     
            "The IP address of a SIP peer subject to limits on HPC calls."
    ::= { sonusHpcLimitEntry 4 }

sonusHpcLimitMaxIngressCallRate OBJECT-TYPE
    SYNTAX          Gauge (0..2000)
    ACCESS          read-write
    STATUS          mandatory
    DESCRIPTION     
            "The number of ingress HPC call attempts per minute allowed from the 
             subject SIP peers.  This includes calls promoted to HPC status based 
             on the number dialed.  The rate is monitored by a token bucket algorithm 
             that tolerates bursts equal to the limit.  The maximum is enforced by 
             denying call attempts that exceed the limit.  An alarm is raised when the 
             configured limit is exceeded, indicating the number of calls denied 
             in this interval. At  the next interval, if any HPC calls were denied, the 
             alarm is repeated, containing the number of calls denied during 
             the interval. The value 0 denies all HPC calls from the subject SIP peers."
    DEFVAL          { 10 }
    ::= { sonusHpcLimitEntry 5 }

sonusHpcLimitMaxSimultaneousCalls OBJECT-TYPE
    SYNTAX          Gauge (0..20000)
    ACCESS          read-write
    STATUS          mandatory
    DESCRIPTION     
            "The total number of active plus stable HPC calls allowed from or to the subject 
             SIP peers. This includes calls promoted to HPC status based on the number dialed.
             The maximum is enforced by denying new call attempts that exceed the limit.  
             Existing calls persist even if the limit is lowered.  An alarm is raised when 
             the configured limit is exceeded, indicating the number of calls denied in 
             this interval. At  the next interval, if any HPC calls were denied, the alarm 
             is repeated, containing the number of calls denied during the interval. 
             The value 0 denies all HPC calls from or to the subject SIP peers."
    DEFVAL          { 10 }
    ::= { sonusHpcLimitEntry 6 }

sonusHpcLimitState OBJECT-TYPE
    SYNTAX          SonusAdminState
    ACCESS          read-write
    STATUS          mandatory
    DESCRIPTION     
            "This enables and disables the HPC Limit entry. Call limit statistics are 
             reset while the limit is disabled."
    DEFVAL          { disabled }
    ::= { sonusHpcLimitEntry 7 }

sonusHpcLimitRowStatus OBJECT-TYPE
    SYNTAX          RowStatus
    ACCESS          read-write
    STATUS          mandatory
    DESCRIPTION     
            "This is for SNMP use."
    ::= { sonusHpcLimitEntry 8 }

sonusHpcLimitSignalingIp6Address OBJECT-TYPE
    SYNTAX          Ipv6Address
    ACCESS          read-write
    STATUS          mandatory
    DESCRIPTION     
            "The IPv6 address of a SIP peer subject to limits on HPC calls."
    ::= { sonusHpcLimitEntry 9 }

sonusHpcLimitSignalingIpVersion OBJECT-TYPE
    SYNTAX          INTEGER { afInet(2), afInet6(24) }
    ACCESS          read-only
    STATUS          mandatory
    DESCRIPTION     
            "The IP address type of a SIP peer ."
    ::= { sonusHpcLimitEntry 10 }

sonusHpcLimitStatObjects OBJECT IDENTIFIER
    ::= { sonusTrunkGroupResourcesMIBObjects 12 }

sonusHpcLimitStatTable OBJECT-TYPE
    SYNTAX          SEQUENCE OF SonusHpcLimitStatEntry
    ACCESS          not-accessible
    STATUS          mandatory
    DESCRIPTION     
            "Call statistics for SIP signaling peers subject to HPC limits.
             Total call attempt counts increment beginning at zero while a 
             limit is enabled."
    ::= { sonusHpcLimitStatObjects 1 }

sonusHpcLimitStatEntry OBJECT-TYPE
    SYNTAX          SonusHpcLimitStatEntry
    ACCESS          not-accessible
    STATUS          mandatory
    DESCRIPTION     
            "A HPC Limit status entry."
    INDEX           { sonusHpcLimitStatIndex }
    ::= { sonusHpcLimitStatTable 1 }

SonusHpcLimitStatEntry ::=
    SEQUENCE {
        sonusHpcLimitStatIndex          Gauge,
        sonusHpcLimitStatName           DisplayString,
        sonusHpcLimitStatTotalIngressHpcCallsAllowed            Gauge,
        sonusHpcLimitStatTotalIngressHpcCallsDeniedByRate                 Gauge,
        sonusHpcLimitStatTotalIngressHpcCallsDeniedByNumber                   Gauge,
        sonusHpcLimitStatCurrentIngressHpcCalls       Gauge,
        sonusHpcLimitStatTotalEgressHpcCallsAllowed           Gauge,
        sonusHpcLimitStatTotalEgressHpcCallsDeniedByNumber                  Gauge,
        sonusHpcLimitStatCurrentEgressHpcCalls      Gauge
    }

sonusHpcLimitStatIndex OBJECT-TYPE
    SYNTAX          Gauge
    ACCESS          read-only
    STATUS          mandatory
    DESCRIPTION     
            "Index of this Hpc Limit Status table entry."
    ::= { sonusHpcLimitStatEntry 1 }

sonusHpcLimitStatName OBJECT-TYPE
    SYNTAX          DisplayString (SIZE(0..23))
    ACCESS          read-only
    STATUS          mandatory
    DESCRIPTION     
            "The name of the corresponding sonusHpcLimitEntry."
    ::= { sonusHpcLimitStatEntry 2 }

sonusHpcLimitStatTotalIngressHpcCallsAllowed OBJECT-TYPE
    SYNTAX          Gauge
    ACCESS          read-only
    STATUS          mandatory
    DESCRIPTION     
            "The number of ingress HPC call attempts allowed under an HPC  limit."
    ::= { sonusHpcLimitStatEntry 3 }

sonusHpcLimitStatTotalIngressHpcCallsDeniedByRate OBJECT-TYPE
    SYNTAX          Gauge
    ACCESS          read-only
    STATUS          mandatory
    DESCRIPTION     
            "The number of ingress HPC call attempts denied because they exceeded 
             the rate allowed by an HPC limit."
    ::= { sonusHpcLimitStatEntry 4 }

sonusHpcLimitStatTotalIngressHpcCallsDeniedByNumber OBJECT-TYPE
    SYNTAX          Gauge
    ACCESS          read-only
    STATUS          mandatory
    DESCRIPTION     
            "The number of ingress HPC call attempts denied because they exceeded
             the number of simultaneous calls allowed by an HPC limit."
    ::= { sonusHpcLimitStatEntry 5 }

sonusHpcLimitStatCurrentIngressHpcCalls OBJECT-TYPE
    SYNTAX          Gauge
    ACCESS          read-only
    STATUS          mandatory
    DESCRIPTION     
            "The number of active plus stable ingress HPC calls from the SIP peers 
             subject to an HPC limit."
    ::= { sonusHpcLimitStatEntry 6 }

sonusHpcLimitStatTotalEgressHpcCallsAllowed OBJECT-TYPE
    SYNTAX          Gauge
    ACCESS          read-only
    STATUS          mandatory
    DESCRIPTION     
            "The number of egress HPC call attempts allowed under an HPC limit."
    ::= { sonusHpcLimitStatEntry 7 }

sonusHpcLimitStatTotalEgressHpcCallsDeniedByNumber OBJECT-TYPE
    SYNTAX          Gauge
    ACCESS          read-only
    STATUS          mandatory
    DESCRIPTION     
            "The number of egress HPC call attempts denied because they exceeded 
             the number of simultaneous calls allowed by an HPC limit."
    ::= { sonusHpcLimitStatEntry 8 }

sonusHpcLimitStatCurrentEgressHpcCalls OBJECT-TYPE
    SYNTAX          Gauge
    ACCESS          read-only
    STATUS          mandatory
    DESCRIPTION     
            "The number of active plus stable egress HPC calls to the SIP peers 
             subject to an HPC limit."
    ::= { sonusHpcLimitStatEntry 9 }

sonusMlppObjects OBJECT IDENTIFIER
    ::= { sonusTrunkGroupResourcesMIBObjects 13 }

sonusMlppTable OBJECT-TYPE
    SYNTAX          SEQUENCE OF SonusMlppEntry
    ACCESS          not-accessible
    STATUS          mandatory
    DESCRIPTION     
            "A list of MLPP shelf-wide admin entries."
    ::= { sonusMlppObjects 2 }

sonusMlppEntry OBJECT-TYPE
    SYNTAX          SonusMlppEntry
    ACCESS          not-accessible
    STATUS          mandatory
    DESCRIPTION     
            "An MLPP shelf-wide admin entry."
    INDEX           { sonusMlppShelfIndex }
    ::= { sonusMlppTable 1 }

SonusMlppEntry ::=
    SEQUENCE {
        sonusMlppShelfIndex             SonusShelfIndex,
        sonusMlppNetDomainDsnAdminState SonusAdminState,
        sonusMlppRowStatus              RowStatus
    }

sonusMlppShelfIndex OBJECT-TYPE
    SYNTAX          SonusShelfIndex
    ACCESS          not-accessible
    STATUS          mandatory
    DESCRIPTION     
            "Index of this table entry. This is equivalent to the GSX
             shelf index, i.e. one entry per GSX shelf."
    ::= { sonusMlppEntry 1 }

sonusMlppNetDomainDsnAdminState OBJECT-TYPE
    SYNTAX          SonusAdminState
    ACCESS          read-write
    STATUS          mandatory
    DESCRIPTION     
            "This enables an didsables the 'dsn' network domain."
    DEFVAL          { disabled }
    ::= { sonusMlppEntry 2 }

sonusMlppRowStatus OBJECT-TYPE
    SYNTAX          RowStatus
    ACCESS          read-write
    STATUS          mandatory
    DESCRIPTION     
            "This is for SNMP use."
    ::= { sonusMlppEntry 3 }

sonusMlppStatTable OBJECT-TYPE
    SYNTAX          SEQUENCE OF SonusMlppStatEntry
    ACCESS          not-accessible
    STATUS          mandatory
    DESCRIPTION     
            "Table of shelf-wide MLPP status."
    ::= { sonusMlppObjects 3 }

sonusMlppStatEntry OBJECT-TYPE
    SYNTAX          SonusMlppStatEntry
    ACCESS          not-accessible
    STATUS          mandatory
    DESCRIPTION     
            "Entry of shelf-wide MLPP status."
    INDEX           { sonusMlppStatShelfIndex }
    ::= { sonusMlppStatTable 1 }

SonusMlppStatEntry ::=
    SEQUENCE {
        sonusMlppStatShelfIndex         SonusShelfIndex,
        sonusMlppStatDsnPreemptedCallCount  Gauge
    }

sonusMlppStatShelfIndex OBJECT-TYPE
    SYNTAX          SonusShelfIndex
    ACCESS          read-only
    STATUS          mandatory
    DESCRIPTION     
            "GSX Shelf Index of this MLPP status."
    ::= { sonusMlppStatEntry 1 }

sonusMlppStatDsnPreemptedCallCount OBJECT-TYPE
    SYNTAX          Gauge
    ACCESS          read-only
    STATUS          mandatory
    DESCRIPTION     
            "Total number of preempted calls on the DSN network domain."
    ::= { sonusMlppStatEntry 2 }

sonusTgMlppProfObjects OBJECT IDENTIFIER
    ::= { sonusTrunkGroupResourcesMIBObjects 14 }

sonusMlppTgProfileNextIndex OBJECT-TYPE
    SYNTAX          Gauge
    ACCESS          not-accessible
    STATUS          mandatory
    DESCRIPTION     
            "The next valid index to use when creating a new sonusMlppTgProfileEntry"
    ::= { sonusTgMlppProfObjects 1 }

sonusMlppTgProfileTable OBJECT-TYPE
    SYNTAX          SEQUENCE OF SonusMlppTgProfileEntry
    ACCESS          not-accessible
    STATUS          mandatory
    DESCRIPTION     
            "A list of MLPP trunk group profiles."
    ::= { sonusTgMlppProfObjects 2 }

sonusMlppTgProfileEntry OBJECT-TYPE
    SYNTAX          SonusMlppTgProfileEntry
    ACCESS          not-accessible
    STATUS          mandatory
    DESCRIPTION     
            "An MLPP trunk group profile admin entry."
    INDEX           { sonusMlppTgProfileIndex }
    ::= { sonusMlppTgProfileTable 1 }

SonusMlppTgProfileEntry ::=
    SEQUENCE {
        sonusMlppTgProfileIndex         Gauge,
        sonusMlppTgProfileName          SonusName,
        sonusMlppTgProfilePreemptionState SonusAdminState,
        sonusMlppTgProfilePeerMlppSupport SonusAdminState,
        sonusMlppTgProfileRowStatus     RowStatus
    }

sonusMlppTgProfileIndex OBJECT-TYPE
    SYNTAX          Gauge
    ACCESS          not-accessible
    STATUS          mandatory
    DESCRIPTION     
            "Index of this table entry."
    ::= { sonusMlppTgProfileEntry 1 }

sonusMlppTgProfileName OBJECT-TYPE
    SYNTAX          SonusName
    ACCESS          read-write
    STATUS          mandatory
    DESCRIPTION     
            "The name of this MLPP trunk group Profile."
    ::= { sonusMlppTgProfileEntry 2 }

sonusMlppTgProfilePreemptionState OBJECT-TYPE
    SYNTAX          SonusAdminState
    ACCESS          read-write
    STATUS          mandatory
    DESCRIPTION     
            "This enables and disables preemption on each trunk group
             which is associated with this profile."
    DEFVAL          { disabled }
    ::= { sonusMlppTgProfileEntry 3 }

sonusMlppTgProfilePeerMlppSupport OBJECT-TYPE
    SYNTAX          SonusAdminState
    ACCESS          read-write
    STATUS          mandatory
    DESCRIPTION     
            "Indicates whether or not the far end supports MLPP.  When an
             MLPP call egresses to a network which does not support MLPP the
             GSX will play a Loss of C2 Features (LOC2) announcement towards
             the calling party."
    DEFVAL          { disabled }
    ::= { sonusMlppTgProfileEntry 4 }

sonusMlppTgProfileRowStatus OBJECT-TYPE
    SYNTAX          RowStatus
    ACCESS          read-write
    STATUS          mandatory
    DESCRIPTION     
            "This is for SNMP use."
    ::= { sonusMlppTgProfileEntry 5 }

sonusTrunkGroupResourcesMIBNotifications OBJECT IDENTIFIER
    ::= { sonusTrunkGroupResourcesMIB 2 }

sonusTrunkGroupResourcesMIBNotificationsPrefix OBJECT IDENTIFIER
    ::= { sonusTrunkGroupResourcesMIBNotifications 0 }

sonusTrunkGroupResourcesMIBNotificationsObjects OBJECT IDENTIFIER
    ::= { sonusTrunkGroupResourcesMIBNotifications 1 }

sonusTrunkOutOfServiceReason OBJECT-TYPE
    SYNTAX          INTEGER { configured(1), allResourcesBlocked(2) }
    ACCESS          read-only
    STATUS          mandatory
    DESCRIPTION     
            "The reason why the Trunk Group is out of service."
    ::= { sonusTrunkGroupResourcesMIBNotificationsObjects 1 }

sonusTrunkNumberOfCircuits OBJECT-TYPE
    SYNTAX          INTEGER
    ACCESS          read-only
    STATUS          mandatory
    DESCRIPTION     
            "sonusTrunkNumberOfCircuits indicates the number of
             circuits that have been added to or deleted from a
             trunk group."
    ::= { sonusTrunkGroupResourcesMIBNotificationsObjects 2 }

sonusTrunkGroupTCObject OBJECT-TYPE
    SYNTAX          INTEGER { sonusTgTCInboundReserved(1), 
                        sonusTgTCCirResvState(2), 
                        sonusTgTCPriorityCallReserve(3), 
                        sonusTgTCIncomingCallReserve(4), 
                        sonusTgTCOutgoingCallReserve(5), 
                        sonusTgTCSilcState(6), 
                        sonusTgTCSilcMC1Percent(7), 
                        sonusTgTCSilcMC2Percent(8) }
    ACCESS          read-only
    STATUS          mandatory
    DESCRIPTION     
            "This object is a bit mask that indicates what traffic
             control object in the trunk group table has changed."
    ::= { sonusTrunkGroupResourcesMIBNotificationsObjects 3 }

sonusTrunkGroupManCon OBJECT-TYPE
    SYNTAX          OCTET STRING
--                       { skip(0), cant(1), canf(2), irr(3), sirr(4), 
--                         orr(5), sorr(6) }
    ACCESS          read-only
    STATUS          mandatory
    DESCRIPTION     
            "This object is a bit mask that indicates what 
             manual trunk group controls were active in the
             last 30 seconds."
    ::= { sonusTrunkGroupResourcesMIBNotificationsObjects 4 }

sonusTrunkGroupAutoCon OBJECT-TYPE
    SYNTAX          OCTET STRING
--                       { acc(0), str(1), silc(2), dre(3), pod(4), 
--                         gwAcc(5), callPolicing(6), regPolicing(7) }
    ACCESS          read-only
    STATUS          mandatory
    DESCRIPTION     
            "This object is a bit mask that indicates what 
             automatic trunk group controls were active in 
             the last 30 seconds."
    ::= { sonusTrunkGroupResourcesMIBNotificationsObjects 5 }

sonusHpcLimitCallAttemptsDenied OBJECT-TYPE
    SYNTAX          Gauge
    ACCESS          read-only
    STATUS          mandatory
    DESCRIPTION     
            "The number of HPC call attempts that have been denied because of 
             exceeding the HPC limit associated with the trap since the last 
             instance of the trap"
    ::= { sonusTrunkGroupResourcesMIBNotificationsObjects 6 }

sonusTrunkEnabledNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group is now enabled."
    ::= 1

sonusTrunkDisabledNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group is now disabled."
    ::= 2

sonusTrunkInServiceNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group is now in service."
    ::= 3

sonusTrunkOutOfServiceNotification TRAP-TYPE
    ENTERPRISE      sonusTrunkGroupResourcesMIBNotifications
    VARIABLES       { sonusTgName, sonusTrunkOutOfServiceReason, 
                      sonusEventDescription, sonusEventClass, 
                      sonusEventLevel, sonusSequenceId, sonusEventTime, 
                      sonusTgAdditionalData }
--     STATUS          mandatory
    DESCRIPTION     
            "This trap indicates that a Trunk Group is out of service."
    ::= 4

sonusTrunkDeletedNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group is now deleted."
    ::= 5

sonusTrunkNameChangedNotification TRAP-TYPE
    ENTERPRISE      sonusTrunkGroupResourcesMIBNotifications
    VARIABLES       { sonusTgName, sonusTgAlternateName, 
                      sonusEventDescription, sonusEventClass, 
                      sonusEventLevel, sonusSequenceId, sonusEventTime, 
                      sonusTgAdditionalData }
--     STATUS          mandatory
    DESCRIPTION     
            "This trap indicates a Trunk Group name has changed.
             sonusTgName is the new trunk group name.  
             sonusTgAlternateName is the old trunk group name."
    ::= 6

sonusTrunkGroupAddedNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group has been added."
    ::= 7

sonusTrunkGroupCircuitsAddedNotification TRAP-TYPE
    ENTERPRISE      sonusTrunkGroupResourcesMIBNotifications
    VARIABLES       { sonusTgName, sonusShelfIndex, sonusSlotIndex, 
                      sonusPortIndex, sonusTrunkNumberOfCircuits, 
                      sonusEventDescription, sonusEventClass, 
                      sonusEventLevel, sonusSequenceId, sonusEventTime, 
                      sonusTgAdditionalData }
--     STATUS          mandatory
    DESCRIPTION     
            "This trap indicates that circuits have been added
             to a trunk group."
    ::= 8

sonusTrunkGroupCircuitsDeletedNotification TRAP-TYPE
    ENTERPRISE      sonusTrunkGroupResourcesMIBNotifications
    VARIABLES       { sonusTgName, sonusShelfIndex, sonusSlotIndex, 
                      sonusPortIndex, sonusTrunkNumberOfCircuits, 
                      sonusEventDescription, sonusEventClass, 
                      sonusEventLevel, sonusSequenceId, sonusEventTime, 
                      sonusTgAdditionalData }
--     STATUS          mandatory
    DESCRIPTION     
            "This trap indicates that circuits have been deleted
             from a trunk group."
    ::= 9

sonusTrunkGroupIllegalSFGNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates that a Simulated Facility Group was
             enabled on a trunk group with non-ISDN service groups."
    ::= 10

sonusTrunkGroupTrafficControlConfChanged TRAP-TYPE
    ENTERPRISE      sonusTrunkGroupResourcesMIBNotifications
    VARIABLES       { sonusTgName, sonusTrunkGroupTCObject, 
                      sonusEventDescription, sonusEventClass, 
                      sonusEventLevel, sonusSequenceId, sonusEventTime, 
                      sonusTgAdditionalData }
--     STATUS          mandatory
    DESCRIPTION     
            "This trap indicates that a traffic control
             configuration object in 
             the trunk group table has changed.  The 
             sonusTrunkGroupTCObject parameter indicates what 
             object or objects have changed."
    ::= 11

sonusTrunkGroupManualControlActive TRAP-TYPE
    ENTERPRISE      sonusTrunkGroupResourcesMIBNotifications
    VARIABLES       { sonusTgName, sonusTrunkGroupManCon, 
                      sonusEventDescription, sonusEventClass, 
                      sonusEventLevel, sonusSequenceId, sonusEventTime, 
                      sonusTgAdditionalData }
--     STATUS          mandatory
    DESCRIPTION     
            "This trap indicates that a manual traffic control 
             was active within the last 30 seconds.  The 
             sonusTrunkGroupManualControl parameter indicates what 
             manual control was active."
    ::= 12

sonusTrunkGroupAutomaticControlActive TRAP-TYPE
    ENTERPRISE      sonusTrunkGroupResourcesMIBNotifications
    VARIABLES       { sonusTgName, sonusTrunkGroupAutoCon, 
                      sonusEventDescription, sonusEventClass, 
                      sonusEventLevel, sonusSequenceId, sonusEventTime, 
                      sonusTgAdditionalData }
--     STATUS          mandatory
    DESCRIPTION     
            "This trap indicates that an automatic traffic control 
             was active within the last 30 seconds.  The 
             sonusTrunkGroupAutomaticControl parameter indicates 
             what automatic control was active."
    ::= 13

sonusTrunkGroupOutOfResourcesNotification TRAP-TYPE
    ENTERPRISE      sonusTrunkGroupResourcesMIBNotifications
    VARIABLES       { sonusTgName, sonusEventDescription, 
                      sonusEventClass, sonusEventLevel, sonusSequenceId, 
                      sonusEventTime, sonusTgAdditionalData }
--     STATUS          mandatory
    DESCRIPTION     
            "This trap indicates a Trunk Group is out of resources."
    ::= 14

sonusHpcLimitHighIngressCallRateNotification TRAP-TYPE
    ENTERPRISE      sonusTrunkGroupResourcesMIBNotifications
    VARIABLES       { sonusHpcLimitName, sonusHpcLimitCallAttemptsDenied, 
                      sonusEventDescription, sonusEventClass, 
                      sonusEventLevel, sonusSequenceId, sonusEventTime }
--     STATUS          mandatory
    DESCRIPTION     
            "This trap indicates that one or more ingress HPC call attempts were 
             denied because they exceeded the high threshold rate allowed by an 
             HPC limit."
    ::= 15

sonusHpcLimitHighSimultaneousCallsNotification TRAP-TYPE
    ENTERPRISE      sonusTrunkGroupResourcesMIBNotifications
    VARIABLES       { sonusHpcLimitName, sonusHpcLimitCallAttemptsDenied, 
                      sonusEventDescription, sonusEventClass, 
                      sonusEventLevel, sonusSequenceId, sonusEventTime }
--     STATUS          mandatory
    DESCRIPTION     
            "This trap indicates that one or more HPC call attempts were denied 
             because they exceeded the number of simultaneous calls allowed by 
             an HPC limit."
    ::= 16

END -- end of module SONUS-TRUNK-GROUP-RESOURCES-MIB.
