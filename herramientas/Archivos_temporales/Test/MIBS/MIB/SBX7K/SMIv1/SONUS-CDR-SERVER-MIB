--
-- This SMIv1 module has been generated by smidump 0.2-cvs. Do not edit.
--

SONUS-CDR-SERVER-MIB DEFINITIONS ::= BEGIN

IMPORTS
    OBJECT-TYPE
        FROM RFC-1212
    Counter, Gauge, IpAddress
        FROM RFC1155-SMI
    RowStatus
        FROM SNMPv2-TC
    sonusCommonSoftwarePlatformServicesMIBs
        FROM SONUS-SMI;

sonusCdrServerMIB OBJECT IDENTIFIER
    ::= { sonusCommonSoftwarePlatformServicesMIBs 17 }

-- sonusCdrServerMIB MODULE-IDENTITY
--     LAST-UPDATED    "201212310000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "Configuration for external CDR servers."
--     REVISION        "201212310000Z"
--     DESCRIPTION     
--             "Auto generated MIB."
--     ::= { sonusCommonSoftwarePlatformServicesMIBs 17 }


UnsignedShort ::=
    Gauge (0..65535)

-- UnsignedShort ::= TEXTUAL-CONVENTION
--     DISPLAY-HINT    "d"
--     STATUS          mandatory
--     DESCRIPTION     
--             "xs:unsignedShort"
--     SYNTAX          Gauge (0..65535)

ConfdString ::=
    OCTET STRING

-- ConfdString ::= TEXTUAL-CONVENTION
--     DISPLAY-HINT    "1t"
--     STATUS          mandatory
--     DESCRIPTION     
--             "xs: and confd: types mapped to strings"
--     SYNTAX          OCTET STRING

InetAddressIP ::=
    OCTET STRING (SIZE(4 | 16))

-- InetAddressIP ::= TEXTUAL-CONVENTION
--     STATUS          mandatory
--     DESCRIPTION     
--             "confd:inetAddressIP"
--     SYNTAX          OCTET STRING (SIZE(4 | 16))

String ::=
    OCTET STRING

-- String ::= TEXTUAL-CONVENTION
--     DISPLAY-HINT    "1t"
--     STATUS          mandatory
--     DESCRIPTION     
--             "xs:string"
--     SYNTAX          OCTET STRING

SonusCdrServerTypeXferState ::=
    INTEGER { idle(0), started(1), connecting(2), transferring(3), 
                        failed(4), done(5) }

-- SonusCdrServerTypeXferState ::= TEXTUAL-CONVENTION
--     STATUS          mandatory
--     DESCRIPTION     
--             "
--              Server state
--              "
--     SYNTAX          INTEGER
--                       { idle(0), started(1), connecting(2), 
--                         transferring(3), failed(4), done(5) }

SonusAccountingOutOfServiceReason ::=
    INTEGER { configchange(1), eventloggingerror(2) }

-- SonusAccountingOutOfServiceReason ::= TEXTUAL-CONVENTION
--     STATUS          mandatory
--     DESCRIPTION     
--             "
--              The reason why Sonus Acccounting is out of Service
--              "
--     SYNTAX          INTEGER
--                       { configchange(1), eventloggingerror(2) }

SonusCdrServerConnectionTimeoutType ::=
    INTEGER (15..120)

-- SonusCdrServerConnectionTimeoutType ::= TEXTUAL-CONVENTION
--     STATUS          mandatory
--     DESCRIPTION     
--             "
--              Enter a value between in the range (15..120)
--              "
--     SYNTAX          INTEGER (15..120)

SonusCdrServerTypePasswdStr ::=
    OCTET STRING

-- SonusCdrServerTypePasswdStr ::= TEXTUAL-CONVENTION
--     DISPLAY-HINT    "1t"
--     STATUS          mandatory
--     DESCRIPTION     
--             "
--              Enter encrypted string password data
--              "
--     SYNTAX          OCTET STRING

SonusCdrServerPublicKey ::=
    OCTET STRING (SIZE(0..2048))

-- SonusCdrServerPublicKey ::= TEXTUAL-CONVENTION
--     DISPLAY-HINT    "1t"
--     STATUS          mandatory
--     DESCRIPTION     
--             "
--              Enter public key of CDR server
--              "
--     SYNTAX          OCTET STRING (SIZE(0..2048))

SonusCdrServerTypeState ::=
    INTEGER { active(1), standby(2) }

-- SonusCdrServerTypeState ::= TEXTUAL-CONVENTION
--     STATUS          mandatory
--     DESCRIPTION     
--             "
--              Server state
--              "
--     SYNTAX          INTEGER
--                       { active(1), standby(2) }

SonusCdrServerBufferSizeType ::=
    INTEGER (4..1024)

-- SonusCdrServerBufferSizeType ::= TEXTUAL-CONVENTION
--     STATUS          mandatory
--     DESCRIPTION     
--             "
--              Enter a value between in the range (4..1024)
--              "
--     SYNTAX          INTEGER (4..1024)

SonusCdrServerTypeName ::=
    OCTET STRING (SIZE(0..255))

-- SonusCdrServerTypeName ::= TEXTUAL-CONVENTION
--     DISPLAY-HINT    "1t"
--     STATUS          mandatory
--     DESCRIPTION     
--             "
--              Enter string character data
--              "
--     SYNTAX          OCTET STRING (SIZE(0..255))

SonusCdrServerTimeoutType ::=
    INTEGER (15..600)

-- SonusCdrServerTimeoutType ::= TEXTUAL-CONVENTION
--     STATUS          mandatory
--     DESCRIPTION     
--             "
--              Enter a value between in the range (15..600)
--              "
--     SYNTAX          INTEGER (15..600)

SonusCdrServerTypeType ::=
    INTEGER { primary(1), secondary(2) }

-- SonusCdrServerTypeType ::= TEXTUAL-CONVENTION
--     STATUS          mandatory
--     DESCRIPTION     
--             "
--              One of primary or secondary
--              "
--     SYNTAX          INTEGER
--                       { primary(1), secondary(2) }

sonusCdrServer OBJECT IDENTIFIER
    ::= { sonusCdrServerMIB 1 }

sonusCdrServerAdminTable OBJECT-TYPE
    SYNTAX          SEQUENCE OF SonusCdrServerAdminEntry
    ACCESS          not-accessible
    STATUS          obsolete
    DESCRIPTION     
            "
             CDR server admin
             "
    ::= { sonusCdrServer 1 }

sonusCdrServerAdminEntry OBJECT-TYPE
    SYNTAX          SonusCdrServerAdminEntry
    ACCESS          not-accessible
    STATUS          obsolete
    DESCRIPTION     
            ""
    INDEX           { sonusCdrServerAdminType }
    ::= { sonusCdrServerAdminTable 1 }

SonusCdrServerAdminEntry ::=
    SEQUENCE {
        sonusCdrServerAdminType         SonusCdrServerTypeType,
        sonusCdrServerAdminIpAddress    InetAddressIP,
        sonusCdrServerAdminUsername     SonusCdrServerTypeName,
        sonusCdrServerAdminPassword     SonusCdrServerTypePasswdStr,
        sonusCdrServerAdminPath         SonusCdrServerTypeName,
        sonusCdrServerAdminFilePrefix   SonusCdrServerTypeName,
        sonusCdrServerAdminConnectionTimeout    SonusCdrServerConnectionTimeoutType,
        sonusCdrServerAdminTransferTimeout  SonusCdrServerTimeoutType,
        sonusCdrServerAdminRowstatus    RowStatus,
        sonusCdrServerAdminBufferSize   SonusCdrServerBufferSizeType,
        sonusCdrServerAdminCdrPort      UnsignedShort,
        sonusCdrServerAdminUseSshKeyFile INTEGER,
        sonusCdrServerAdminUseFilePostfix INTEGER
    }

sonusCdrServerAdminType OBJECT-TYPE
    SYNTAX          SonusCdrServerTypeType
    ACCESS          not-accessible
    STATUS          obsolete
    DESCRIPTION     
            "
             Server type - either primary of secondary.
             "
    ::= { sonusCdrServerAdminEntry 1 }

sonusCdrServerAdminIpAddress OBJECT-TYPE
    SYNTAX          InetAddressIP
    ACCESS          read-write
    STATUS          obsolete
    DESCRIPTION     
            "
             The IP address of the server
             "
    ::= { sonusCdrServerAdminEntry 2 }

sonusCdrServerAdminUsername OBJECT-TYPE
    SYNTAX          SonusCdrServerTypeName
    ACCESS          read-write
    STATUS          obsolete
    DESCRIPTION     
            "
             The username on the remote server
             "
    ::= { sonusCdrServerAdminEntry 3 }

sonusCdrServerAdminPassword OBJECT-TYPE
    SYNTAX          SonusCdrServerTypePasswdStr
    ACCESS          read-write
    STATUS          obsolete
    DESCRIPTION     
            "
             The password on the remote server
             "
    ::= { sonusCdrServerAdminEntry 4 }

sonusCdrServerAdminPath OBJECT-TYPE
    SYNTAX          SonusCdrServerTypeName
    ACCESS          read-write
    STATUS          obsolete
    DESCRIPTION     
            "
             The path on the remote server
             "
    ::= { sonusCdrServerAdminEntry 5 }

sonusCdrServerAdminFilePrefix OBJECT-TYPE
    SYNTAX          SonusCdrServerTypeName
    ACCESS          read-write
    STATUS          obsolete
    DESCRIPTION     
            "
             The remote file prefix that will be appended with a datestamp
             "
    ::= { sonusCdrServerAdminEntry 6 }

sonusCdrServerAdminConnectionTimeout OBJECT-TYPE
    SYNTAX          SonusCdrServerConnectionTimeoutType
    ACCESS          read-write
    STATUS          obsolete
    DESCRIPTION     
            "
             The time to wait before timing out the connect operation
             "
    DEFVAL          { 30 }
    ::= { sonusCdrServerAdminEntry 7 }

sonusCdrServerAdminTransferTimeout OBJECT-TYPE
    SYNTAX          SonusCdrServerTimeoutType
    ACCESS          read-write
    STATUS          obsolete
    DESCRIPTION     
            "
             The time to wait before timing out the file transfer
             "
    DEFVAL          { 120 }
    ::= { sonusCdrServerAdminEntry 8 }

sonusCdrServerAdminRowstatus OBJECT-TYPE
    SYNTAX          RowStatus
    ACCESS          read-write
    STATUS          obsolete
    DESCRIPTION     
            ""
    ::= { sonusCdrServerAdminEntry 9 }

sonusCdrServerAdminBufferSize OBJECT-TYPE
    SYNTAX          SonusCdrServerBufferSizeType
    ACCESS          read-write
    STATUS          obsolete
    DESCRIPTION     
            "
             The size of data to send to sftp server. Some servers may not handle large sizes.
             "
    DEFVAL          { 1024 }
    ::= { sonusCdrServerAdminEntry 10 }

sonusCdrServerAdminCdrPort OBJECT-TYPE
    SYNTAX          UnsignedShort (1..65535)
    ACCESS          read-write
    STATUS          obsolete
    DESCRIPTION     
            "
             The ssh port of the remote server.
             "
    ::= { sonusCdrServerAdminEntry 11 }

sonusCdrServerAdminUseSshKeyFile OBJECT-TYPE
    SYNTAX          INTEGER { disable(0), enable(1) }
    ACCESS          read-write
    STATUS          obsolete
    DESCRIPTION     
            "
             use ssh public key for authentication on the remote server.
             "
    ::= { sonusCdrServerAdminEntry 12 }

sonusCdrServerAdminUseFilePostfix OBJECT-TYPE
    SYNTAX          INTEGER { disable(0), enable(1) }
    ACCESS          read-write
    STATUS          obsolete
    DESCRIPTION     
            "
             Use a temporary file with an extension specified by filePostFix when copying to the server
             "
    ::= { sonusCdrServerAdminEntry 13 }

sonusCdrServerStatusTable OBJECT-TYPE
    SYNTAX          SEQUENCE OF SonusCdrServerStatusEntry
    ACCESS          not-accessible
    STATUS          mandatory
    DESCRIPTION     
            "
             CDR server status
             "
    ::= { sonusCdrServer 2 }

sonusCdrServerStatusEntry OBJECT-TYPE
    SYNTAX          SonusCdrServerStatusEntry
    ACCESS          not-accessible
    STATUS          mandatory
    DESCRIPTION     
            ""
    INDEX           { sonusCdrServerStatusType }
    ::= { sonusCdrServerStatusTable 1 }

SonusCdrServerStatusEntry ::=
    SEQUENCE {
        sonusCdrServerStatusType        SonusCdrServerTypeType,
        sonusCdrServerStatusState       SonusCdrServerTypeState,
        sonusCdrServerStatusProgress    SonusCdrServerTypeXferState,
        sonusCdrServerStatusSuccessfulTransfers       Counter,
        sonusCdrServerStatusFailedTransfers   Counter,
        sonusCdrServerStatusPendingTransfers    Counter
    }

sonusCdrServerStatusType OBJECT-TYPE
    SYNTAX          SonusCdrServerTypeType
    ACCESS          not-accessible
    STATUS          mandatory
    DESCRIPTION     
            "
             Server type - either primary of secondary.
             "
    ::= { sonusCdrServerStatusEntry 1 }

sonusCdrServerStatusState OBJECT-TYPE
    SYNTAX          SonusCdrServerTypeState
    ACCESS          read-only
    STATUS          mandatory
    DESCRIPTION     
            "
             The type of the event log.  Each type has separate
             configuration parameters and logs to a separate file.
             "
    ::= { sonusCdrServerStatusEntry 2 }

sonusCdrServerStatusProgress OBJECT-TYPE
    SYNTAX          SonusCdrServerTypeXferState
    ACCESS          read-only
    STATUS          mandatory
    DESCRIPTION     
            "
             Indicator that a transfer is in progress.
             "
    ::= { sonusCdrServerStatusEntry 3 }

sonusCdrServerStatusSuccessfulTransfers OBJECT-TYPE
    SYNTAX          Counter
    ACCESS          read-only
    STATUS          mandatory
    DESCRIPTION     
            "
             Count of the number of files successfully transferred.
             "
    ::= { sonusCdrServerStatusEntry 4 }

sonusCdrServerStatusFailedTransfers OBJECT-TYPE
    SYNTAX          Counter
    ACCESS          read-only
    STATUS          mandatory
    DESCRIPTION     
            "
             Count of the number of failed transfers.
             "
    ::= { sonusCdrServerStatusEntry 5 }

sonusCdrServerStatusPendingTransfers OBJECT-TYPE
    SYNTAX          Counter
    ACCESS          read-only
    STATUS          mandatory
    DESCRIPTION     
            "
             Count the nmber of pending transfers.
             "
    ::= { sonusCdrServerStatusEntry 6 }

END -- end of module SONUS-CDR-SERVER-MIB.
