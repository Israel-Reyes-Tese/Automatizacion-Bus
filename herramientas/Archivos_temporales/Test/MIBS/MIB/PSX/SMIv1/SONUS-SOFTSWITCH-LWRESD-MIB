--
-- This SMIv1 module has been generated by smidump 0.2-cvs. Do not edit.
--

SONUS-SOFTSWITCH-LWRESD-MIB DEFINITIONS ::= BEGIN

IMPORTS
    InetAddress, InetAddressType
        FROM INET-ADDRESS-MIB
    OBJECT-TYPE
        FROM RFC-1212
    TRAP-TYPE
        FROM RFC-1215
    Counter, Gauge
        FROM RFC1155-SMI
    sonusEventClass, sonusEventDescription, sonusEventLevel, 
    sonusEventTime
        FROM SONUS-COMMON-MIB
    sonusServicesMIBs
        FROM SONUS-SMI
    SonusSoftSwitchDomainName, SonusSoftSwitchDomainNameLength
        FROM SONUS-SOFTSWITCH-TC;

sonusSoftSwitchLwresdMIB OBJECT IDENTIFIER
    ::= { sonusServicesMIBs 33 }

-- sonusSoftSwitchLwresdMIB MODULE-IDENTITY
--     LAST-UPDATED    "201107010000Z"
--     ORGANIZATION    
--             "Sonus Networks, Inc."
--     CONTACT-INFO    
--             "   Customer Support    
--              Sonus Networks, Inc.
--              7 Tech Park Dr
--              Westford, MA 01886
--              USA
--              
--              Tel: 978-614-8100
--              Fax: 978-614-8609"
--     DESCRIPTION     
--             "The MIB Module for SoftSwitch Lwresd Management."
--     ::= { sonusServicesMIBs 33 }


sonusSoftSwitchLwresdMIBObjects OBJECT IDENTIFIER
    ::= { sonusSoftSwitchLwresdMIB 1 }

sonusSoftSwitchLwresdMIBNotifications OBJECT IDENTIFIER
    ::= { sonusSoftSwitchLwresdMIB 2 }

sonusSoftSwitchLwresdMIBNotificationsPrefix OBJECT IDENTIFIER
    ::= { sonusSoftSwitchLwresdMIBNotifications 0 }

sonusSoftSwitchLwresdStatistics OBJECT IDENTIFIER
    ::= { sonusSoftSwitchLwresdMIB 3 }

sonusSoftSwitchLwresdServerCounters OBJECT IDENTIFIER
    ::= { sonusSoftSwitchLwresdStatistics 1 }

sonusSoftSwitchLwresdCountersServerTable OBJECT-TYPE
    SYNTAX          SEQUENCE OF SonusSoftSwitchLwresdCountersServerEntry
    ACCESS          not-accessible
    STATUS          mandatory
    DESCRIPTION     
            "Server Table to hold ENUM/DNS server counters."
    ::= { sonusSoftSwitchLwresdServerCounters 1 }

sonusSoftSwitchLwresdCountersServerEntry OBJECT-TYPE
    SYNTAX          SonusSoftSwitchLwresdCountersServerEntry
    ACCESS          not-accessible
    STATUS          mandatory
    DESCRIPTION     
            "An entry in the ENUM/DNS Server Table."
    INDEX           { sonusSoftSwitchLwresdCountersServerIpAddressType, 
                      sonusSoftSwitchLwresdCountersServerIpAddress, 
                      sonusSoftSwitchLwresdCountersServerPort, 
                      sonusSoftSwitchLwresdCountersServerTransportType }
    ::= { sonusSoftSwitchLwresdCountersServerTable 1 }

SonusSoftSwitchLwresdCountersServerEntry ::=
    SEQUENCE {
        sonusSoftSwitchLwresdCountersServerIpAddressType                InetAddressType,
        sonusSoftSwitchLwresdCountersServerIpAddress            InetAddress,
        sonusSoftSwitchLwresdCountersServerPort       INTEGER,
        sonusSoftSwitchLwresdCountersServerTransportType                INTEGER,
        sonusSoftSwitchLwresdCountersServerNAPTRReq           Counter,
        sonusSoftSwitchLwresdCountersServerNAPTRRsp           Counter,
        sonusSoftSwitchLwresdCountersServerNAPTRNoAnsRsp                Counter,
        sonusSoftSwitchLwresdCountersServerNAPTRTimeout               Counter,
        sonusSoftSwitchLwresdCountersServerNAPTRDestUnreachable                       Counter,
        sonusSoftSwitchLwresdCountersServerSRVReq         Counter,
        sonusSoftSwitchLwresdCountersServerSRVRsp         Counter,
        sonusSoftSwitchLwresdCountersServerSRVNoAnsRsp              Counter,
        sonusSoftSwitchLwresdCountersServerSRVTimeout             Counter,
        sonusSoftSwitchLwresdCountersServerSRVDestUnreachable                     Counter,
        sonusSoftSwitchLwresdCountersServerAReq       Counter,
        sonusSoftSwitchLwresdCountersServerARsp       Counter,
        sonusSoftSwitchLwresdCountersServerANoAnsRsp            Counter,
        sonusSoftSwitchLwresdCountersServerATimeout           Counter,
        sonusSoftSwitchLwresdCountersServerADestUnreachable                   Counter,
        sonusSoftSwitchLwresdCountersServerAAAAReq          Counter,
        sonusSoftSwitchLwresdCountersServerAAAARsp          Counter,
        sonusSoftSwitchLwresdCountersServerAAAANoAnsRsp               Counter,
        sonusSoftSwitchLwresdCountersServerAAAATimeout              Counter,
        sonusSoftSwitchLwresdCountersServerAAAADestUnreachable                      Counter,
        sonusSoftSwitchLwresdCountersServerTCPConnectionAttempt                       Counter,
        sonusSoftSwitchLwresdCountersServerTCPConnectionEstablished                           Counter,
        sonusSoftSwitchLwresdCountersServerTCPConnectionFailed                      Counter
    }

sonusSoftSwitchLwresdCountersServerIpAddressType OBJECT-TYPE
    SYNTAX          InetAddressType
    ACCESS          read-only
    STATUS          mandatory
    DESCRIPTION     
            "The ENUM/DNS Server IP address Type."
    ::= { sonusSoftSwitchLwresdCountersServerEntry 1 }

sonusSoftSwitchLwresdCountersServerIpAddress OBJECT-TYPE
    SYNTAX          InetAddress
    ACCESS          read-only
    STATUS          mandatory
    DESCRIPTION     
            "The ENUM/DNS Server IP address."
    ::= { sonusSoftSwitchLwresdCountersServerEntry 2 }

sonusSoftSwitchLwresdCountersServerPort OBJECT-TYPE
    SYNTAX          INTEGER
    ACCESS          read-only
    STATUS          mandatory
    DESCRIPTION     
            "The Port on which the ENUM/DNS server is listening."
    ::= { sonusSoftSwitchLwresdCountersServerEntry 3 }

sonusSoftSwitchLwresdCountersServerTransportType OBJECT-TYPE
    SYNTAX          INTEGER
    ACCESS          read-only
    STATUS          mandatory
    DESCRIPTION     
            "The transport type used towards the ENUM/DNS Server.1-tcp, 2-udp, 3-tcp fallback"
    ::= { sonusSoftSwitchLwresdCountersServerEntry 4 }

sonusSoftSwitchLwresdCountersServerNAPTRReq OBJECT-TYPE
    SYNTAX          Counter
    ACCESS          read-only
    STATUS          mandatory
    DESCRIPTION     
            "Number of NAPTR requests sent to the server."
    ::= { sonusSoftSwitchLwresdCountersServerEntry 5 }

sonusSoftSwitchLwresdCountersServerNAPTRRsp OBJECT-TYPE
    SYNTAX          Counter
    ACCESS          read-only
    STATUS          mandatory
    DESCRIPTION     
            "Number of NAPTR responses received from the Server."
    ::= { sonusSoftSwitchLwresdCountersServerEntry 6 }

sonusSoftSwitchLwresdCountersServerNAPTRNoAnsRsp OBJECT-TYPE
    SYNTAX          Counter
    ACCESS          read-only
    STATUS          mandatory
    DESCRIPTION     
            "Number of NAPTR no answer responses received from the  Server."
    ::= { sonusSoftSwitchLwresdCountersServerEntry 7 }

sonusSoftSwitchLwresdCountersServerNAPTRTimeout OBJECT-TYPE
    SYNTAX          Counter
    ACCESS          read-only
    STATUS          mandatory
    DESCRIPTION     
            "Number of NAPTR requests timed out for the Server."
    ::= { sonusSoftSwitchLwresdCountersServerEntry 8 }

sonusSoftSwitchLwresdCountersServerNAPTRDestUnreachable OBJECT-TYPE
    SYNTAX          Counter
    ACCESS          read-only
    STATUS          mandatory
    DESCRIPTION     
            "Number of NAPTR requests failed due to destination unreachable for the Server."
    ::= { sonusSoftSwitchLwresdCountersServerEntry 9 }

sonusSoftSwitchLwresdCountersServerSRVReq OBJECT-TYPE
    SYNTAX          Counter
    ACCESS          read-only
    STATUS          mandatory
    DESCRIPTION     
            "Number of SRV requests sent to the Server."
    ::= { sonusSoftSwitchLwresdCountersServerEntry 10 }

sonusSoftSwitchLwresdCountersServerSRVRsp OBJECT-TYPE
    SYNTAX          Counter
    ACCESS          read-only
    STATUS          mandatory
    DESCRIPTION     
            "Number of SRV responses received from the  Server."
    ::= { sonusSoftSwitchLwresdCountersServerEntry 11 }

sonusSoftSwitchLwresdCountersServerSRVNoAnsRsp OBJECT-TYPE
    SYNTAX          Counter
    ACCESS          read-only
    STATUS          mandatory
    DESCRIPTION     
            "Number of SRV no answer responses received from the Server."
    ::= { sonusSoftSwitchLwresdCountersServerEntry 12 }

sonusSoftSwitchLwresdCountersServerSRVTimeout OBJECT-TYPE
    SYNTAX          Counter
    ACCESS          read-only
    STATUS          mandatory
    DESCRIPTION     
            "Number of SRV requests timed out for the Server."
    ::= { sonusSoftSwitchLwresdCountersServerEntry 13 }

sonusSoftSwitchLwresdCountersServerSRVDestUnreachable OBJECT-TYPE
    SYNTAX          Counter
    ACCESS          read-only
    STATUS          mandatory
    DESCRIPTION     
            "Number of SRV requests failed due to destination unreachable for the Server."
    ::= { sonusSoftSwitchLwresdCountersServerEntry 14 }

sonusSoftSwitchLwresdCountersServerAReq OBJECT-TYPE
    SYNTAX          Counter
    ACCESS          read-only
    STATUS          mandatory
    DESCRIPTION     
            "Number of A requests sent to the Server."
    ::= { sonusSoftSwitchLwresdCountersServerEntry 15 }

sonusSoftSwitchLwresdCountersServerARsp OBJECT-TYPE
    SYNTAX          Counter
    ACCESS          read-only
    STATUS          mandatory
    DESCRIPTION     
            "Number of A responses received from the  Server."
    ::= { sonusSoftSwitchLwresdCountersServerEntry 16 }

sonusSoftSwitchLwresdCountersServerANoAnsRsp OBJECT-TYPE
    SYNTAX          Counter
    ACCESS          read-only
    STATUS          mandatory
    DESCRIPTION     
            "Number of A no answer responses received from the Server."
    ::= { sonusSoftSwitchLwresdCountersServerEntry 17 }

sonusSoftSwitchLwresdCountersServerATimeout OBJECT-TYPE
    SYNTAX          Counter
    ACCESS          read-only
    STATUS          mandatory
    DESCRIPTION     
            "Number of A requests timed out for the Server."
    ::= { sonusSoftSwitchLwresdCountersServerEntry 18 }

sonusSoftSwitchLwresdCountersServerADestUnreachable OBJECT-TYPE
    SYNTAX          Counter
    ACCESS          read-only
    STATUS          mandatory
    DESCRIPTION     
            "Number of A requests failed due to destination unreachable for the Server."
    ::= { sonusSoftSwitchLwresdCountersServerEntry 19 }

sonusSoftSwitchLwresdCountersServerAAAAReq OBJECT-TYPE
    SYNTAX          Counter
    ACCESS          read-only
    STATUS          mandatory
    DESCRIPTION     
            "Number of AAAA requests sent to the Server."
    ::= { sonusSoftSwitchLwresdCountersServerEntry 20 }

sonusSoftSwitchLwresdCountersServerAAAARsp OBJECT-TYPE
    SYNTAX          Counter
    ACCESS          read-only
    STATUS          mandatory
    DESCRIPTION     
            "Number of AAAA responses received from the  Server."
    ::= { sonusSoftSwitchLwresdCountersServerEntry 21 }

sonusSoftSwitchLwresdCountersServerAAAANoAnsRsp OBJECT-TYPE
    SYNTAX          Counter
    ACCESS          read-only
    STATUS          mandatory
    DESCRIPTION     
            "Number of AAAA no answer responses received from the Server."
    ::= { sonusSoftSwitchLwresdCountersServerEntry 22 }

sonusSoftSwitchLwresdCountersServerAAAATimeout OBJECT-TYPE
    SYNTAX          Counter
    ACCESS          read-only
    STATUS          mandatory
    DESCRIPTION     
            "Number of AAAA requests timed out for the Server."
    ::= { sonusSoftSwitchLwresdCountersServerEntry 23 }

sonusSoftSwitchLwresdCountersServerAAAADestUnreachable OBJECT-TYPE
    SYNTAX          Counter
    ACCESS          read-only
    STATUS          mandatory
    DESCRIPTION     
            "Number of AAAA requests failed due to destination unreachable for the Server."
    ::= { sonusSoftSwitchLwresdCountersServerEntry 24 }

sonusSoftSwitchLwresdCountersServerTCPConnectionAttempt OBJECT-TYPE
    SYNTAX          Counter
    ACCESS          read-only
    STATUS          mandatory
    DESCRIPTION     
            "Number of TCP Connection esteblishment attempts."
    ::= { sonusSoftSwitchLwresdCountersServerEntry 25 }

sonusSoftSwitchLwresdCountersServerTCPConnectionEstablished OBJECT-TYPE
    SYNTAX          Counter
    ACCESS          read-only
    STATUS          mandatory
    DESCRIPTION     
            "Number of established TCP Connections."
    ::= { sonusSoftSwitchLwresdCountersServerEntry 26 }

sonusSoftSwitchLwresdCountersServerTCPConnectionFailed OBJECT-TYPE
    SYNTAX          Counter
    ACCESS          read-only
    STATUS          mandatory
    DESCRIPTION     
            "Number of failed TCP Connections."
    ::= { sonusSoftSwitchLwresdCountersServerEntry 27 }

sonusSoftSwitchLwresdZoneCounters OBJECT IDENTIFIER
    ::= { sonusSoftSwitchLwresdStatistics 2 }

sonusSoftSwitchLwresdCountersZoneTable OBJECT-TYPE
    SYNTAX          SEQUENCE OF SonusSoftSwitchLwresdCountersZoneEntry
    ACCESS          not-accessible
    STATUS          mandatory
    DESCRIPTION     
            "Zone table to hold ENUM/DNS Zone counters."
    ::= { sonusSoftSwitchLwresdZoneCounters 1 }

sonusSoftSwitchLwresdCountersZoneEntry OBJECT-TYPE
    SYNTAX          SonusSoftSwitchLwresdCountersZoneEntry
    ACCESS          not-accessible
    STATUS          mandatory
    DESCRIPTION     
            "An entry in the ENUM/DNS Zone table."
    INDEX           { sonusSoftSwitchLwresdCountersZoneNameLength, 
                      sonusSoftSwitchLwresdCountersZoneName, 
                      sonusSoftSwitchLwresdCountersZoneTransportType }
    ::= { sonusSoftSwitchLwresdCountersZoneTable 1 }

SonusSoftSwitchLwresdCountersZoneEntry ::=
    SEQUENCE {
        sonusSoftSwitchLwresdCountersZoneNameLength           SonusSoftSwitchDomainNameLength,
        sonusSoftSwitchLwresdCountersZoneName     SonusSoftSwitchDomainName,
        sonusSoftSwitchLwresdCountersZoneTransportType              INTEGER,
        sonusSoftSwitchLwresdCountersZoneNAPTRReq         Counter,
        sonusSoftSwitchLwresdCountersZoneNAPTRRsp         Counter,
        sonusSoftSwitchLwresdCountersZoneNAPTRNoAnsRsp              Counter,
        sonusSoftSwitchLwresdCountersZoneNAPTRTimeout             Counter,
        sonusSoftSwitchLwresdCountersZoneNAPTRDestUnreachable                     Counter,
        sonusSoftSwitchLwresdCountersZoneSRVReq       Counter,
        sonusSoftSwitchLwresdCountersZoneSRVRsp       Counter,
        sonusSoftSwitchLwresdCountersZoneSRVNoAnsRsp            Counter,
        sonusSoftSwitchLwresdCountersZoneSRVTimeout           Counter,
        sonusSoftSwitchLwresdCountersZoneSRVDestUnreachable                   Counter,
        sonusSoftSwitchLwresdCountersZoneAReq     Counter,
        sonusSoftSwitchLwresdCountersZoneARsp     Counter,
        sonusSoftSwitchLwresdCountersZoneANoAnsRsp          Counter,
        sonusSoftSwitchLwresdCountersZoneATimeout         Counter,
        sonusSoftSwitchLwresdCountersZoneADestUnreachable                 Counter,
        sonusSoftSwitchLwresdCountersZoneAAAAReq        Counter,
        sonusSoftSwitchLwresdCountersZoneAAAARsp        Counter,
        sonusSoftSwitchLwresdCountersZoneAAAANoAnsRsp             Counter,
        sonusSoftSwitchLwresdCountersZoneAAAATimeout            Counter,
        sonusSoftSwitchLwresdCountersZoneAAAADestUnreachable                    Counter,
        sonusSoftSwitchLwresdCountersZoneTCPConnectionAttempt                     Counter,
        sonusSoftSwitchLwresdCountersZoneTCPConnectionEstablished                         Counter,
        sonusSoftSwitchLwresdCountersZoneTCPConnectionFailed                    Counter
    }

sonusSoftSwitchLwresdCountersZoneNameLength OBJECT-TYPE
    SYNTAX          SonusSoftSwitchDomainNameLength
    ACCESS          read-only
    STATUS          mandatory
    DESCRIPTION     
            "Length of the Zone Name."
    ::= { sonusSoftSwitchLwresdCountersZoneEntry 1 }

sonusSoftSwitchLwresdCountersZoneName OBJECT-TYPE
    SYNTAX          SonusSoftSwitchDomainName
    ACCESS          read-only
    STATUS          mandatory
    DESCRIPTION     
            "Zone Name for which counters are applicable."
    ::= { sonusSoftSwitchLwresdCountersZoneEntry 2 }

sonusSoftSwitchLwresdCountersZoneTransportType OBJECT-TYPE
    SYNTAX          INTEGER
    ACCESS          read-only
    STATUS          mandatory
    DESCRIPTION     
            "The transport type used towards the Zone.1-tcp, 2-udp, 3-tcp fallback"
    ::= { sonusSoftSwitchLwresdCountersZoneEntry 3 }

sonusSoftSwitchLwresdCountersZoneNAPTRReq OBJECT-TYPE
    SYNTAX          Counter
    ACCESS          read-only
    STATUS          mandatory
    DESCRIPTION     
            "Number of NAPTR requests sent for the Zone."
    ::= { sonusSoftSwitchLwresdCountersZoneEntry 4 }

sonusSoftSwitchLwresdCountersZoneNAPTRRsp OBJECT-TYPE
    SYNTAX          Counter
    ACCESS          read-only
    STATUS          mandatory
    DESCRIPTION     
            "Number of NAPTR responses received for the Zone."
    ::= { sonusSoftSwitchLwresdCountersZoneEntry 5 }

sonusSoftSwitchLwresdCountersZoneNAPTRNoAnsRsp OBJECT-TYPE
    SYNTAX          Counter
    ACCESS          read-only
    STATUS          mandatory
    DESCRIPTION     
            "Number of NAPTR no answer responses received for the Zone."
    ::= { sonusSoftSwitchLwresdCountersZoneEntry 6 }

sonusSoftSwitchLwresdCountersZoneNAPTRTimeout OBJECT-TYPE
    SYNTAX          Counter
    ACCESS          read-only
    STATUS          mandatory
    DESCRIPTION     
            "Number of NAPTR requests timed out for the Zone."
    ::= { sonusSoftSwitchLwresdCountersZoneEntry 7 }

sonusSoftSwitchLwresdCountersZoneNAPTRDestUnreachable OBJECT-TYPE
    SYNTAX          Counter
    ACCESS          read-only
    STATUS          mandatory
    DESCRIPTION     
            "Number of NAPTR requests failed due to destination unreachable for the Zone."
    ::= { sonusSoftSwitchLwresdCountersZoneEntry 8 }

sonusSoftSwitchLwresdCountersZoneSRVReq OBJECT-TYPE
    SYNTAX          Counter
    ACCESS          read-only
    STATUS          mandatory
    DESCRIPTION     
            "Number of SRV requests sent for the Zone."
    ::= { sonusSoftSwitchLwresdCountersZoneEntry 9 }

sonusSoftSwitchLwresdCountersZoneSRVRsp OBJECT-TYPE
    SYNTAX          Counter
    ACCESS          read-only
    STATUS          mandatory
    DESCRIPTION     
            "Number of SRV responses received for the Zone."
    ::= { sonusSoftSwitchLwresdCountersZoneEntry 10 }

sonusSoftSwitchLwresdCountersZoneSRVNoAnsRsp OBJECT-TYPE
    SYNTAX          Counter
    ACCESS          read-only
    STATUS          mandatory
    DESCRIPTION     
            "Number of SRV no answer responses received for the Zone."
    ::= { sonusSoftSwitchLwresdCountersZoneEntry 11 }

sonusSoftSwitchLwresdCountersZoneSRVTimeout OBJECT-TYPE
    SYNTAX          Counter
    ACCESS          read-only
    STATUS          mandatory
    DESCRIPTION     
            "Number of SRV requests timed out for the Zone."
    ::= { sonusSoftSwitchLwresdCountersZoneEntry 12 }

sonusSoftSwitchLwresdCountersZoneSRVDestUnreachable OBJECT-TYPE
    SYNTAX          Counter
    ACCESS          read-only
    STATUS          mandatory
    DESCRIPTION     
            "Number of SRV requests failed due to destination unreachable for the Zone."
    ::= { sonusSoftSwitchLwresdCountersZoneEntry 13 }

sonusSoftSwitchLwresdCountersZoneAReq OBJECT-TYPE
    SYNTAX          Counter
    ACCESS          read-only
    STATUS          mandatory
    DESCRIPTION     
            "Number of A requests sent for the Zone."
    ::= { sonusSoftSwitchLwresdCountersZoneEntry 14 }

sonusSoftSwitchLwresdCountersZoneARsp OBJECT-TYPE
    SYNTAX          Counter
    ACCESS          read-only
    STATUS          mandatory
    DESCRIPTION     
            "Number of A responses received for the Zone."
    ::= { sonusSoftSwitchLwresdCountersZoneEntry 15 }

sonusSoftSwitchLwresdCountersZoneANoAnsRsp OBJECT-TYPE
    SYNTAX          Counter
    ACCESS          read-only
    STATUS          mandatory
    DESCRIPTION     
            "Number of A no answer responses received for the Zone."
    ::= { sonusSoftSwitchLwresdCountersZoneEntry 16 }

sonusSoftSwitchLwresdCountersZoneATimeout OBJECT-TYPE
    SYNTAX          Counter
    ACCESS          read-only
    STATUS          mandatory
    DESCRIPTION     
            "Number of A requests timed out for the Zone."
    ::= { sonusSoftSwitchLwresdCountersZoneEntry 17 }

sonusSoftSwitchLwresdCountersZoneADestUnreachable OBJECT-TYPE
    SYNTAX          Counter
    ACCESS          read-only
    STATUS          mandatory
    DESCRIPTION     
            "Number of A requests failed due to destination unreachable for the Zone."
    ::= { sonusSoftSwitchLwresdCountersZoneEntry 18 }

sonusSoftSwitchLwresdCountersZoneAAAAReq OBJECT-TYPE
    SYNTAX          Counter
    ACCESS          read-only
    STATUS          mandatory
    DESCRIPTION     
            "Number of AAAA requests sent for the Zone."
    ::= { sonusSoftSwitchLwresdCountersZoneEntry 19 }

sonusSoftSwitchLwresdCountersZoneAAAARsp OBJECT-TYPE
    SYNTAX          Counter
    ACCESS          read-only
    STATUS          mandatory
    DESCRIPTION     
            "Number of AAAA responses received for the Zone."
    ::= { sonusSoftSwitchLwresdCountersZoneEntry 20 }

sonusSoftSwitchLwresdCountersZoneAAAANoAnsRsp OBJECT-TYPE
    SYNTAX          Counter
    ACCESS          read-only
    STATUS          mandatory
    DESCRIPTION     
            "Number of AAAA no answer responses received for the Zone."
    ::= { sonusSoftSwitchLwresdCountersZoneEntry 21 }

sonusSoftSwitchLwresdCountersZoneAAAATimeout OBJECT-TYPE
    SYNTAX          Counter
    ACCESS          read-only
    STATUS          mandatory
    DESCRIPTION     
            "Number of AAAA requests timed out for the Zone."
    ::= { sonusSoftSwitchLwresdCountersZoneEntry 22 }

sonusSoftSwitchLwresdCountersZoneAAAADestUnreachable OBJECT-TYPE
    SYNTAX          Counter
    ACCESS          read-only
    STATUS          mandatory
    DESCRIPTION     
            "Number of AAAA requests failed due to destination unreachable for the Zone."
    ::= { sonusSoftSwitchLwresdCountersZoneEntry 23 }

sonusSoftSwitchLwresdCountersZoneTCPConnectionAttempt OBJECT-TYPE
    SYNTAX          Counter
    ACCESS          read-only
    STATUS          mandatory
    DESCRIPTION     
            "Number of TCP connection establishment attempts for the Zone."
    ::= { sonusSoftSwitchLwresdCountersZoneEntry 24 }

sonusSoftSwitchLwresdCountersZoneTCPConnectionEstablished OBJECT-TYPE
    SYNTAX          Counter
    ACCESS          read-only
    STATUS          mandatory
    DESCRIPTION     
            "Number of successfully established TCP connections for the Zone."
    ::= { sonusSoftSwitchLwresdCountersZoneEntry 25 }

sonusSoftSwitchLwresdCountersZoneTCPConnectionFailed OBJECT-TYPE
    SYNTAX          Counter
    ACCESS          read-only
    STATUS          mandatory
    DESCRIPTION     
            "Number of failed TCP connections for the Zone."
    ::= { sonusSoftSwitchLwresdCountersZoneEntry 26 }

sonusSoftSwitchLwresdServerHpcCounters OBJECT IDENTIFIER
    ::= { sonusSoftSwitchLwresdStatistics 3 }

sonusSoftSwitchLwresdHpcCountersServerTable OBJECT-TYPE
    SYNTAX          SEQUENCE OF SonusSoftSwitchLwresdHpcCountersServerEntry
    ACCESS          not-accessible
    STATUS          mandatory
    DESCRIPTION     
            "Server Table to hold ENUM/DNS server counters for High Priority and Normal calls."
    ::= { sonusSoftSwitchLwresdServerHpcCounters 1 }

sonusSoftSwitchLwresdHpcCountersServerEntry OBJECT-TYPE
    SYNTAX          SonusSoftSwitchLwresdHpcCountersServerEntry
    ACCESS          not-accessible
    STATUS          mandatory
    DESCRIPTION     
            "An entry in the ENUM/DNS Server Table."
    INDEX           { 
                      sonusSoftSwitchLwresdHpcCountersServerIpAddressType, 
                      sonusSoftSwitchLwresdHpcCountersServerIpAddress, 
                      sonusSoftSwitchLwresdHpcCountersServerPort, 
                      sonusSoftSwitchLwresdHpcCountersServerTransportType }
    ::= { sonusSoftSwitchLwresdHpcCountersServerTable 1 }

SonusSoftSwitchLwresdHpcCountersServerEntry ::=
    SEQUENCE {
        sonusSoftSwitchLwresdHpcCountersServerIpAddressType                   InetAddressType,
        sonusSoftSwitchLwresdHpcCountersServerIpAddress               InetAddress,
        sonusSoftSwitchLwresdHpcCountersServerPort          INTEGER,
        sonusSoftSwitchLwresdHpcCountersServerTransportType                   INTEGER,
        sonusSoftSwitchLwresdHpcCountersServerHpcReq            Counter,
        sonusSoftSwitchLwresdHpcCountersServerHpcRsp            Counter,
        sonusSoftSwitchLwresdHpcCountersServerHpcNoAnsRsp                 Counter,
        sonusSoftSwitchLwresdHpcCountersServerHpcTimeout                Counter,
        sonusSoftSwitchLwresdHpcCountersServerHpcDestUnreachable                        Counter,
        sonusSoftSwitchLwresdHpcCountersServerNonHpcReq               Counter,
        sonusSoftSwitchLwresdHpcCountersServerNonHpcRsp               Counter,
        sonusSoftSwitchLwresdHpcCountersServerNonHpcNoAnsRsp                    Counter,
        sonusSoftSwitchLwresdHpcCountersServerNonHpcTimeout                   Counter,
        sonusSoftSwitchLwresdHpcCountersServerNonHpcDestUnreachable                           Counter
    }

sonusSoftSwitchLwresdHpcCountersServerIpAddressType OBJECT-TYPE
    SYNTAX          InetAddressType
    ACCESS          read-only
    STATUS          mandatory
    DESCRIPTION     
            "The ENUM/DNS Server IP address Type."
    ::= { sonusSoftSwitchLwresdHpcCountersServerEntry 1 }

sonusSoftSwitchLwresdHpcCountersServerIpAddress OBJECT-TYPE
    SYNTAX          InetAddress
    ACCESS          read-only
    STATUS          mandatory
    DESCRIPTION     
            "The ENUM/DNS Server IP address."
    ::= { sonusSoftSwitchLwresdHpcCountersServerEntry 2 }

sonusSoftSwitchLwresdHpcCountersServerPort OBJECT-TYPE
    SYNTAX          INTEGER
    ACCESS          read-only
    STATUS          mandatory
    DESCRIPTION     
            "The Port on which the ENUM/DNS server is listening."
    ::= { sonusSoftSwitchLwresdHpcCountersServerEntry 3 }

sonusSoftSwitchLwresdHpcCountersServerTransportType OBJECT-TYPE
    SYNTAX          INTEGER
    ACCESS          read-only
    STATUS          mandatory
    DESCRIPTION     
            "The transport type used towards the ENUM/DNS Server.1-tcp, 2-udp, 3-tcp fallback"
    ::= { sonusSoftSwitchLwresdHpcCountersServerEntry 4 }

sonusSoftSwitchLwresdHpcCountersServerHpcReq OBJECT-TYPE
    SYNTAX          Counter
    ACCESS          read-only
    STATUS          mandatory
    DESCRIPTION     
            "Number of DNS requests sent to the server for High Priority Calls ."
    ::= { sonusSoftSwitchLwresdHpcCountersServerEntry 5 }

sonusSoftSwitchLwresdHpcCountersServerHpcRsp OBJECT-TYPE
    SYNTAX          Counter
    ACCESS          read-only
    STATUS          mandatory
    DESCRIPTION     
            "Number of DNS responses received from the Server for High Priority Calls ."
    ::= { sonusSoftSwitchLwresdHpcCountersServerEntry 6 }

sonusSoftSwitchLwresdHpcCountersServerHpcNoAnsRsp OBJECT-TYPE
    SYNTAX          Counter
    ACCESS          read-only
    STATUS          mandatory
    DESCRIPTION     
            "Number of DNS no answer responses received from the  Server for High Priority Calls ."
    ::= { sonusSoftSwitchLwresdHpcCountersServerEntry 7 }

sonusSoftSwitchLwresdHpcCountersServerHpcTimeout OBJECT-TYPE
    SYNTAX          Counter
    ACCESS          read-only
    STATUS          mandatory
    DESCRIPTION     
            "Number of HPC DNS requests timed out for the Server."
    ::= { sonusSoftSwitchLwresdHpcCountersServerEntry 8 }

sonusSoftSwitchLwresdHpcCountersServerHpcDestUnreachable OBJECT-TYPE
    SYNTAX          Counter
    ACCESS          read-only
    STATUS          mandatory
    DESCRIPTION     
            "Number of HPC DNS requests failed due to destination unreachable for the Server."
    ::= { sonusSoftSwitchLwresdHpcCountersServerEntry 9 }

sonusSoftSwitchLwresdHpcCountersServerNonHpcReq OBJECT-TYPE
    SYNTAX          Counter
    ACCESS          read-only
    STATUS          mandatory
    DESCRIPTION     
            "Number of DNS requests sent to the Server for Non High Priority Calls."
    ::= { sonusSoftSwitchLwresdHpcCountersServerEntry 10 }

sonusSoftSwitchLwresdHpcCountersServerNonHpcRsp OBJECT-TYPE
    SYNTAX          Counter
    ACCESS          read-only
    STATUS          mandatory
    DESCRIPTION     
            "Number of DNS responses received from the Server for Non High Priority Calls.."
    ::= { sonusSoftSwitchLwresdHpcCountersServerEntry 11 }

sonusSoftSwitchLwresdHpcCountersServerNonHpcNoAnsRsp OBJECT-TYPE
    SYNTAX          Counter
    ACCESS          read-only
    STATUS          mandatory
    DESCRIPTION     
            "Number of DNS no answer responses received from the Server for Non High Priority Calls.."
    ::= { sonusSoftSwitchLwresdHpcCountersServerEntry 12 }

sonusSoftSwitchLwresdHpcCountersServerNonHpcTimeout OBJECT-TYPE
    SYNTAX          Counter
    ACCESS          read-only
    STATUS          mandatory
    DESCRIPTION     
            "Number of Non HPC DNS requests timed out for the Server."
    ::= { sonusSoftSwitchLwresdHpcCountersServerEntry 13 }

sonusSoftSwitchLwresdHpcCountersServerNonHpcDestUnreachable OBJECT-TYPE
    SYNTAX          Counter
    ACCESS          read-only
    STATUS          mandatory
    DESCRIPTION     
            "Number of Non HPC DNS requests failed due to destination unreachable for the Server."
    ::= { sonusSoftSwitchLwresdHpcCountersServerEntry 14 }

sonusSoftSwitchLwresdZoneHpcCounters OBJECT IDENTIFIER
    ::= { sonusSoftSwitchLwresdStatistics 4 }

sonusSoftSwitchLwresdHpcCountersZoneTable OBJECT-TYPE
    SYNTAX          SEQUENCE OF SonusSoftSwitchLwresdHpcCountersZoneEntry
    ACCESS          not-accessible
    STATUS          mandatory
    DESCRIPTION     
            "Zone table to hold ENUM/DNS Zone Hpc counters."
    ::= { sonusSoftSwitchLwresdZoneHpcCounters 1 }

sonusSoftSwitchLwresdHpcCountersZoneEntry OBJECT-TYPE
    SYNTAX          SonusSoftSwitchLwresdHpcCountersZoneEntry
    ACCESS          not-accessible
    STATUS          mandatory
    DESCRIPTION     
            "An entry in the ENUM/DNS Zone table."
    INDEX           { sonusSoftSwitchLwresdHpcCountersZoneNameLength, 
                      sonusSoftSwitchLwresdHpcCountersZoneName, 
                      sonusSoftSwitchLwresdHpcCountersZoneTransportType }
    ::= { sonusSoftSwitchLwresdHpcCountersZoneTable 1 }

SonusSoftSwitchLwresdHpcCountersZoneEntry ::=
    SEQUENCE {
        sonusSoftSwitchLwresdHpcCountersZoneNameLength              SonusSoftSwitchDomainNameLength,
        sonusSoftSwitchLwresdHpcCountersZoneName        SonusSoftSwitchDomainName,
        sonusSoftSwitchLwresdHpcCountersZoneTransportType                 INTEGER,
        sonusSoftSwitchLwresdHpcCountersZoneHpcReq          Counter,
        sonusSoftSwitchLwresdHpcCountersZoneHpcRsp          Counter,
        sonusSoftSwitchLwresdHpcCountersZoneHpcNoAnsRsp               Counter,
        sonusSoftSwitchLwresdHpcCountersZoneHpcTimeout              Counter,
        sonusSoftSwitchLwresdHpcCountersZoneHpcDestUnreachable                      Counter,
        sonusSoftSwitchLwresdHpcCountersZoneNonHpcReq             Counter,
        sonusSoftSwitchLwresdHpcCountersZoneNonHpcRsp             Counter,
        sonusSoftSwitchLwresdHpcCountersZoneNonHpcNoAnsRsp                  Counter,
        sonusSoftSwitchLwresdHpcCountersZoneNonHpcTimeout                 Counter,
        sonusSoftSwitchLwresdHpcCountersZoneNonHpcDestUnreachable                         Counter
    }

sonusSoftSwitchLwresdHpcCountersZoneNameLength OBJECT-TYPE
    SYNTAX          SonusSoftSwitchDomainNameLength
    ACCESS          read-only
    STATUS          mandatory
    DESCRIPTION     
            "Length of the Zone Name."
    ::= { sonusSoftSwitchLwresdHpcCountersZoneEntry 1 }

sonusSoftSwitchLwresdHpcCountersZoneName OBJECT-TYPE
    SYNTAX          SonusSoftSwitchDomainName
    ACCESS          read-only
    STATUS          mandatory
    DESCRIPTION     
            "Zone Name for which counters are applicable."
    ::= { sonusSoftSwitchLwresdHpcCountersZoneEntry 2 }

sonusSoftSwitchLwresdHpcCountersZoneTransportType OBJECT-TYPE
    SYNTAX          INTEGER
    ACCESS          read-only
    STATUS          mandatory
    DESCRIPTION     
            "The transport type used towards the Zone.1-tcp, 2-udp, 3-tcp fallback"
    ::= { sonusSoftSwitchLwresdHpcCountersZoneEntry 3 }

sonusSoftSwitchLwresdHpcCountersZoneHpcReq OBJECT-TYPE
    SYNTAX          Counter
    ACCESS          read-only
    STATUS          mandatory
    DESCRIPTION     
            "Number of HPC DNS requests sent for the Zone."
    ::= { sonusSoftSwitchLwresdHpcCountersZoneEntry 4 }

sonusSoftSwitchLwresdHpcCountersZoneHpcRsp OBJECT-TYPE
    SYNTAX          Counter
    ACCESS          read-only
    STATUS          mandatory
    DESCRIPTION     
            "Number of HPC DNS responses received for the Zone."
    ::= { sonusSoftSwitchLwresdHpcCountersZoneEntry 5 }

sonusSoftSwitchLwresdHpcCountersZoneHpcNoAnsRsp OBJECT-TYPE
    SYNTAX          Counter
    ACCESS          read-only
    STATUS          mandatory
    DESCRIPTION     
            "Number of HPC DNS no answer responses received for the Zone."
    ::= { sonusSoftSwitchLwresdHpcCountersZoneEntry 6 }

sonusSoftSwitchLwresdHpcCountersZoneHpcTimeout OBJECT-TYPE
    SYNTAX          Counter
    ACCESS          read-only
    STATUS          mandatory
    DESCRIPTION     
            "Number of HPC DNS requests timed out for the Zone."
    ::= { sonusSoftSwitchLwresdHpcCountersZoneEntry 7 }

sonusSoftSwitchLwresdHpcCountersZoneHpcDestUnreachable OBJECT-TYPE
    SYNTAX          Counter
    ACCESS          read-only
    STATUS          mandatory
    DESCRIPTION     
            "Number of HPC DNS requests failed due to destination unreachable for the Zone."
    ::= { sonusSoftSwitchLwresdHpcCountersZoneEntry 8 }

sonusSoftSwitchLwresdHpcCountersZoneNonHpcReq OBJECT-TYPE
    SYNTAX          Counter
    ACCESS          read-only
    STATUS          mandatory
    DESCRIPTION     
            "Number of Non HPC DNS requests sent for the Zone."
    ::= { sonusSoftSwitchLwresdHpcCountersZoneEntry 9 }

sonusSoftSwitchLwresdHpcCountersZoneNonHpcRsp OBJECT-TYPE
    SYNTAX          Counter
    ACCESS          read-only
    STATUS          mandatory
    DESCRIPTION     
            "Number of Non HPC DNS responses received for the Zone."
    ::= { sonusSoftSwitchLwresdHpcCountersZoneEntry 10 }

sonusSoftSwitchLwresdHpcCountersZoneNonHpcNoAnsRsp OBJECT-TYPE
    SYNTAX          Counter
    ACCESS          read-only
    STATUS          mandatory
    DESCRIPTION     
            "Number of Non HPC DNS no answer responses received for the Zone."
    ::= { sonusSoftSwitchLwresdHpcCountersZoneEntry 11 }

sonusSoftSwitchLwresdHpcCountersZoneNonHpcTimeout OBJECT-TYPE
    SYNTAX          Counter
    ACCESS          read-only
    STATUS          mandatory
    DESCRIPTION     
            "Number of Non HPC DNS requests timed out for the Zone."
    ::= { sonusSoftSwitchLwresdHpcCountersZoneEntry 12 }

sonusSoftSwitchLwresdHpcCountersZoneNonHpcDestUnreachable OBJECT-TYPE
    SYNTAX          Counter
    ACCESS          read-only
    STATUS          mandatory
    DESCRIPTION     
            "Number of Non HPC DNS requests failed due to destination unreachable for the Zone."
    ::= { sonusSoftSwitchLwresdHpcCountersZoneEntry 13 }

sonusSoftswitchLWRESDDNSServerBlacklistedNotification TRAP-TYPE
    ENTERPRISE      sonusSoftSwitchLwresdMIBNotifications
    VARIABLES       { sonusEventDescription, sonusEventClass, 
                      sonusEventLevel, sonusEventTime }
--     STATUS          mandatory
    DESCRIPTION     
            "DNS Server is Black listed"
    ::= 1

sonusSoftswitchLWRESDDNSServerRecoveredNotification TRAP-TYPE
    ENTERPRISE      sonusSoftSwitchLwresdMIBNotifications
    VARIABLES       { sonusEventDescription, sonusEventClass, 
                      sonusEventLevel, sonusEventTime }
--     STATUS          mandatory
    DESCRIPTION     
            "DNS Serevr is Recovered"
    ::= 2

sonusSoftswitchLWRESDEDNSResponseFailure TRAP-TYPE
    ENTERPRISE      sonusSoftSwitchLwresdMIBNotifications
    VARIABLES       { sonusEventDescription, sonusEventClass, 
                      sonusEventLevel, sonusEventTime }
--     STATUS          mandatory
    DESCRIPTION     
            "Failure Response for EDNS query with NOT-IMPLE, FORMERR or SERVFAIL"
    ::= 3

sonusSoftswitchLWRESDEDNSResponseSuccess TRAP-TYPE
    ENTERPRISE      sonusSoftSwitchLwresdMIBNotifications
    VARIABLES       { sonusEventDescription, sonusEventClass, 
                      sonusEventLevel, sonusEventTime }
--     STATUS          mandatory
    DESCRIPTION     
            "Successful Response for EDNS query which failed earlier for that domain"
    ::= 4

sonusSoftswitchLWRESDTTLExpiredRRFallback TRAP-TYPE
    ENTERPRISE      sonusSoftSwitchLwresdMIBNotifications
    VARIABLES       { sonusEventDescription, sonusEventClass, 
                      sonusEventLevel, sonusEventTime }
--     STATUS          mandatory
    DESCRIPTION     
            "Fallback to TTL expired RR due to DNS response failure"
    ::= 5

sonusSoftswitchLWRESDNormalDNSResponse TRAP-TYPE
    ENTERPRISE      sonusSoftSwitchLwresdMIBNotifications
    VARIABLES       { sonusEventDescription, sonusEventClass, 
                      sonusEventLevel, sonusEventTime }
--     STATUS          mandatory
    DESCRIPTION     
            "Normal DNS response for a query that previously used expired TTL RR"
    ::= 6

END -- end of module SONUS-SOFTSWITCH-LWRESD-MIB.
