--
-- This SMIv1 module has been generated by smidump 0.2-cvs. Do not edit.
--

SONUS-SOFTSWITCH-PIPE-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI
    sonusSoftSwitchTMAddressNature, sonusSoftSwitchTMElementType, 
    sonusSoftSwitchTMIdentifier1, sonusSoftSwitchTMIdentifier2, 
    sonusSoftSwitchTMProvControlType
        FROM SONUS-SOFTSWITCH-MIB;

sonusSoftSwitchPIPEMIB OBJECT IDENTIFIER
    ::= { sonusServicesMIBs 18 }

-- sonusSoftSwitchPIPEMIB MODULE-IDENTITY
--     LAST-UPDATED    "200211040000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for SoftSwitch PIPE Management."
--     ::= { sonusServicesMIBs 18 }


sonusSoftSwitchPIPEMIBObjects OBJECT IDENTIFIER
    ::= { sonusSoftSwitchPIPEMIB 1 }

sonusSoftSwitchPIPEMIBNotifications OBJECT IDENTIFIER
    ::= { sonusSoftSwitchPIPEMIB 2 }

sonusSoftSwitchPIPEMIBNotificationsPrefix OBJECT IDENTIFIER
    ::= { sonusSoftSwitchPIPEMIBNotifications 0 }

sonusSoftSwitchPIPEMIBNotificationsObjects OBJECT IDENTIFIER
    ::= { sonusSoftSwitchPIPEMIBNotifications 1 }

sonusSoftSwitchPipeDownNotification TRAP-TYPE
    ENTERPRISE      sonusSoftSwitchPIPEMIBNotifications
    VARIABLES       { sonusEventDescription, sonusEventClass, 
                      sonusEventLevel, sonusEventTime }
--     STATUS          mandatory
    DESCRIPTION     
            "PIPE is down"
    ::= 1

sonusSoftSwitchPipeUpNotification TRAP-TYPE
    ENTERPRISE      sonusSoftSwitchPIPEMIBNotifications
    VARIABLES       { sonusEventDescription, sonusEventClass, 
                      sonusEventLevel, sonusEventTime }
--     STATUS          mandatory
    DESCRIPTION     
            "PIPE is up"
    ::= 2

sonusSoftSwitchPipeTMControlProvisionedNotification TRAP-TYPE
    ENTERPRISE      sonusSoftSwitchPIPEMIBNotifications
    VARIABLES       { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
--     STATUS          mandatory
    DESCRIPTION     
            "A traffic control has been provisioned."
    ::= 3

sonusSoftSwitchPipeTMControlRemovedNotification TRAP-TYPE
    ENTERPRISE      sonusSoftSwitchPIPEMIBNotifications
    VARIABLES       { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
--     STATUS          mandatory
    DESCRIPTION     
            "A traffic control has been removed."
    ::= 4

sonusSoftSwitchPipeTMControlModifiedNotification TRAP-TYPE
    ENTERPRISE      sonusSoftSwitchPIPEMIBNotifications
    VARIABLES       { sonusSoftSwitchTMElementType, 
                      sonusSoftSwitchTMIdentifier1, 
                      sonusSoftSwitchTMIdentifier2, 
                      sonusSoftSwitchTMProvControlType, 
                      sonusSoftSwitchTMAddressNature, 
                      sonusEventDescription, sonusEventClass, 
                      sonusEventLevel, sonusEventTime }
--     STATUS          mandatory
    DESCRIPTION     
            "A traffic control has been modified."
    ::= 5

sonusSoftSwitchMasterKeyNotification TRAP-TYPE
    ENTERPRISE      sonusSoftSwitchPIPEMIBNotifications
    VARIABLES       { sonusEventDescription, sonusEventClass, 
                      sonusEventLevel, sonusEventTime }
--     STATUS          mandatory
    DESCRIPTION     
            "Master Key has not been Configured.Please Configure Master Key"
    ::= 6

END -- end of module SONUS-SOFTSWITCH-PIPE-MIB.
