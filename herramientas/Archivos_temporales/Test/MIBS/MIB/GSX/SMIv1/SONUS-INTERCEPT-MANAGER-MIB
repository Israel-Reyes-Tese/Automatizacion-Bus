--
-- This SMIv1 module has been generated by smidump 0.2-cvs. Do not edit.
--

SONUS-INTERCEPT-MANAGER-MIB DEFINITIONS ::= BEGIN

IMPORTS
    Ipv6Address
        FROM IPV6-TC
    OBJECT-TYPE
        FROM RFC-1212
    TRAP-TYPE
        FROM RFC-1215
    Counter, IpAddress
        FROM RFC1155-SMI
    RowStatus
        FROM SNMPv2-TC
    sonusEventClass, sonusEventDescription, sonusEventLevel, 
    sonusEventTime, sonusSequenceId
        FROM SONUS-COMMON-MIB
    sonusServicesMIBs
        FROM SONUS-SMI
    SonusName, SonusNameReference
        FROM SONUS-TC;

sonusInterceptManagerMIB OBJECT IDENTIFIER
    ::= { sonusServicesMIBs 28 }

-- sonusInterceptManagerMIB MODULE-IDENTITY
--     LAST-UPDATED    "201209130000Z"
--     ORGANIZATION    
--             "Sonus Networks, Inc."
--     CONTACT-INFO    
--             "   Customer Support    
--              Sonus Networks, Inc,
--              5 carlisle Road
--              Westford, MA 01886
--              USA
--              
--              Tel: 978-692-8999
--              Fax: 978-392-9118
--              E-mail: cs.snmp@sonusnet.com"
--     DESCRIPTION     
--             "The MIB Module for the Intercept Manager."
--     ::= { sonusServicesMIBs 28 }


sonusInterceptManagerMIBObjects OBJECT IDENTIFIER
    ::= { sonusInterceptManagerMIB 1 }

sonusImAdmnNodeNumber OBJECT-TYPE
    SYNTAX          DisplayString (SIZE(1..5))
    ACCESS          read-write
    STATUS          mandatory
    DESCRIPTION     
            "The node number that will be used to identify this GSX in all call data
             messages sent to the Intercept Server.  It must be unique within a 
             carrier's network."
    ::= { sonusInterceptManagerMIBObjects 1 }

sonusImAdmnTableNextIndex OBJECT-TYPE
    SYNTAX          INTEGER
    ACCESS          read-only
    STATUS          mandatory
    DESCRIPTION     
            "The next valid index to use when creating a new sonusImAdmnEntry"
    ::= { sonusInterceptManagerMIBObjects 2 }

sonusImAdmnTable OBJECT-TYPE
    SYNTAX          SEQUENCE OF SonusImAdmnEntry
    ACCESS          not-accessible
    STATUS          mandatory
    DESCRIPTION     
            "A list of Intercept Manager entries."
    ::= { sonusInterceptManagerMIBObjects 3 }

sonusImAdmnEntry OBJECT-TYPE
    SYNTAX          SonusImAdmnEntry
    ACCESS          not-accessible
    STATUS          mandatory
    DESCRIPTION     
            "Each sonusImAdmnEntry containing configuration objects.
             Rules & Behaviors:
                  A sonusImAdmnEntry cannot be modified when it is  enabled."
    INDEX           { sonusImAdmnIndex }
    ::= { sonusImAdmnTable 1 }

SonusImAdmnEntry ::=
    SEQUENCE {
        sonusImAdmnIndex                Gauge,
        sonusImAdmnName                 SonusName,
        sonusImAdmnPriState             INTEGER,
        sonusImAdmnPriIpaddr            IpAddress,
        sonusImAdmnUdpPort              Gauge,
        sonusImAdmnPriMode              INTEGER,
        sonusImAdmnSecState             INTEGER,
        sonusImAdmnSecIpaddr            IpAddress,
        sonusImAdmnSecMode              INTEGER,
        sonusImAdmnKeepAliveTimer       Gauge,
        sonusImAdmnRetries              Gauge,
        sonusImAdmnRowStatus            RowStatus,
        sonusImAdmnNifGroupName         SonusNameReference,
        sonusImAdmnPriIp6addr           Ipv6Address,
        sonusImAdmnSecIp6addr           Ipv6Address,
        sonusImAdmnPriIpVersion         INTEGER,
        sonusImAdmnSecIpVersion         INTEGER,
        sonusImAdmnNoaParamSupport      INTEGER,
        sonusImAdmnServerType           INTEGER
    }

sonusImAdmnIndex OBJECT-TYPE
    SYNTAX          Gauge
    ACCESS          read-only
    STATUS          mandatory
    DESCRIPTION     
            "A unique value for each Intercept Manager that is between 1
             and maximum allowed"
    ::= { sonusImAdmnEntry 1 }

sonusImAdmnName OBJECT-TYPE
    SYNTAX          SonusName
    ACCESS          read-write
    STATUS          mandatory
    DESCRIPTION     
            "The name of this Intercept Manager instance."
    ::= { sonusImAdmnEntry 2 }

sonusImAdmnPriState OBJECT-TYPE
    SYNTAX          INTEGER { disabled(1), enabled(2) }
    ACCESS          read-write
    STATUS          mandatory
    DESCRIPTION     
            "The administrative state of the call data channel to the primary Intercept Server."
    DEFVAL          { disabled }
    ::= { sonusImAdmnEntry 3 }

sonusImAdmnPriIpaddr OBJECT-TYPE
    SYNTAX          IpAddress
    ACCESS          read-write
    STATUS          mandatory
    DESCRIPTION     
            "Specifies the IP Address of the primary call data channel to the Intercept Server platform."
    ::= { sonusImAdmnEntry 4 }

sonusImAdmnUdpPort OBJECT-TYPE
    SYNTAX          Gauge (1..65535)
    ACCESS          read-write
    STATUS          mandatory
    DESCRIPTION     
            "UDP port for the primary and secondary call data channel to the Intercept Server platform."
    ::= { sonusImAdmnEntry 5 }

sonusImAdmnPriMode OBJECT-TYPE
    SYNTAX          INTEGER { active(1), standby(2), outOfService(3) }
    ACCESS          read-write
    STATUS          mandatory
    DESCRIPTION     
            "Specifies the service mode of the primary call data channel to the Intercept Server platform."
    DEFVAL          { outOfService }
    ::= { sonusImAdmnEntry 6 }

sonusImAdmnSecState OBJECT-TYPE
    SYNTAX          INTEGER { disabled(1), enabled(2) }
    ACCESS          read-write
    STATUS          mandatory
    DESCRIPTION     
            "The administrative state of the call data channel to the secondary Intercept Server."
    DEFVAL          { disabled }
    ::= { sonusImAdmnEntry 7 }

sonusImAdmnSecIpaddr OBJECT-TYPE
    SYNTAX          IpAddress
    ACCESS          read-write
    STATUS          mandatory
    DESCRIPTION     
            "Specifies the IP Address of the primary call data channel to the Intercept Server platform."
    ::= { sonusImAdmnEntry 8 }

sonusImAdmnSecMode OBJECT-TYPE
    SYNTAX          INTEGER { active(1), standby(2), outOfService(3) }
    ACCESS          read-write
    STATUS          mandatory
    DESCRIPTION     
            "Specifies the service mode of the secondary call data channel to the Intercept Server platform."
    DEFVAL          { outOfService }
    ::= { sonusImAdmnEntry 9 }

sonusImAdmnKeepAliveTimer OBJECT-TYPE
    SYNTAX          Gauge (0..60)
    ACCESS          read-write
    STATUS          mandatory
    DESCRIPTION     
            "The value in seconds of the keep alive timer for the active call data channel."
    DEFVAL          { 5 }
    ::= { sonusImAdmnEntry 10 }

sonusImAdmnRetries OBJECT-TYPE
    SYNTAX          Gauge (1..10)
    ACCESS          read-write
    STATUS          mandatory
    DESCRIPTION     
            "The number of retries that will be attempted when a call data channel message is lost."
    DEFVAL          { 3 }
    ::= { sonusImAdmnEntry 11 }

sonusImAdmnRowStatus OBJECT-TYPE
    SYNTAX          RowStatus
    ACCESS          read-write
    STATUS          mandatory
    DESCRIPTION     
            "This object is used to create a new row or modify or delete an  existing row in this table."
    ::= { sonusImAdmnEntry 12 }

sonusImAdmnNifGroupName OBJECT-TYPE
    SYNTAX          SonusNameReference
    ACCESS          read-write
    STATUS          mandatory
    DESCRIPTION     
            "The NIF group which this call data channel belongs to."
    ::= { sonusImAdmnEntry 13 }

sonusImAdmnPriIp6addr OBJECT-TYPE
    SYNTAX          Ipv6Address
    ACCESS          read-write
    STATUS          mandatory
    DESCRIPTION     
            "Specifies the IPV6 Address of the primary call data channel to the Intercept Server platform."
    ::= { sonusImAdmnEntry 14 }

sonusImAdmnSecIp6addr OBJECT-TYPE
    SYNTAX          Ipv6Address
    ACCESS          read-write
    STATUS          mandatory
    DESCRIPTION     
            "Specifies the IPV6 Address of the primary call data channel to the Intercept Server platform."
    ::= { sonusImAdmnEntry 15 }

sonusImAdmnPriIpVersion OBJECT-TYPE
    SYNTAX          INTEGER { afInet(2), afInet6(24) }
    ACCESS          read-only
    STATUS          mandatory
    DESCRIPTION     
            "The Im Admn Pri IP version."
    ::= { sonusImAdmnEntry 16 }

sonusImAdmnSecIpVersion OBJECT-TYPE
    SYNTAX          INTEGER { afInet(2), afInet6(24) }
    ACCESS          read-only
    STATUS          mandatory
    DESCRIPTION     
            "The Im Admn Sec IP version."
    ::= { sonusImAdmnEntry 17 }

sonusImAdmnNoaParamSupport OBJECT-TYPE
    SYNTAX          INTEGER { disabled(1), enabled(2) }
    ACCESS          read-write
    STATUS          mandatory
    DESCRIPTION     
            "This flag will determine if the NOA parameter will be sent in LI messages or not. "
    DEFVAL          { disabled }
    ::= { sonusImAdmnEntry 18 }

sonusImAdmnServerType OBJECT-TYPE
    SYNTAX          INTEGER { default(0), zeel(1) }
    ACCESS          read-write
    STATUS          mandatory
    DESCRIPTION     
            "The server type being used for this Intercept Server, currently support for DEFAULT or ZEEL."
    DEFVAL          { default }
    ::= { sonusImAdmnEntry 19 }

sonusImStatusTable OBJECT-TYPE
    SYNTAX          SEQUENCE OF SonusImStatusEntry
    ACCESS          not-accessible
    STATUS          mandatory
    DESCRIPTION     
            "Status Table of the intercept server"
    ::= { sonusInterceptManagerMIBObjects 4 }

sonusImStatusEntry OBJECT-TYPE
    SYNTAX          SonusImStatusEntry
    ACCESS          not-accessible
    STATUS          mandatory
    DESCRIPTION     
            "Each entry describes the current status of a intercept manager entry."
    INDEX           { sonusImStatusIndex }
    ::= { sonusImStatusTable 1 }

SonusImStatusEntry ::=
    SEQUENCE {
        sonusImStatusIndex              Gauge,
        sonusImStatusPriOperState       INTEGER,
        sonusImStatusSecOperState       INTEGER,
        sonusImStatusSignalStartSuccess Counter,
        sonusImStatusSignalStartUnsuccess Counter,
        sonusImStatusCallAnswerSuccess  Counter,
        sonusImStatusCallAnswerUnsuccess Counter,
        sonusImStatusCallDisconnectSuccess  Counter,
        sonusImStatusCallDisconnectUnsuccess    Counter,
        sonusImStatusMediaReportSuccess Counter,
        sonusImStatusMediaReportUnsuccess Counter,
        sonusImStatusServiceInstanceSuccess   Counter,
        sonusImStatusServiceInstanceUnsuccess     Counter,
        sonusImStatusSignalInstanceSuccess  Counter,
        sonusImStatusSignalInstanceUnsuccess    Counter,
        sonusImStatusIndicationSuccess  Counter,
        sonusImStatusIndicationUnsuccess Counter,
        sonusImStatusKeepAliveSuccess   Counter,
        sonusImStatusKeepAliveUnsuccess Counter,
        sonusImStatusRestartSuccess     Counter,
        sonusImStatusRestartUnsuccess   Counter,
        sonusImStatusRadiusAckReceived  Counter,
        sonusImStatusRadiusUnknownMsgReceived     Counter,
        sonusImStatusSignalStartResponseReceived        Counter,
        sonusImStatusSignalStopSuccess  Counter,
        sonusImStatusSignalStopUnsuccess Counter
    }

sonusImStatusIndex OBJECT-TYPE
    SYNTAX          Gauge
    ACCESS          read-only
    STATUS          mandatory
    DESCRIPTION     
            "A unique value for each intercept manager entry between 1 and maximum 
             allowed."
    ::= { sonusImStatusEntry 1 }

sonusImStatusPriOperState OBJECT-TYPE
    SYNTAX          INTEGER { inService(1), outOfService(2), standBy(3) }
    ACCESS          read-only
    STATUS          mandatory
    DESCRIPTION     
            " Current operational state of the primary call data channel."
    ::= { sonusImStatusEntry 2 }

sonusImStatusSecOperState OBJECT-TYPE
    SYNTAX          INTEGER { inService(1), outOfService(2), standBy(3) }
    ACCESS          read-only
    STATUS          mandatory
    DESCRIPTION     
            " Current operational state of the Secondary call data channel."
    ::= { sonusImStatusEntry 3 }

sonusImStatusSignalStartSuccess OBJECT-TYPE
    SYNTAX          Counter
    ACCESS          read-only
    STATUS          mandatory
    DESCRIPTION     
            " The number of successful Signal Start messages sent on the active call data channel."
    ::= { sonusImStatusEntry 4 }

sonusImStatusSignalStartUnsuccess OBJECT-TYPE
    SYNTAX          Counter
    ACCESS          read-only
    STATUS          mandatory
    DESCRIPTION     
            " The number of unsuccessful Signal Start messages sent on the active call data channel."
    ::= { sonusImStatusEntry 5 }

sonusImStatusCallAnswerSuccess OBJECT-TYPE
    SYNTAX          Counter
    ACCESS          read-only
    STATUS          mandatory
    DESCRIPTION     
            " The number of successful Call Answer messages sent on the active call data channel."
    ::= { sonusImStatusEntry 6 }

sonusImStatusCallAnswerUnsuccess OBJECT-TYPE
    SYNTAX          Counter
    ACCESS          read-only
    STATUS          mandatory
    DESCRIPTION     
            " The number of unsuccessful Call Answer messages sent on the active call data channel."
    ::= { sonusImStatusEntry 7 }

sonusImStatusCallDisconnectSuccess OBJECT-TYPE
    SYNTAX          Counter
    ACCESS          read-only
    STATUS          mandatory
    DESCRIPTION     
            " The number of successful Call Disconnect messages sent on the active call data channel."
    ::= { sonusImStatusEntry 8 }

sonusImStatusCallDisconnectUnsuccess OBJECT-TYPE
    SYNTAX          Counter
    ACCESS          read-only
    STATUS          mandatory
    DESCRIPTION     
            " The number of unsuccessful Call Disconnect messages sent on the active call data channel."
    ::= { sonusImStatusEntry 9 }

sonusImStatusMediaReportSuccess OBJECT-TYPE
    SYNTAX          Counter
    ACCESS          read-only
    STATUS          mandatory
    DESCRIPTION     
            " The number of successful Media Report messages sent on the active call data channel."
    ::= { sonusImStatusEntry 10 }

sonusImStatusMediaReportUnsuccess OBJECT-TYPE
    SYNTAX          Counter
    ACCESS          read-only
    STATUS          mandatory
    DESCRIPTION     
            " The number of unsuccessful Media Report messages sent on the active call data channel."
    ::= { sonusImStatusEntry 11 }

sonusImStatusServiceInstanceSuccess OBJECT-TYPE
    SYNTAX          Counter
    ACCESS          read-only
    STATUS          mandatory
    DESCRIPTION     
            " The number of successful Service Instance messages sent on the active call data channel."
    ::= { sonusImStatusEntry 12 }

sonusImStatusServiceInstanceUnsuccess OBJECT-TYPE
    SYNTAX          Counter
    ACCESS          read-only
    STATUS          mandatory
    DESCRIPTION     
            " The number of unsuccessful Service Instance messages sent on the active call data channel."
    ::= { sonusImStatusEntry 13 }

sonusImStatusSignalInstanceSuccess OBJECT-TYPE
    SYNTAX          Counter
    ACCESS          read-only
    STATUS          mandatory
    DESCRIPTION     
            " The number of successful Signal Instance messages sent on the active call data channel."
    ::= { sonusImStatusEntry 14 }

sonusImStatusSignalInstanceUnsuccess OBJECT-TYPE
    SYNTAX          Counter
    ACCESS          read-only
    STATUS          mandatory
    DESCRIPTION     
            " The number of unsuccessful Signal Instance messages sent on the active call data channel."
    ::= { sonusImStatusEntry 15 }

sonusImStatusIndicationSuccess OBJECT-TYPE
    SYNTAX          Counter
    ACCESS          read-only
    STATUS          mandatory
    DESCRIPTION     
            " The number of successful Indication messages sent on the active call data channel."
    ::= { sonusImStatusEntry 16 }

sonusImStatusIndicationUnsuccess OBJECT-TYPE
    SYNTAX          Counter
    ACCESS          read-only
    STATUS          mandatory
    DESCRIPTION     
            " The number of unsuccessful Indication messages sent on the active call data channel."
    ::= { sonusImStatusEntry 17 }

sonusImStatusKeepAliveSuccess OBJECT-TYPE
    SYNTAX          Counter
    ACCESS          read-only
    STATUS          mandatory
    DESCRIPTION     
            " The number of successful Keep Alive messages sent on the active call data channel."
    ::= { sonusImStatusEntry 18 }

sonusImStatusKeepAliveUnsuccess OBJECT-TYPE
    SYNTAX          Counter
    ACCESS          read-only
    STATUS          mandatory
    DESCRIPTION     
            " The number of unsuccessful Keep Alive messages sent on the active call data channel."
    ::= { sonusImStatusEntry 19 }

sonusImStatusRestartSuccess OBJECT-TYPE
    SYNTAX          Counter
    ACCESS          read-only
    STATUS          mandatory
    DESCRIPTION     
            " The number of successful Restart messages sent on the active call data channel."
    ::= { sonusImStatusEntry 20 }

sonusImStatusRestartUnsuccess OBJECT-TYPE
    SYNTAX          Counter
    ACCESS          read-only
    STATUS          mandatory
    DESCRIPTION     
            " The number of unsuccessful Restart messages sent on the active call data channel."
    ::= { sonusImStatusEntry 21 }

sonusImStatusRadiusAckReceived OBJECT-TYPE
    SYNTAX          Counter
    ACCESS          read-only
    STATUS          mandatory
    DESCRIPTION     
            " The number of Radius Acknowledgement messages received on the active call data channel."
    ::= { sonusImStatusEntry 22 }

sonusImStatusRadiusUnknownMsgReceived OBJECT-TYPE
    SYNTAX          Counter
    ACCESS          read-only
    STATUS          mandatory
    DESCRIPTION     
            " The number of messages received with an unknown Radius message code on the active call data channel."
    ::= { sonusImStatusEntry 23 }

sonusImStatusSignalStartResponseReceived OBJECT-TYPE
    SYNTAX          Counter
    ACCESS          read-only
    STATUS          mandatory
    DESCRIPTION     
            " The number of Signaling Start Response messages received on the active call data channel."
    ::= { sonusImStatusEntry 24 }

sonusImStatusSignalStopSuccess OBJECT-TYPE
    SYNTAX          Counter
    ACCESS          read-only
    STATUS          mandatory
    DESCRIPTION     
            " The number of successful Signal Stop messages sent on the active call data channel."
    ::= { sonusImStatusEntry 25 }

sonusImStatusSignalStopUnsuccess OBJECT-TYPE
    SYNTAX          Counter
    ACCESS          read-only
    STATUS          mandatory
    DESCRIPTION     
            " The number of unsuccessful Signal Stop messages sent on the active call data channel."
    ::= { sonusImStatusEntry 26 }

sonusInterceptManagerMIBNotifications OBJECT IDENTIFIER
    ::= { sonusInterceptManagerMIB 2 }

sonusInterceptManagerMIBNotificationsPrefix OBJECT IDENTIFIER
    ::= { sonusInterceptManagerMIBNotifications 0 }

sonusInterceptManagerMIBNotificationsObjects OBJECT IDENTIFIER
    ::= { sonusInterceptManagerMIBNotifications 1 }

sonusImPriOperStateChange TRAP-TYPE
    ENTERPRISE      sonusInterceptManagerMIBNotifications
    VARIABLES       { sonusImAdmnName, sonusImStatusPriOperState, 
                      sonusEventDescription, sonusEventClass, 
                      sonusEventLevel, sonusSequenceId, sonusEventTime }
--     STATUS          mandatory
    DESCRIPTION     
            "This trap indicates the intercept manager primary operational state has changed."
    ::= 1

sonusImSecOperStateChange TRAP-TYPE
    ENTERPRISE      sonusInterceptManagerMIBNotifications
    VARIABLES       { sonusImAdmnName, sonusImStatusSecOperState, 
                      sonusEventDescription, sonusEventClass, 
                      sonusEventLevel, sonusSequenceId, sonusEventTime }
--     STATUS          mandatory
    DESCRIPTION     
            "This trap indicates the intercept manager secondary operational state has changed."
    ::= 2

END -- end of module SONUS-INTERCEPT-MANAGER-MIB.
