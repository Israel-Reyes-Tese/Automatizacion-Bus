--
-- This SMIv1 module has been generated by smidump 0.2-cvs. Do not edit.
--

CONNEXIP-TRAPS-MIB DEFINITIONS ::= BEGIN

IMPORTS
    OBJECT-TYPE
        FROM RFC-1212
    TRAP-TYPE
        FROM RFC-1215
    DisplayString
        FROM SNMPv2-TC
    sonusAlarmDescription, sonusAlarmLevel, sonusAlarmNodeID, 
    sonusAlarmSequenceId, sonusAlarmTime, sonusServerID
        FROM SONUS-COMMON-TRAP-MIB
    sonusCspsNotificationMIBs
        FROM SONUS-SMI;

sonusConnexIpTrapsMIB OBJECT IDENTIFIER
    ::= { sonusCspsNotificationMIBs 4 }

-- sonusConnexIpTrapsMIB MODULE-IDENTITY
--     LAST-UPDATED    "200807110000Z"
--     ORGANIZATION    
--             "Sonus Networks, Inc."
--     CONTACT-INFO    
--             "   Customer Support    
--              Sonus Networks, Inc.
--              4 Technology Park Drive
--              Westford, MA 01886
--              USA
--              
--              Tel: 978-614-8100
--              Fax: 978-614-8609"
--     DESCRIPTION     
--             "The MIB Module for ConnexIp Traps."
--     REVISION        "200807110000Z"
--     DESCRIPTION     
--             "Last revision."
--     ::= { sonusCspsNotificationMIBs 4 }


sonusConnexIpTraps OBJECT IDENTIFIER
    ::= { sonusConnexIpTrapsMIB 1 }

sonusConnexIpSystemServicesMIBNotifications OBJECT IDENTIFIER
    ::= { sonusConnexIpTraps 1 }

sonusConnexIpSystemServicesMIBNotificationsPrefix OBJECT IDENTIFIER
    ::= { sonusConnexIpSystemServicesMIBNotifications 0 }

sonusConnexIpSystemServicesMIBNotificationsObjects OBJECT IDENTIFIER
    ::= { sonusConnexIpSystemServicesMIBNotifications 1 }

sonusConnexIpSystemServerName OBJECT-TYPE
    SYNTAX          DisplayString
    ACCESS          read-only
    STATUS          mandatory
    DESCRIPTION     
            "
             The unique identifier assigned to this card or server.
             "
    ::= { sonusConnexIpSystemServicesMIBNotificationsObjects 1 }

sonusConnexIpSystemPowerSupplyId OBJECT-TYPE
    SYNTAX          DisplayString
    ACCESS          read-only
    STATUS          mandatory
    DESCRIPTION     
            "
             The name of the power supply (/SYS/VPS)
             "
    ::= { sonusConnexIpSystemServicesMIBNotificationsObjects 2 }

sonusConnexIpSystemFanId OBJECT-TYPE
    SYNTAX          DisplayString
    ACCESS          read-only
    STATUS          mandatory
    DESCRIPTION     
            "
             The name of the fan (usually /FT0/F0/ /FT0/F1/ etc).
             
             "
    ::= { sonusConnexIpSystemServicesMIBNotificationsObjects 3 }

sonusConnexIpSystemFanSpeed OBJECT-TYPE
    SYNTAX          INTEGER
    ACCESS          read-only
    STATUS          mandatory
    DESCRIPTION     
            "
             Fan speed (in rpm)
             "
    ::= { sonusConnexIpSystemServicesMIBNotificationsObjects 4 }

sonusConnexIpSystemAdminName OBJECT-TYPE
    SYNTAX          DisplayString
    ACCESS          read-only
    STATUS          mandatory
    DESCRIPTION     
            "
             Name of the system
             "
    ::= { sonusConnexIpSystemServicesMIBNotificationsObjects 5 }

sonusConnexIpSlotNum OBJECT-TYPE
    SYNTAX          INTEGER
    ACCESS          read-only
    STATUS          mandatory
    DESCRIPTION     
            "
             Slot number
             "
    ::= { sonusConnexIpSystemServicesMIBNotificationsObjects 6 }

sonusConnexIpCardType OBJECT-TYPE
    SYNTAX          DisplayString
    ACCESS          read-only
    STATUS          mandatory
    DESCRIPTION     
            "
             Card type
             "
    ::= { sonusConnexIpSystemServicesMIBNotificationsObjects 7 }

sonusConnexIpCardAdminState OBJECT-TYPE
    SYNTAX          INTEGER { disabled(1), enabled(2) }
    ACCESS          read-only
    STATUS          mandatory
    DESCRIPTION     
            "
             Admin state of the card
             		"
    ::= { sonusConnexIpSystemServicesMIBNotificationsObjects 8 }

sonusConnexIpCleanupType OBJECT-TYPE
    SYNTAX          INTEGER { graceful(1), forced(2) }
    ACCESS          read-only
    STATUS          mandatory
    DESCRIPTION     
            "
             Cleanup type on disabling a slot
             		"
    ::= { sonusConnexIpSystemServicesMIBNotificationsObjects 9 }

sonusConnexIpDryupTime OBJECT-TYPE
    SYNTAX          INTEGER
    ACCESS          read-only
    STATUS          mandatory
    DESCRIPTION     
            "
             Dryup time allowed on disabling a slot
             		"
    ::= { sonusConnexIpSystemServicesMIBNotificationsObjects 10 }

sonusConnexIpSystemCEPowerSupplyFailureNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemPowerSupplyId }
--     STATUS          mandatory
    DESCRIPTION     
            "This trap indicates that a power supply of the server failed."
    ::= 1

sonusConnexIpSystemCEPowerSupplyNormalNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemPowerSupplyId }
--     STATUS          mandatory
    DESCRIPTION     
            "This trap indicates that a power supply of the server is normal."
    ::= 2

sonusConnexIpSystemCEPowerSupplyUnitRemovedNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemPowerSupplyId }
--     STATUS          mandatory
    DESCRIPTION     
            "This trap indicates that a power supply unit of the server is removed."
    ::= 3

sonusConnexIpSystemCEPowerSupplyUnitInsertedNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemPowerSupplyId }
--     STATUS          mandatory
    DESCRIPTION     
            "This trap indicates that a power supply unit of the server is inserted."
    ::= 4

sonusConnexIpSystemCEFanNormalNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemFanId, 
                      sonusConnexIpSystemFanSpeed }
--     STATUS          mandatory
    DESCRIPTION     
            "This trap indicates that a fan of the server is operating normal."
    ::= 5

sonusConnexIpSystemCEFanFailureNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemFanId, 
                      sonusConnexIpSystemFanSpeed }
--     STATUS          mandatory
    DESCRIPTION     
            "This trap indicates that a fan of the server is failed."
    ::= 6

sonusConnexIpSystemCEFanAbsentNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemFanId }
--     STATUS          mandatory
    DESCRIPTION     
            "This trap indicates that a fan of the server is removed (absent)."
    ::= 7

sonusConnexIpSystemCEFanPresentNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName, 
                      sonusConnexIpSystemFanId }
--     STATUS          mandatory
    DESCRIPTION     
            "This trap indicates that a fan of the server is inserted (present)."
    ::= 8

sonusConnexIpSystemCEMultipleFanAbsentNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName }
--     STATUS          mandatory
    DESCRIPTION     
            "This trap indicates that two or more fans of the server are removed (absent)."
    ::= 9

sonusConnexIpSystemCEMultipleFanPresentNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemAdminName, 
                      sonusConnexIpSystemServerName }
--     STATUS          mandatory
    DESCRIPTION     
            "This trap indicates that at least two fans of the server are present."
    ::= 10

sonusConnexIpSystemCECardInsertedNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum, sonusConnexIpCardType, 
                      sonusConnexIpCardAdminState }
--     STATUS          mandatory
    DESCRIPTION     
            "This trap indicates that a card is inserted into a specified slot on the server."
    ::= 11

sonusConnexIpSystemCECardRemovedNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum, sonusConnexIpCardType, 
                      sonusConnexIpCardAdminState }
--     STATUS          mandatory
    DESCRIPTION     
            "This trap indicates that a card is removed from a specified slot on the server."
    ::= 12

sonusConnexIpSystemCESlotEnabledNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum, sonusConnexIpCardType }
--     STATUS          mandatory
    DESCRIPTION     
            "This trap indicates that a specified slot on the server is enabled."
    ::= 13

sonusConnexIpSystemCESlotDisabledNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum, sonusConnexIpCardType, 
                      sonusConnexIpCleanupType, sonusConnexIpDryupTime }
--     STATUS          mandatory
    DESCRIPTION     
            "This trap indicates that a specified slot on the server is disabled."
    ::= 14

sonusConnexIpSystemCESlotDryupNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum, sonusConnexIpCardType }
--     STATUS          mandatory
    DESCRIPTION     
            "This trap indicates that a specified slot on the server is going to dryup mode."
    ::= 15

sonusConnexIpSystemCESlotMismatchNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum }
--     STATUS          mandatory
    DESCRIPTION     
            "This trap indicates that a specified slot on the server is mismatched with peer server."
    ::= 16

sonusConnexIpSystemCESlotMismatchClearNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum }
--     STATUS          mandatory
    DESCRIPTION     
            "This trap indicates that a specified slot on the server mismatch with peer server is cleared ."
    ::= 17

sonusConnexIpSystemCESlotLockNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum }
--     STATUS          mandatory
    DESCRIPTION     
            "This trap indicates that a specified slot on the server is locked due to mismatch with peer server, system admin dspMismatchAction set to preserve redunndancy."
    ::= 18

sonusConnexIpSystemCESlotLockClearNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum }
--     STATUS          mandatory
    DESCRIPTION     
            "This trap indicates that a specified slot on the server lockout is cleared."
    ::= 19

sonusConnexIpSystemCESlotFailedNotification TRAP-TYPE
    ENTERPRISE      sonusConnexIpSystemServicesMIBNotifications
    VARIABLES       { sonusAlarmNodeID, sonusAlarmLevel, 
                      sonusAlarmSequenceId, sonusAlarmTime, 
                      sonusAlarmDescription, 
                      sonusConnexIpSystemServerName, 
                      sonusConnexIpSlotNum }
--     STATUS          mandatory
    DESCRIPTION     
            "This trap indicates that a specified slot on the server load/boot failed on 3 or more consecutive attempts. Module should be disabled, replaced and re-enabled in order to be returned to service."
    ::= 20

END -- end of module CONNEXIP-TRAPS-MIB.
