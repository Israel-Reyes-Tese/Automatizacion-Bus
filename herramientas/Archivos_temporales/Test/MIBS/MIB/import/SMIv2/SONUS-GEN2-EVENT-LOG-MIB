--
-- This SMIv2 module has been generated by smidump 0.2-cvs. Do not edit.
--

SONUS-GEN2-EVENT-LOG-MIB DEFINITIONS ::= BEGIN

IMPORTS
    Ipv6Address
        FROM IPV6-TC
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusGen2EventLogMIB MODULE-IDENTITY
    LAST-UPDATED    "201212310000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for Event Log Management."
    REVISION        "201212310000Z"
    DESCRIPTION     
            "Auto generated MIB."
    ::= { sonusCommonSoftwarePlatformServicesMIBs 3 }


UnsignedShort ::= TEXTUAL-CONVENTION
    DISPLAY-HINT    "d"
    STATUS          current
    DESCRIPTION     
            "xs:unsignedShort"
    SYNTAX          Unsigned32 (0..65535)

String ::= TEXTUAL-CONVENTION
    DISPLAY-HINT    "1t"
    STATUS          current
    DESCRIPTION     
            "xs:string"
    SYNTAX          OCTET STRING

SonusProcMsgRole ::= TEXTUAL-CONVENTION
    STATUS          current
    DESCRIPTION     
            "
             This data type is used to specify the primary or standby for process wide commands.
             "
    SYNTAX          INTEGER { active(0), standby(1) }

SonusEvLogShutdownReason ::= TEXTUAL-CONVENTION
    STATUS          current
    DESCRIPTION     
            "
             The reason why a log was shutdown
             "
    SYNTAX          INTEGER { writeFileFailure(1), nfsError(2), 
                        createDirFailure(3), maxFilecountReached(4), 
                        removeFileFailure(5), openFileFailure(6), 
                        writeHeaderFailure(7), memAllocFailure(8), 
                        adminShutdown(9), localDiskUnavailable(10) }

CompressionBlockSizeType ::= TEXTUAL-CONVENTION
    STATUS          current
    DESCRIPTION     
            "Enter a value in the range (2..128)"
    SYNTAX          Integer32 (2..128)

SonusEvLogConfdDebugType ::= TEXTUAL-CONVENTION
    STATUS          current
    DESCRIPTION     
            ""
    SYNTAX          INTEGER { silent(0), debug(1), trace(2) }

SonusEvLogTypeFileMsgQueueType ::= TEXTUAL-CONVENTION
    STATUS          current
    DESCRIPTION     
            "
             Enter a value between in the range (2..100)
             "
    SYNTAX          Integer32 (2..100)

MemusageMode ::= TEXTUAL-CONVENTION
    STATUS          current
    DESCRIPTION     
            "
             The level of process memory usage logging.
             "
    SYNTAX          INTEGER { none(0), summary(1), detailed(2) }

SonusEvLogRolloverIntervalType ::= TEXTUAL-CONVENTION
    STATUS          current
    DESCRIPTION     
            "
             Enter the number of seconds(15 .. 31536000)
             "
    SYNTAX          Integer32 (0..31536000)

SonusEvLogTypeStatusTypeType ::= TEXTUAL-CONVENTION
    STATUS          current
    DESCRIPTION     
            ""
    SYNTAX          INTEGER { system(1), debug(2), trace(3), acct(4), 
                        security(5), audit(6), packet(7), memusage(8) }

SonusEvLogTypeFileWriteModeType ::= TEXTUAL-CONVENTION
    STATUS          current
    DESCRIPTION     
            ""
    SYNTAX          INTEGER { default(1), optimize(2) }

CompressionCleanupDirType ::= TEXTUAL-CONVENTION
    DISPLAY-HINT    "1t"
    STATUS          current
    DESCRIPTION     
            "
             This data type is used to store filenames
             "
    SYNTAX          OCTET STRING (SIZE(0..255))

SonusEvLogOpenclovisDebugType ::= TEXTUAL-CONVENTION
    STATUS          current
    DESCRIPTION     
            "
             The Openclovis log levels.
             "
    SYNTAX          INTEGER { trace(0), debug(1), info(2), notice(3), 
                        warning(4), error(5), critical(6) }

CompressionDaysToKeepType ::= TEXTUAL-CONVENTION
    STATUS          current
    DESCRIPTION     
            "Enter a value in the range (1..7)"
    SYNTAX          Integer32 (1..7)

SonusEvLogFilterTypeType ::= TEXTUAL-CONVENTION
    STATUS          current
    DESCRIPTION     
            ""
    SYNTAX          INTEGER { system(1), debug(2), trace(3), security(4), 
                        audit(5), memusage(6) }

SonusEvLogTypeSaveToType ::= TEXTUAL-CONVENTION
    STATUS          current
    DESCRIPTION     
            ""
    SYNTAX          INTEGER { none(0), disk(1) }

SonusSyslogServerHostNameType ::= TEXTUAL-CONVENTION
    DISPLAY-HINT    "1t"
    STATUS          current
    DESCRIPTION     
            ""
    SYNTAX          OCTET STRING (SIZE(0..255))

SubsystemIdType ::= TEXTUAL-CONVENTION
    STATUS          current
    DESCRIPTION     
            "
             An INTEGER representing the sub-system identifiers for
             software components in Hornet/Bluejay/Orca.
             "
    SYNTAX          INTEGER { nrs(3), fm(4), sm(5), sma(6), nrm(7), 
                        nrma(8), brm(9), drm(10), xrm(12), cc(13), 
                        ds(17), trm(19), gwfe(21), gwsg(22), cam(37), 
                        mgsg(39), enm(47), arm(49), rtm(50), h323sg(60), 
                        h323fe(61), sipsg(62), sipfe(63), dnsc(64), 
                        sec(75), ipm(80), im(81), cpx(84), chm(85), 
                        nim(89), pathchk(99), debug(105), diamc(106), 
                        lvm(107), h248fe(108), ipacl(109), ike(110), 
                        pipe(111), pes(113), ssa(114), scpa(115), 
                        ema(116), dbl(117), enmalarmmgr(118) }

SonusEvLogSubsysEventCategory ::= TEXTUAL-CONVENTION
    STATUS          current
    DESCRIPTION     
            ""
    SYNTAX          BITS { c0(0), c1(1), c2(2), c3(3), c4(4), c5(5), 
                        c6(6), c7(7) }

EventClassType ::= TEXTUAL-CONVENTION
    STATUS          current
    DESCRIPTION     
            "
             The categories of which events are classified by.
             "
    SYNTAX          INTEGER { sysmgmt(1), callproc(2), resmgmt(3), 
                        directory(4), netmgmt(5), signaling(6), 
                        routing(7), trace(8), security(9), policy(10), 
                        audit(11), memusage(12) }

DataAgentConnectionStatusType ::= TEXTUAL-CONVENTION
    STATUS          current
    DESCRIPTION     
            "
             "
    SYNTAX          INTEGER { unconnected(0), connected(1) }

DataAgentTypeType ::= TEXTUAL-CONVENTION
    STATUS          current
    DESCRIPTION     
            "
             "
    SYNTAX          INTEGER { platform(0), application(1), trace(2) }

SonusEvLogFilterStateType ::= TEXTUAL-CONVENTION
    STATUS          current
    DESCRIPTION     
            ""
    SYNTAX          INTEGER { off(1), on(2) }

SonusEvLogMemTypeType ::= TEXTUAL-CONVENTION
    STATUS          current
    DESCRIPTION     
            ""
    SYNTAX          INTEGER { system(1), debug(2), trace(3), acct(4), 
                        security(5), audit(6), packet(7), memusage(8) }

SonusEvLogTypeFileSizeType ::= TEXTUAL-CONVENTION
    STATUS          current
    DESCRIPTION     
            "
             Enter a value between in the range (256..65535) KB
             "
    SYNTAX          Integer32 (256..65535)

SonusEvLogTypeMaxEventMemSizeType ::= TEXTUAL-CONVENTION
    STATUS          current
    DESCRIPTION     
            "
             Enter a value between in the range (1..64)
             "
    SYNTAX          Integer32 (1..64)

EventFormatString ::= TEXTUAL-CONVENTION
    DISPLAY-HINT    "1t"
    STATUS          current
    DESCRIPTION     
            ""
    SYNTAX          OCTET STRING (SIZE(0..1023))

SonusEvLogSyslogFacility ::= TEXTUAL-CONVENTION
    STATUS          current
    DESCRIPTION     
            "
             The facility used for logging message to the linux syslog
             "
    SYNTAX          INTEGER { user(1), daemon(3), authpriv(10), 
                        local0(16), local1(17), local2(18), local3(19), 
                        local4(20), local5(21), local6(22), local7(23) }

CompressionLevelType ::= TEXTUAL-CONVENTION
    STATUS          current
    DESCRIPTION     
            "Enter a value in the range (1..9)"
    SYNTAX          Integer32 (1..9)

InfoLevelLoggingState ::= TEXTUAL-CONVENTION
    STATUS          current
    DESCRIPTION     
            "
             "
    SYNTAX          INTEGER { false(0), true(1) }

SonusEvLogTypeRolloverTypeType ::= TEXTUAL-CONVENTION
    STATUS          current
    DESCRIPTION     
            ""
    SYNTAX          INTEGER { repetitive(1), nonrepetitive(2) }

SonusServerNo ::= TEXTUAL-CONVENTION
    STATUS          current
    DESCRIPTION     
            ""
    SYNTAX          INTEGER { server1(1), server2(2), server3(3) }

SonusEvLogTypeAdminStateType ::= TEXTUAL-CONVENTION
    STATUS          current
    DESCRIPTION     
            ""
    SYNTAX          INTEGER { disabled(1), enabled(2), rollfile(3) }

SonusEvLogTypeStatusLogDestinationType ::= TEXTUAL-CONVENTION
    STATUS          current
    DESCRIPTION     
            ""
    SYNTAX          INTEGER { nfsServer(1), localDisk(2), 
                        streamServer(3) }

SonusEvLogTypeType ::= TEXTUAL-CONVENTION
    STATUS          current
    DESCRIPTION     
            ""
    SYNTAX          INTEGER { system(1), debug(2), trace(3), acct(4), 
                        security(5), audit(6), packet(7), memusage(8) }

SonusEvLogSubsysMinEventIdType ::= TEXTUAL-CONVENTION
    STATUS          current
    DESCRIPTION     
            ""
    SYNTAX          Unsigned32

SonusEvLogTypeFileCountType ::= TEXTUAL-CONVENTION
    STATUS          current
    DESCRIPTION     
            "
             Enter a value between in the range (1..2048)
             "
    SYNTAX          Integer32 (1..2048)

SonusEvLogTypeSyslogStateType ::= TEXTUAL-CONVENTION
    STATUS          current
    DESCRIPTION     
            ""
    SYNTAX          INTEGER { disabled(1), enabled(2) }

SyslogRemoteProtocolType ::= TEXTUAL-CONVENTION
    STATUS          current
    DESCRIPTION     
            ""
    SYNTAX          INTEGER { udp(1), tcp(2), relp(3), tls-tcp(4) }

CompressionSupportType ::= TEXTUAL-CONVENTION
    STATUS          current
    DESCRIPTION     
            "
             The type of compression to be used
             "
    SYNTAX          INTEGER { none(1), only(2), both(3) }

SonusEvLogFilterStatusTypeType ::= TEXTUAL-CONVENTION
    STATUS          current
    DESCRIPTION     
            ""
    SYNTAX          INTEGER { system(1), debug(2), trace(3), security(4), 
                        audit(6), memusage(8) }

SonusEvLogSubsysMaxEventIdType ::= TEXTUAL-CONVENTION
    STATUS          current
    DESCRIPTION     
            ""
    SYNTAX          Unsigned32

SonusEvLogTypeDiskType ::= TEXTUAL-CONVENTION
    STATUS          current
    DESCRIPTION     
            ""
    SYNTAX          INTEGER { nfsServer(1), localDisk(2) }

SonusEvLogTypeRolloverActionType ::= TEXTUAL-CONVENTION
    STATUS          current
    DESCRIPTION     
            ""
    SYNTAX          INTEGER { start(1), stop(2) }

SonusProcInstance ::= TEXTUAL-CONVENTION
    STATUS          current
    DESCRIPTION     
            ""
    SYNTAX          Integer32 (-1..7)

SonusEvLogStatusType ::= TEXTUAL-CONVENTION
    STATUS          current
    DESCRIPTION     
            "
             "
    SYNTAX          INTEGER { up(0), down(1) }

SonusEvLogSubsysEventCategoryType ::= TEXTUAL-CONVENTION
    STATUS          current
    DESCRIPTION     
            ""
    SYNTAX          BITS { c0(0), c1(1), c2(2), c3(3), c4(4), c5(5), 
                        c6(6), c7(7) }

SonusSyslogClassType ::= TEXTUAL-CONVENTION
    STATUS          current
    DESCRIPTION     
            "
             The class of log type entries to be enabled
             "
    SYNTAX          INTEGER { eventlog(1) }

LogIndex ::= TEXTUAL-CONVENTION
    STATUS          current
    DESCRIPTION     
            "
             The index for a Sonus event log.
             "
    SYNTAX          Unsigned32

sonusEventLog OBJECT IDENTIFIER
    ::= { sonusGen2EventLogMIB 1 }

sonusEventLogConfd OBJECT IDENTIFIER
    ::= { sonusEventLog 1 }

sonusEventLogConfdDebugLevel OBJECT-TYPE
    SYNTAX          SonusEvLogConfdDebugType
    MAX-ACCESS      read-only
    STATUS          obsolete
    DESCRIPTION     
            "
             Current debug level for ConfD components.
             "
    ::= { sonusEventLog 2 }

sonusEventLogConfdNbiWriteAccessState OBJECT-TYPE
    SYNTAX          INTEGER { disabled(1), enabled(2) }
    MAX-ACCESS      read-only
    STATUS          obsolete
    DESCRIPTION     
            "
             Current debug level for ConfD components.
             "
    ::= { sonusEventLog 3 }

sonusEventLogProcess OBJECT IDENTIFIER
    ::= { sonusEventLog 4 }

sonusEventLogTypeAdminTable OBJECT-TYPE
    SYNTAX          SEQUENCE OF SonusEventLogTypeAdminEntry
    MAX-ACCESS      not-accessible
    STATUS          current
    DESCRIPTION     
            "
             Event Log configuration table for configuration items
             related to each Event Log type.
             "
    ::= { sonusEventLog 5 }

sonusEventLogTypeAdminEntry OBJECT-TYPE
    SYNTAX          SonusEventLogTypeAdminEntry
    MAX-ACCESS      not-accessible
    STATUS          current
    DESCRIPTION     
            ""
    INDEX           { sonusEventLogTypeAdminType }
    ::= { sonusEventLogTypeAdminTable 1 }

SonusEventLogTypeAdminEntry ::=
    SEQUENCE {
        sonusEventLogTypeAdminType      SonusEvLogTypeType,
        sonusEventLogTypeAdminState     SonusEvLogTypeAdminStateType,
        sonusEventLogTypeAdminFileCount SonusEvLogTypeFileCountType,
        sonusEventLogTypeAdminFileSize  SonusEvLogTypeFileSizeType,
        sonusEventLogTypeAdminMessageQueueSize      SonusEvLogTypeFileMsgQueueType,
        sonusEventLogTypeAdminSaveTo    SonusEvLogTypeSaveToType,
        sonusEventLogTypeAdminMaxEventMemorySize        SonusEvLogTypeMaxEventMemSizeType,
        sonusEventLogTypeAdminFilterLevel INTEGER,
        sonusEventLogTypeAdminRolloverStartTime       DateAndTime,
        sonusEventLogTypeAdminRolloverInterval      SonusEvLogRolloverIntervalType,
        sonusEventLogTypeAdminRolloverType  SonusEvLogTypeRolloverTypeType,
        sonusEventLogTypeAdminRolloverAction    SonusEvLogTypeRolloverActionType,
        sonusEventLogTypeAdminFileWriteMode   SonusEvLogTypeFileWriteModeType,
        sonusEventLogTypeAdminSyslogState SonusEvLogTypeSyslogStateType,
        sonusEventLogTypeAdminSyslogRemoteHost      String,
        sonusEventLogTypeAdminSyslogRemoteProtocol          SyslogRemoteProtocolType,
        sonusEventLogTypeAdminSyslogRemotePort      UnsignedShort,
        sonusEventLogTypeAdminRenameOpenFiles     INTEGER,
        sonusEventLogTypeAdminDiskThrottleLimit       Unsigned32,
        sonusEventLogTypeAdminRowstatus RowStatus
    }

sonusEventLogTypeAdminType OBJECT-TYPE
    SYNTAX          SonusEvLogTypeType
    MAX-ACCESS      not-accessible
    STATUS          current
    DESCRIPTION     
            "
             The type of the event log.  Each type has separate
             configuration parameters and logs to a separate file.
             "
    ::= { sonusEventLogTypeAdminEntry 1 }

sonusEventLogTypeAdminState OBJECT-TYPE
    SYNTAX          SonusEvLogTypeAdminStateType
    MAX-ACCESS      read-create
    STATUS          current
    DESCRIPTION     
            "
             The requested state of the given Event Log type.
             "
    DEFVAL          { enabled }
    ::= { sonusEventLogTypeAdminEntry 2 }

sonusEventLogTypeAdminFileCount OBJECT-TYPE
    SYNTAX          SonusEvLogTypeFileCountType
    MAX-ACCESS      read-create
    STATUS          current
    DESCRIPTION     
            "
             The number of event log files that will be maintained
             for this event type.  All event types
             will overwrite the oldest file when the file count is
             exceeded.  A warning will be issued when the
             count approaches the maximum.
             "
    DEFVAL          { 32 }
    ::= { sonusEventLogTypeAdminEntry 3 }

sonusEventLogTypeAdminFileSize OBJECT-TYPE
    SYNTAX          SonusEvLogTypeFileSizeType
    MAX-ACCESS      read-create
    STATUS          current
    DESCRIPTION     
            "
             The maximum size (in KB) that a single event log
             file will ever grow to.
             "
    DEFVAL          { 2048 }
    ::= { sonusEventLogTypeAdminEntry 4 }

sonusEventLogTypeAdminMessageQueueSize OBJECT-TYPE
    SYNTAX          SonusEvLogTypeFileMsgQueueType
    MAX-ACCESS      read-create
    STATUS          current
    DESCRIPTION     
            "
             The number of event log message entries to buffer
             before writing them to disk.
             
             The size may be a value between 2 and 100 (inclusive).
             "
    DEFVAL          { 10 }
    ::= { sonusEventLogTypeAdminEntry 5 }

sonusEventLogTypeAdminSaveTo OBJECT-TYPE
    SYNTAX          SonusEvLogTypeSaveToType
    MAX-ACCESS      read-create
    STATUS          current
    DESCRIPTION     
            "
             Save events to disk or none.
             "
    DEFVAL          { disk }
    ::= { sonusEventLogTypeAdminEntry 6 }

sonusEventLogTypeAdminMaxEventMemorySize OBJECT-TYPE
    SYNTAX          SonusEvLogTypeMaxEventMemSizeType
    MAX-ACCESS      read-create
    STATUS          obsolete
    DESCRIPTION     
            "
             The maximum size of the memory event log buffer
             (in KB).
             "
    DEFVAL          { 16 }
    ::= { sonusEventLogTypeAdminEntry 7 }

sonusEventLogTypeAdminFilterLevel OBJECT-TYPE
    SYNTAX          INTEGER { noevents(0), critical(1), major(2), 
                        minor(3), info(4) }
    MAX-ACCESS      read-create
    STATUS          current
    DESCRIPTION     
            "
             Events that are at least as severe as the designated
             level will be logged. noevents suppresses all events
             of this type from being logged.
             "
    ::= { sonusEventLogTypeAdminEntry 8 }

sonusEventLogTypeAdminRolloverStartTime OBJECT-TYPE
    SYNTAX          DateAndTime
    MAX-ACCESS      read-create
    STATUS          current
    DESCRIPTION     
            "
             The start time for event log rollover.
             "
    ::= { sonusEventLogTypeAdminEntry 9 }

sonusEventLogTypeAdminRolloverInterval OBJECT-TYPE
    SYNTAX          SonusEvLogRolloverIntervalType
    MAX-ACCESS      read-create
    STATUS          current
    DESCRIPTION     
            "
             The event log rollover interval.
             "
    DEFVAL          { 0 }
    ::= { sonusEventLogTypeAdminEntry 10 }

sonusEventLogTypeAdminRolloverType OBJECT-TYPE
    SYNTAX          SonusEvLogTypeRolloverTypeType
    MAX-ACCESS      read-create
    STATUS          current
    DESCRIPTION     
            "
             The event log rollover type. Repetitive type will
             rollover logs continuosly after rollover Interval.
             "
    DEFVAL          { nonrepetitive }
    ::= { sonusEventLogTypeAdminEntry 11 }

sonusEventLogTypeAdminRolloverAction OBJECT-TYPE
    SYNTAX          SonusEvLogTypeRolloverActionType
    MAX-ACCESS      read-create
    STATUS          current
    DESCRIPTION     
            "
             Event log rollover actions.
             start - Start event log rollover at specified starting time.
             stop  - Stop event log rollover.
             "
    DEFVAL          { stop }
    ::= { sonusEventLogTypeAdminEntry 12 }

sonusEventLogTypeAdminFileWriteMode OBJECT-TYPE
    SYNTAX          SonusEvLogTypeFileWriteModeType
    MAX-ACCESS      read-create
    STATUS          current
    DESCRIPTION     
            "
             Identifies event log NFS write mode.
             1. DEFAULT  - Log data is written to NFS as 1344 byte packet.
             2. OPTIMIZE - Log data is written to NFS as 8000 byte packet.
             Optimize write mode results in IP fragmentation but yields better throughput.
             "
    DEFVAL          { default }
    ::= { sonusEventLogTypeAdminEntry 13 }

sonusEventLogTypeAdminSyslogState OBJECT-TYPE
    SYNTAX          SonusEvLogTypeSyslogStateType
    MAX-ACCESS      read-create
    STATUS          current
    DESCRIPTION     
            "
             Specifies whether the contents of this log are also written out to the syslog
             "
    DEFVAL          { disabled }
    ::= { sonusEventLogTypeAdminEntry 14 }

sonusEventLogTypeAdminSyslogRemoteHost OBJECT-TYPE
    SYNTAX          String (SIZE(0..255))
    MAX-ACCESS      read-create
    STATUS          deprecated
    DESCRIPTION     
            "
             Specifies the remote host where the messages are written to the syslog.
             This must be a valid IP address.
             "
    ::= { sonusEventLogTypeAdminEntry 15 }

sonusEventLogTypeAdminSyslogRemoteProtocol OBJECT-TYPE
    SYNTAX          SyslogRemoteProtocolType
    MAX-ACCESS      read-create
    STATUS          deprecated
    DESCRIPTION     
            "
             Specifies the protocol to use to send messages to the remote syslog.
             "
    DEFVAL          { tcp }
    ::= { sonusEventLogTypeAdminEntry 16 }

sonusEventLogTypeAdminSyslogRemotePort OBJECT-TYPE
    SYNTAX          UnsignedShort (1..65535)
    MAX-ACCESS      read-create
    STATUS          deprecated
    DESCRIPTION     
            "
             Specifies the port to use to send messages to the remote syslog.
             "
    ::= { sonusEventLogTypeAdminEntry 17 }

sonusEventLogTypeAdminRenameOpenFiles OBJECT-TYPE
    SYNTAX          INTEGER { disabled(1), enabled(2) }
    MAX-ACCESS      read-create
    STATUS          current
    DESCRIPTION     
            "
             Specifies whether to name open accounting, packet files with a .OPEN extension
             "
    ::= { sonusEventLogTypeAdminEntry 18 }

sonusEventLogTypeAdminDiskThrottleLimit OBJECT-TYPE
    SYNTAX          Unsigned32
    MAX-ACCESS      read-create
    STATUS          current
    DESCRIPTION     
            "
             Limit on info level messages logged to the disk in one second
             A value of 0 disables the limit
             "
    DEFVAL          { 10000 }
    ::= { sonusEventLogTypeAdminEntry 19 }

sonusEventLogTypeAdminRowstatus OBJECT-TYPE
    SYNTAX          RowStatus
    MAX-ACCESS      read-create
    STATUS          current
    DESCRIPTION     
            ""
    ::= { sonusEventLogTypeAdminEntry 20 }

sonusEventLogTypeStatusTable OBJECT-TYPE
    SYNTAX          SEQUENCE OF SonusEventLogTypeStatusEntry
    MAX-ACCESS      not-accessible
    STATUS          current
    DESCRIPTION     
            "
             Event Log status table for status items
             related to each Event Log type.
             "
    ::= { sonusEventLog 6 }

sonusEventLogTypeStatusEntry OBJECT-TYPE
    SYNTAX          SonusEventLogTypeStatusEntry
    MAX-ACCESS      not-accessible
    STATUS          current
    DESCRIPTION     
            ""
    INDEX           { sonusEventLogTypeStatusType }
    ::= { sonusEventLogTypeStatusTable 1 }

SonusEventLogTypeStatusEntry ::=
    SEQUENCE {
        sonusEventLogTypeStatusType     SonusEvLogTypeStatusTypeType,
        sonusEventLogTypeStatusCurrentFile  String,
        sonusEventLogTypeStatusFileRecords  Unsigned32,
        sonusEventLogTypeStatusFileBytes Unsigned32,
        sonusEventLogTypeStatusTotalFiles Unsigned32,
        sonusEventLogTypeStatusTotalFileBytes     Counter64,
        sonusEventLogTypeStatusMemoryRecords    Unsigned32,
        sonusEventLogTypeStatusMemoryBytes  Unsigned32,
        sonusEventLogTypeStatusFilesDropped   Unsigned32,
        sonusEventLogTypeStatusMemoryDropped    Unsigned32,
        sonusEventLogTypeStatusNextRollover   Unsigned32,
        sonusEventLogTypeStatusLogDestination     SonusEvLogTypeStatusLogDestinationType,
        sonusEventLogTypeStatusLastFileDrop   DateAndTime,
        sonusEventLogTypeStatusLastMemoryDrop     DateAndTime,
        sonusEventLogTypeStatusInfoLevelLoggingDisabled               InfoLevelLoggingState
    }

sonusEventLogTypeStatusType OBJECT-TYPE
    SYNTAX          SonusEvLogTypeStatusTypeType
    MAX-ACCESS      not-accessible
    STATUS          current
    DESCRIPTION     
            "
             The type of the event log.  Each type has separate
             configuration parameters and logs to a separate file.
             "
    ::= { sonusEventLogTypeStatusEntry 1 }

sonusEventLogTypeStatusCurrentFile OBJECT-TYPE
    SYNTAX          String (SIZE(0..255))
    MAX-ACCESS      read-only
    STATUS          current
    DESCRIPTION     
            "
             The filename that is currently being used for logging.
             No name is displayed when disk logging is disabled. The
             name RECOVERING is displayed when an attempt to automatically
             restart disk logging is in progress.
             "
    ::= { sonusEventLogTypeStatusEntry 2 }

sonusEventLogTypeStatusFileRecords OBJECT-TYPE
    SYNTAX          Unsigned32
    MAX-ACCESS      read-only
    STATUS          current
    DESCRIPTION     
            "
             Count of the number of event records written to
             the current event log file.
             "
    ::= { sonusEventLogTypeStatusEntry 3 }

sonusEventLogTypeStatusFileBytes OBJECT-TYPE
    SYNTAX          Unsigned32
    MAX-ACCESS      read-only
    STATUS          current
    DESCRIPTION     
            "
             Count of the number of bytes written to
             the current event log file.
             "
    ::= { sonusEventLogTypeStatusEntry 4 }

sonusEventLogTypeStatusTotalFiles OBJECT-TYPE
    SYNTAX          Unsigned32
    MAX-ACCESS      read-only
    STATUS          current
    DESCRIPTION     
            "
             Count of the number of log files of this event type.
             "
    ::= { sonusEventLogTypeStatusEntry 5 }

sonusEventLogTypeStatusTotalFileBytes OBJECT-TYPE
    SYNTAX          Counter64
    MAX-ACCESS      read-only
    STATUS          current
    DESCRIPTION     
            "
             Count of the number of bytes written to
             the log files of this event type.
             "
    ::= { sonusEventLogTypeStatusEntry 6 }

sonusEventLogTypeStatusMemoryRecords OBJECT-TYPE
    SYNTAX          Unsigned32
    MAX-ACCESS      read-only
    STATUS          obsolete
    DESCRIPTION     
            "
             Count of the number of event records written to
             the event log memory buffer.
             "
    ::= { sonusEventLogTypeStatusEntry 7 }

sonusEventLogTypeStatusMemoryBytes OBJECT-TYPE
    SYNTAX          Unsigned32
    MAX-ACCESS      read-only
    STATUS          obsolete
    DESCRIPTION     
            "
             Count of the number of bytes written to
             the event log memory buffer.
             "
    ::= { sonusEventLogTypeStatusEntry 8 }

sonusEventLogTypeStatusFilesDropped OBJECT-TYPE
    SYNTAX          Unsigned32
    MAX-ACCESS      read-only
    STATUS          current
    DESCRIPTION     
            "
             Count of the number of event records dropped when writing
             to an Event Log file.
             "
    ::= { sonusEventLogTypeStatusEntry 9 }

sonusEventLogTypeStatusMemoryDropped OBJECT-TYPE
    SYNTAX          Unsigned32
    MAX-ACCESS      read-only
    STATUS          obsolete
    DESCRIPTION     
            "
             Count of the number of event records dropped when writing
             to an Event Log memory buffer.
             "
    ::= { sonusEventLogTypeStatusEntry 10 }

sonusEventLogTypeStatusNextRollover OBJECT-TYPE
    SYNTAX          Unsigned32
    MAX-ACCESS      read-only
    STATUS          current
    DESCRIPTION     
            "
             Time in minutes left before next rollover.
             "
    ::= { sonusEventLogTypeStatusEntry 11 }

sonusEventLogTypeStatusLogDestination OBJECT-TYPE
    SYNTAX          SonusEvLogTypeStatusLogDestinationType
    MAX-ACCESS      read-only
    STATUS          current
    DESCRIPTION     
            "
             Identifies the location where this Event Log type writes to.
             "
    ::= { sonusEventLogTypeStatusEntry 12 }

sonusEventLogTypeStatusLastFileDrop OBJECT-TYPE
    SYNTAX          DateAndTime
    MAX-ACCESS      read-only
    STATUS          current
    DESCRIPTION     
            "
             Time of the last event record dropped when writing
             to an Event Log file. The value will be zero length if
             no records have been dropped since last reboot.
             "
    ::= { sonusEventLogTypeStatusEntry 13 }

sonusEventLogTypeStatusLastMemoryDrop OBJECT-TYPE
    SYNTAX          DateAndTime
    MAX-ACCESS      read-only
    STATUS          obsolete
    DESCRIPTION     
            "
             Time of the last event record dropped when writing
             to an Event Log memory buffer. The value will be zero length if
             no records have been dropped since last reboot.
             "
    ::= { sonusEventLogTypeStatusEntry 14 }

sonusEventLogTypeStatusInfoLevelLoggingDisabled OBJECT-TYPE
    SYNTAX          InfoLevelLoggingState
    MAX-ACCESS      read-only
    STATUS          current
    DESCRIPTION     
            "
             if set to true, indicates that info level messages are being dropped
             because the system was once congested
             "
    ::= { sonusEventLogTypeStatusEntry 15 }

sonusEventLogMemoryStatusTable OBJECT-TYPE
    SYNTAX          SEQUENCE OF SonusEventLogMemoryStatusEntry
    MAX-ACCESS      not-accessible
    STATUS          obsolete
    DESCRIPTION     
            "
             Events logged to memory.
             "
    ::= { sonusEventLog 7 }

sonusEventLogMemoryStatusEntry OBJECT-TYPE
    SYNTAX          SonusEventLogMemoryStatusEntry
    MAX-ACCESS      not-accessible
    STATUS          obsolete
    DESCRIPTION     
            ""
    INDEX           { sonusEventLogMemoryStatusType, 
                      sonusEventLogMemoryStatusIndex }
    ::= { sonusEventLogMemoryStatusTable 1 }

SonusEventLogMemoryStatusEntry ::=
    SEQUENCE {
        sonusEventLogMemoryStatusType   SonusEvLogMemTypeType,
        sonusEventLogMemoryStatusIndex  LogIndex,
        sonusEventLogMemoryStatusText   EventFormatString
    }

sonusEventLogMemoryStatusType OBJECT-TYPE
    SYNTAX          SonusEvLogMemTypeType
    MAX-ACCESS      not-accessible
    STATUS          obsolete
    DESCRIPTION     
            "
             The Event Log Type to which these table entries
             apply.
             "
    ::= { sonusEventLogMemoryStatusEntry 1 }

sonusEventLogMemoryStatusIndex OBJECT-TYPE
    SYNTAX          LogIndex
    MAX-ACCESS      not-accessible
    STATUS          obsolete
    DESCRIPTION     
            "
             The index for the entry.
             "
    ::= { sonusEventLogMemoryStatusEntry 2 }

sonusEventLogMemoryStatusText OBJECT-TYPE
    SYNTAX          EventFormatString
    MAX-ACCESS      read-only
    STATUS          obsolete
    DESCRIPTION     
            "
             The event log text.  This object only contains the first 1023
             characters of the event.  The event log file will contain the
             entire event.
             "
    ::= { sonusEventLogMemoryStatusEntry 3 }

sonusEventLogSubsystemAdminTable OBJECT-TYPE
    SYNTAX          SEQUENCE OF SonusEventLogSubsystemAdminEntry
    MAX-ACCESS      not-accessible
    STATUS          deprecated
    DESCRIPTION     
            "
             Subsystem Event Logging configuration table.
             This table configures subsystems DO NOT filter events.
             "
    ::= { sonusEventLog 8 }

sonusEventLogSubsystemAdminEntry OBJECT-TYPE
    SYNTAX          SonusEventLogSubsystemAdminEntry
    MAX-ACCESS      not-accessible
    STATUS          deprecated
    DESCRIPTION     
            ""
    INDEX           { sonusEventLogSubsystemAdminCeName, 
                      sonusEventLogSubsystemAdminSystemId }
    ::= { sonusEventLogSubsystemAdminTable 1 }

SonusEventLogSubsystemAdminEntry ::=
    SEQUENCE {
        sonusEventLogSubsystemAdminCeName String,
        sonusEventLogSubsystemAdminSystemId   String,
        sonusEventLogSubsystemAdminInfoLogState       INTEGER,
        sonusEventLogSubsystemAdminMinEventId     SonusEvLogSubsysMinEventIdType,
        sonusEventLogSubsystemAdminMaxEventId     SonusEvLogSubsysMaxEventIdType,
        sonusEventLogSubsystemAdminRowstatus    RowStatus
    }

sonusEventLogSubsystemAdminCeName OBJECT-TYPE
    SYNTAX          String (SIZE(0..255))
    MAX-ACCESS      not-accessible
    STATUS          obsolete
    DESCRIPTION     
            "
             The host name which the subsystem event entries apply.
             "
    ::= { sonusEventLogSubsystemAdminEntry 1 }

sonusEventLogSubsystemAdminSystemId OBJECT-TYPE
    SYNTAX          String (SIZE(0..23))
    MAX-ACCESS      not-accessible
    STATUS          deprecated
    DESCRIPTION     
            "
             The subsystem/task ID for which the subsystem event entries apply.
             "
    ::= { sonusEventLogSubsystemAdminEntry 2 }

sonusEventLogSubsystemAdminInfoLogState OBJECT-TYPE
    SYNTAX          INTEGER { disabled(1), enabled(2) }
    MAX-ACCESS      read-create
    STATUS          deprecated
    DESCRIPTION     
            "
             The subsystem's INFO level event logging state. If this state is
             enabled, then subsystem INFO/MINOR events fall into specified
             range, sonusEvLogSubsystemMinEventId to sonusEvLogSubsystemMinEventId,
             will not be filtered.
             "
    ::= { sonusEventLogSubsystemAdminEntry 3 }

sonusEventLogSubsystemAdminMinEventId OBJECT-TYPE
    SYNTAX          SonusEvLogSubsysMinEventIdType
    MAX-ACCESS      read-create
    STATUS          deprecated
    DESCRIPTION     
            "
             The subsystem's minimun event ID that do not get filtered.
             "
    DEFVAL          { 0 }
    ::= { sonusEventLogSubsystemAdminEntry 4 }

sonusEventLogSubsystemAdminMaxEventId OBJECT-TYPE
    SYNTAX          SonusEvLogSubsysMaxEventIdType
    MAX-ACCESS      read-create
    STATUS          deprecated
    DESCRIPTION     
            "
             The subsystem's maxmum event ID that do not get filtered.
             "
    DEFVAL          { 2048 }
    ::= { sonusEventLogSubsystemAdminEntry 5 }

sonusEventLogSubsystemAdminRowstatus OBJECT-TYPE
    SYNTAX          RowStatus
    MAX-ACCESS      read-create
    STATUS          deprecated
    DESCRIPTION     
            ""
    ::= { sonusEventLogSubsystemAdminEntry 6 }

sonusEventLogSubsystemAdminSbxTable OBJECT-TYPE
    SYNTAX          SEQUENCE OF SonusEventLogSubsystemAdminSbxEntry
    MAX-ACCESS      not-accessible
    STATUS          deprecated
    DESCRIPTION     
            "
             Subsystem Event Logging configuration table.
             This table configures subsystems DO NOT filter events.
             "
    ::= { sonusEventLog 9 }

sonusEventLogSubsystemAdminSbxEntry OBJECT-TYPE
    SYNTAX          SonusEventLogSubsystemAdminSbxEntry
    MAX-ACCESS      not-accessible
    STATUS          deprecated
    DESCRIPTION     
            ""
    INDEX           { sonusEventLogSubsystemAdminSbxCeName, 
                      sonusEventLogSubsystemAdminSbxSystemId }
    ::= { sonusEventLogSubsystemAdminSbxTable 1 }

SonusEventLogSubsystemAdminSbxEntry ::=
    SEQUENCE {
        sonusEventLogSubsystemAdminSbxCeName    String,
        sonusEventLogSubsystemAdminSbxSystemId      String,
        sonusEventLogSubsystemAdminSbxInfoLogState          INTEGER,
        sonusEventLogSubsystemAdminSbxMinEventId        SonusEvLogSubsysMinEventIdType,
        sonusEventLogSubsystemAdminSbxMaxEventId        SonusEvLogSubsysMaxEventIdType,
        sonusEventLogSubsystemAdminSbxRowstatus       RowStatus
    }

sonusEventLogSubsystemAdminSbxCeName OBJECT-TYPE
    SYNTAX          String (SIZE(0..255))
    MAX-ACCESS      not-accessible
    STATUS          obsolete
    DESCRIPTION     
            "
             The host name which the subsystem event entries apply.
             "
    ::= { sonusEventLogSubsystemAdminSbxEntry 1 }

sonusEventLogSubsystemAdminSbxSystemId OBJECT-TYPE
    SYNTAX          String (SIZE(0..23))
    MAX-ACCESS      not-accessible
    STATUS          deprecated
    DESCRIPTION     
            "
             The subsystem/task ID for which the subsystem event entries apply.
             "
    ::= { sonusEventLogSubsystemAdminSbxEntry 2 }

sonusEventLogSubsystemAdminSbxInfoLogState OBJECT-TYPE
    SYNTAX          INTEGER { disabled(1), enabled(2) }
    MAX-ACCESS      read-create
    STATUS          deprecated
    DESCRIPTION     
            "
             The subsystem's INFO level event logging state. If this state is
             enabled, then subsystem INFO/MINOR events fall into specified
             range, sonusEvLogSubsystemMinEventId to sonusEvLogSubsystemMinEventId,
             will not be filtered.
             "
    ::= { sonusEventLogSubsystemAdminSbxEntry 3 }

sonusEventLogSubsystemAdminSbxMinEventId OBJECT-TYPE
    SYNTAX          SonusEvLogSubsysMinEventIdType
    MAX-ACCESS      read-create
    STATUS          deprecated
    DESCRIPTION     
            "
             The subsystem's minimun event ID that do not get filtered.
             "
    DEFVAL          { 0 }
    ::= { sonusEventLogSubsystemAdminSbxEntry 4 }

sonusEventLogSubsystemAdminSbxMaxEventId OBJECT-TYPE
    SYNTAX          SonusEvLogSubsysMaxEventIdType
    MAX-ACCESS      read-create
    STATUS          deprecated
    DESCRIPTION     
            "
             The subsystem's maxmum event ID that do not get filtered.
             "
    DEFVAL          { 2048 }
    ::= { sonusEventLogSubsystemAdminSbxEntry 5 }

sonusEventLogSubsystemAdminSbxRowstatus OBJECT-TYPE
    SYNTAX          RowStatus
    MAX-ACCESS      read-create
    STATUS          deprecated
    DESCRIPTION     
            ""
    ::= { sonusEventLogSubsystemAdminSbxEntry 6 }

sonusEventLogFilterAdminTable OBJECT-TYPE
    SYNTAX          SEQUENCE OF SonusEventLogFilterAdminEntry
    MAX-ACCESS      not-accessible
    STATUS          obsolete
    DESCRIPTION     
            "
             Event Log Class Filter configuration table per card.
             "
    ::= { sonusEventLog 10 }

sonusEventLogFilterAdminEntry OBJECT-TYPE
    SYNTAX          SonusEventLogFilterAdminEntry
    MAX-ACCESS      not-accessible
    STATUS          obsolete
    DESCRIPTION     
            ""
    INDEX           { sonusEventLogFilterAdminCeName, 
                      sonusEventLogFilterAdminType, 
                      sonusEventLogFilterAdminEventClass }
    ::= { sonusEventLogFilterAdminTable 1 }

SonusEventLogFilterAdminEntry ::=
    SEQUENCE {
        sonusEventLogFilterAdminCeName  String,
        sonusEventLogFilterAdminType    SonusEvLogFilterTypeType,
        sonusEventLogFilterAdminEventClass  EventClassType,
        sonusEventLogFilterAdminLevel   INTEGER,
        sonusEventLogFilterAdminState   SonusEvLogFilterStateType,
        sonusEventLogFilterAdminRowstatus RowStatus
    }

sonusEventLogFilterAdminCeName OBJECT-TYPE
    SYNTAX          String (SIZE(0..255))
    MAX-ACCESS      not-accessible
    STATUS          obsolete
    DESCRIPTION     
            "
             The host name for which these table entries apply.
             "
    ::= { sonusEventLogFilterAdminEntry 1 }

sonusEventLogFilterAdminType OBJECT-TYPE
    SYNTAX          SonusEvLogFilterTypeType
    MAX-ACCESS      not-accessible
    STATUS          obsolete
    DESCRIPTION     
            "
             The event log type for which these filter table entries
             apply.
             "
    ::= { sonusEventLogFilterAdminEntry 2 }

sonusEventLogFilterAdminEventClass OBJECT-TYPE
    SYNTAX          EventClassType
    MAX-ACCESS      not-accessible
    STATUS          obsolete
    DESCRIPTION     
            "
             The class of events to which the filter entry applies.
             "
    ::= { sonusEventLogFilterAdminEntry 3 }

sonusEventLogFilterAdminLevel OBJECT-TYPE
    SYNTAX          INTEGER { noevents(0), critical(1), major(2), 
                        minor(3), info(4) }
    MAX-ACCESS      read-create
    STATUS          obsolete
    DESCRIPTION     
            "
             Events that are at least as severe as the designated
             level will be logged. noevents suppresses all events
             of this type from being logged.
             "
    ::= { sonusEventLogFilterAdminEntry 4 }

sonusEventLogFilterAdminState OBJECT-TYPE
    SYNTAX          SonusEvLogFilterStateType
    MAX-ACCESS      read-create
    STATUS          obsolete
    DESCRIPTION     
            "
             On if this filter entry should take precedence over the
             per-node settings.
             "
    DEFVAL          { off }
    ::= { sonusEventLogFilterAdminEntry 5 }

sonusEventLogFilterAdminRowstatus OBJECT-TYPE
    SYNTAX          RowStatus
    MAX-ACCESS      read-create
    STATUS          obsolete
    DESCRIPTION     
            ""
    ::= { sonusEventLogFilterAdminEntry 6 }

sonusEventLogFilterStatusTable OBJECT-TYPE
    SYNTAX          SEQUENCE OF SonusEventLogFilterStatusEntry
    MAX-ACCESS      not-accessible
    STATUS          current
    DESCRIPTION     
            "
             Event Log Class Filter status table per card.
             "
    ::= { sonusEventLog 11 }

sonusEventLogFilterStatusEntry OBJECT-TYPE
    SYNTAX          SonusEventLogFilterStatusEntry
    MAX-ACCESS      not-accessible
    STATUS          current
    DESCRIPTION     
            ""
    INDEX           { sonusEventLogFilterStatusCeName, 
                      sonusEventLogFilterStatusType, 
                      sonusEventLogFilterStatusEventClass }
    ::= { sonusEventLogFilterStatusTable 1 }

SonusEventLogFilterStatusEntry ::=
    SEQUENCE {
        sonusEventLogFilterStatusCeName String,
        sonusEventLogFilterStatusType   SonusEvLogFilterStatusTypeType,
        sonusEventLogFilterStatusEventClass   EventClassType,
        sonusEventLogFilterStatusEventsFiltered       Integer32
    }

sonusEventLogFilterStatusCeName OBJECT-TYPE
    SYNTAX          String (SIZE(0..255))
    MAX-ACCESS      not-accessible
    STATUS          current
    DESCRIPTION     
            "
             The host name for which these table entries apply.
             "
    ::= { sonusEventLogFilterStatusEntry 1 }

sonusEventLogFilterStatusType OBJECT-TYPE
    SYNTAX          SonusEvLogFilterStatusTypeType
    MAX-ACCESS      not-accessible
    STATUS          current
    DESCRIPTION     
            "
             The event log type for which these table entries
             apply.
             "
    ::= { sonusEventLogFilterStatusEntry 2 }

sonusEventLogFilterStatusEventClass OBJECT-TYPE
    SYNTAX          EventClassType
    MAX-ACCESS      not-accessible
    STATUS          current
    DESCRIPTION     
            "
             The event class to which the filter entry applies.
             "
    ::= { sonusEventLogFilterStatusEntry 3 }

sonusEventLogFilterStatusEventsFiltered OBJECT-TYPE
    SYNTAX          Integer32
    MAX-ACCESS      read-only
    STATUS          current
    DESCRIPTION     
            "
             The number of events that were filtered.
             "
    ::= { sonusEventLogFilterStatusEntry 4 }

sonusEventLogSubSystemAdminTable OBJECT-TYPE
    SYNTAX          SEQUENCE OF SonusEventLogSubSystemAdminEntry
    MAX-ACCESS      not-accessible
    STATUS          obsolete
    DESCRIPTION     
            "
             Subsystem Event Logging configuration table.
             This table configures subsystems DO NOT filter events.
             "
    ::= { sonusEventLog 12 }

sonusEventLogSubSystemAdminEntry OBJECT-TYPE
    SYNTAX          SonusEventLogSubSystemAdminEntry
    MAX-ACCESS      not-accessible
    STATUS          obsolete
    DESCRIPTION     
            ""
    INDEX           { sonusEventLogSubSystemAdminCeName, 
                      sonusEventLogSubSystemAdminSystemId }
    ::= { sonusEventLogSubSystemAdminTable 1 }

SonusEventLogSubSystemAdminEntry ::=
    SEQUENCE {
        sonusEventLogSubSystemAdminCeName String,
        sonusEventLogSubSystemAdminSystemId   String,
        sonusEventLogSubSystemAdminInfoLogState       INTEGER,
        sonusEventLogSubSystemAdminMinEventId     SonusEvLogSubsysMinEventIdType,
        sonusEventLogSubSystemAdminMaxEventId     SonusEvLogSubsysMaxEventIdType,
        sonusEventLogSubSystemAdminRowstatus    RowStatus
    }

sonusEventLogSubSystemAdminCeName OBJECT-TYPE
    SYNTAX          String (SIZE(0..255))
    MAX-ACCESS      not-accessible
    STATUS          obsolete
    DESCRIPTION     
            "
             The host name which the subsystem event entries apply.
             "
    ::= { sonusEventLogSubSystemAdminEntry 1 }

sonusEventLogSubSystemAdminSystemId OBJECT-TYPE
    SYNTAX          String (SIZE(0..23))
    MAX-ACCESS      not-accessible
    STATUS          obsolete
    DESCRIPTION     
            "
             The subsystem/task mnemonic for which the subsystem event entries apply.
             "
    ::= { sonusEventLogSubSystemAdminEntry 2 }

sonusEventLogSubSystemAdminInfoLogState OBJECT-TYPE
    SYNTAX          INTEGER { disabled(1), enabled(2) }
    MAX-ACCESS      read-create
    STATUS          obsolete
    DESCRIPTION     
            "
             The subsystem's INFO level event logging state. If this state is
             enabled, then subsystem INFO/MINOR events fall into specified
             range, sonusEvLogSubsystemMinEventId to sonusEvLogSubsystemMinEventId,
             will not be filtered.
             "
    ::= { sonusEventLogSubSystemAdminEntry 3 }

sonusEventLogSubSystemAdminMinEventId OBJECT-TYPE
    SYNTAX          SonusEvLogSubsysMinEventIdType
    MAX-ACCESS      read-create
    STATUS          obsolete
    DESCRIPTION     
            "
             The subsystem's minimum event ID that do not get filtered.
             "
    DEFVAL          { 0 }
    ::= { sonusEventLogSubSystemAdminEntry 4 }

sonusEventLogSubSystemAdminMaxEventId OBJECT-TYPE
    SYNTAX          SonusEvLogSubsysMaxEventIdType
    MAX-ACCESS      read-create
    STATUS          obsolete
    DESCRIPTION     
            "
             The subsystem's maximum event ID that do not get filtered.
             "
    DEFVAL          { 2048 }
    ::= { sonusEventLogSubSystemAdminEntry 5 }

sonusEventLogSubSystemAdminRowstatus OBJECT-TYPE
    SYNTAX          RowStatus
    MAX-ACCESS      read-create
    STATUS          obsolete
    DESCRIPTION     
            ""
    ::= { sonusEventLogSubSystemAdminEntry 6 }

sonusEventLogInfoLevelLoggingEnable OBJECT IDENTIFIER
    ::= { sonusEventLog 13 }

sonusEventLogDataAgentStatusTable OBJECT-TYPE
    SYNTAX          SEQUENCE OF SonusEventLogDataAgentStatusEntry
    MAX-ACCESS      not-accessible
    STATUS          current
    DESCRIPTION     
            "
             Status of the remote data warehouse.
             "
    ::= { sonusEventLog 14 }

sonusEventLogDataAgentStatusEntry OBJECT-TYPE
    SYNTAX          SonusEventLogDataAgentStatusEntry
    MAX-ACCESS      not-accessible
    STATUS          current
    DESCRIPTION     
            ""
    INDEX           { sonusEventLogDataAgentStatusCeName, 
                      sonusEventLogDataAgentStatusAgentType }
    ::= { sonusEventLogDataAgentStatusTable 1 }

SonusEventLogDataAgentStatusEntry ::=
    SEQUENCE {
        sonusEventLogDataAgentStatusCeName  String,
        sonusEventLogDataAgentStatusAgentType     DataAgentTypeType,
        sonusEventLogDataAgentStatusConnectionStatus            DataAgentConnectionStatusType,
        sonusEventLogDataAgentStatusIpAddress     String
    }

sonusEventLogDataAgentStatusCeName OBJECT-TYPE
    SYNTAX          String (SIZE(0..255))
    MAX-ACCESS      not-accessible
    STATUS          current
    DESCRIPTION     
            "
             The host name of the data agent.
             "
    ::= { sonusEventLogDataAgentStatusEntry 1 }

sonusEventLogDataAgentStatusAgentType OBJECT-TYPE
    SYNTAX          DataAgentTypeType
    MAX-ACCESS      not-accessible
    STATUS          current
    DESCRIPTION     
            "
             The name of the data agent.
             "
    ::= { sonusEventLogDataAgentStatusEntry 2 }

sonusEventLogDataAgentStatusConnectionStatus OBJECT-TYPE
    SYNTAX          DataAgentConnectionStatusType
    MAX-ACCESS      read-only
    STATUS          current
    DESCRIPTION     
            "
             The status of the connection to the remote data warehouse.
             "
    ::= { sonusEventLogDataAgentStatusEntry 3 }

sonusEventLogDataAgentStatusIpAddress OBJECT-TYPE
    SYNTAX          String (SIZE(0..255))
    MAX-ACCESS      read-only
    STATUS          current
    DESCRIPTION     
            "
             The IPv4 address currently being used for the connection to the remote data warehouse.
             "
    ::= { sonusEventLogDataAgentStatusEntry 4 }

sonusEventLogDataAgentAdmin OBJECT IDENTIFIER
    ::= { sonusEventLog 15 }

sonusEventLogDataAgentAdminServerIpV4Address OBJECT-TYPE
    SYNTAX          IpAddress
    MAX-ACCESS      read-write
    STATUS          current
    DESCRIPTION     
            "
             The IPv4 address of the remote data warehouse.
             "
    ::= { sonusEventLogDataAgentAdmin 1 }

sonusEventLogDataAgentAdminServerIpV6Address OBJECT-TYPE
    SYNTAX          Ipv6Address
    MAX-ACCESS      read-write
    STATUS          current
    DESCRIPTION     
            "
             The IPv6 address of the remote data warehouse.
             "
    ::= { sonusEventLogDataAgentAdmin 2 }

sonusEventLogDataAgentAdminCdrLogs OBJECT-TYPE
    SYNTAX          INTEGER { disabled(1), enabled(2) }
    MAX-ACCESS      read-write
    STATUS          current
    DESCRIPTION     
            "
             Enable/disable cdr logging.
             "
    ::= { sonusEventLogDataAgentAdmin 3 }

sonusEventLogDataAgentAdminApplicationLogs OBJECT-TYPE
    SYNTAX          INTEGER { disabled(1), enabled(2) }
    MAX-ACCESS      read-write
    STATUS          current
    DESCRIPTION     
            "
             Enable/disable application log forwarding.
             "
    ::= { sonusEventLogDataAgentAdmin 4 }

sonusEventLogDataAgentAdminPlatformLogs OBJECT-TYPE
    SYNTAX          INTEGER { disabled(1), enabled(2) }
    MAX-ACCESS      read-write
    STATUS          current
    DESCRIPTION     
            "
             Enable/disable platform log forwarding.
             "
    ::= { sonusEventLogDataAgentAdmin 5 }

sonusEventLogDataAgentAdminAuditAndSecurityLogs OBJECT-TYPE
    SYNTAX          INTEGER { disabled(1), enabled(2) }
    MAX-ACCESS      read-write
    STATUS          current
    DESCRIPTION     
            "
             Enable/disable audit and security log forwarding.
             "
    ::= { sonusEventLogDataAgentAdmin 6 }

sonusEventLogDataAgentAdminPerformanceStats OBJECT-TYPE
    SYNTAX          INTEGER { disabled(1), enabled(2) }
    MAX-ACCESS      read-write
    STATUS          current
    DESCRIPTION     
            "
             Enable/disable performance statistics log forwarding.
             "
    ::= { sonusEventLogDataAgentAdmin 7 }

sonusEventLogDataAgentAdminSSLStrictMode OBJECT-TYPE
    SYNTAX          INTEGER { disabled(1), enabled(2) }
    MAX-ACCESS      read-write
    STATUS          current
    DESCRIPTION     
            "
             Enable/disable SSL strict mode.
             "
    ::= { sonusEventLogDataAgentAdmin 8 }

sonusEventLogOpenclovis OBJECT IDENTIFIER
    ::= { sonusEventLog 16 }

END -- end of module SONUS-GEN2-EVENT-LOG-MIB.
