--
-- This SMIv1 module has been generated by smidump 0.2-cvs. Do not edit.
--

CTRON-SSR-HARDWARE-MIB DEFINITIONS ::= BEGIN

IMPORTS
    ssrMibs
        FROM CTRON-SSR-SMI-MIB
    OBJECT-TYPE
        FROM RFC-1212
    TimeTicks
        FROM RFC1155-SMI;

hardwareMIB OBJECT IDENTIFIER
    ::= { ssrMibs 200 }

-- hardwareMIB MODULE-IDENTITY
--     LAST-UPDATED    "200006270000Z"
--     ORGANIZATION    
--             "Cabletron Systems, Inc."
--     CONTACT-INFO    
--             "Riverstone Networks, Inc
--              5200 Great America Parkway
--              Santa Clara, CA 95054
--              (408) 878-6500
--              nms-eng@riverstonenet.com
--              http://www.riverstonenet.com"
--     DESCRIPTION     
--             "This module defines a schema to access SSR hardware configuration."
--     REVISION        "200006270000Z"
--     DESCRIPTION     
--             "Update contact information. This mib is found on Riverstone Networks RS product line
--              as well as Enterasys SSR product line"
--     REVISION        "197001010000Z"
--     DESCRIPTION     
--             "Modify SSRPortConnectorType for GBIC connector in 4.0 and update sysHwModuleService  
--              by appending the board serial number for 4.0 for RS-32000."
--     REVISION        "200003200000Z"
--     DESCRIPTION     
--             "Add Firmware 4.0 support. 3200 series modules, gigabit modules with GBIC support."
--     REVISION        "199912300000Z"
--     DESCRIPTION     
--             "Add Firmware 3.1 support. 16 port 10/100 TX, Gigabit over Copper, ATM OC-3, POS OC3/12."
--     REVISION        "199812200000Z"
--     DESCRIPTION     
--             "Add Firmware 3.0 support. Add Backup control module status and last Hotswap event."
--     REVISION        "199808040000Z"
--     DESCRIPTION     
--             "First Revision of SSR Hardware mib. "
--     ::= { ssrMibs 200 }


SSRInterfaceIndex ::=
    INTEGER (0..65535)

-- SSRInterfaceIndex ::= TEXTUAL-CONVENTION
--     STATUS          mandatory
--     DESCRIPTION     
--             "A unique value, greater than zero, for each interface
--              or interface sub-layer in the managed system.  It is
--              recommended that values are assigned contiguously
--              starting from 1.  The value for each interface sub-
--              layer must remain constant at least from one re-
--              initialization of the entity's network management
--              system to the next re-initialization."
--     SYNTAX          INTEGER (0..65535)

SSRModuleType ::=
    INTEGER { controlModule(1), ether100TX(2), ether100FX(3), 
                        gigabitSX(4), gigabitLX(5), serial4port(6), 
                        hssi(7), unknown(8), gigabitLLX(9), none(10), 
                        controlModule2(11), gigabitLLX2P(12), 
                        serial2port(13), cmts1x4port(15), 
                        controlModule3(17), serial4portCE(20), 
                        ether100TX16port(21), gigabitTX(22), atm155(24), 
                        sonet4PortOc3(25), sonet2PortOc12(26), 
                        gigabitFX4P(27), gigabitFX4PGBIC(28), 
                        gigabitFX2PGBIC(29), rbGigabit8PGBIC(503), 
                        rbGigabit4PGBIC(504), rbEther100TX24P(505), 
                        rbEther100TC32P(506), rbControlModule(507) }

-- SSRModuleType ::= TEXTUAL-CONVENTION
--     STATUS          mandatory
--     DESCRIPTION     
--             "A unique value, greater than zero, for each module 
--              type supported by the SSR series of products."
--     SYNTAX          INTEGER
--                       { controlModule(1), ether100TX(2), 
--                         ether100FX(3), gigabitSX(4), gigabitLX(5), 
--                         serial4port(6), hssi(7), unknown(8), 
--                         gigabitLLX(9), none(10), controlModule2(11), 
--                         gigabitLLX2P(12), serial2port(13), 
--                         cmts1x4port(15), controlModule3(17), 
--                         serial4portCE(20), ether100TX16port(21), 
--                         gigabitTX(22), atm155(24), sonet4PortOc3(25), 
--                         sonet2PortOc12(26), gigabitFX4P(27), 
--                         gigabitFX4PGBIC(28), gigabitFX2PGBIC(29), 
--                         rbGigabit8PGBIC(503), rbGigabit4PGBIC(504), 
--                         rbEther100TX24P(505), rbEther100TC32P(506), 
--                         rbControlModule(507) }

SSRModuleStatus ::=
    INTEGER { online(1), offline(2) }

-- SSRModuleStatus ::= TEXTUAL-CONVENTION
--     STATUS          mandatory
--     DESCRIPTION     
--             "Current state of module. online indicates the normal state. Offline indicates a powered off or failed
--              module. Modules may be powered off prior to hot swap."
--     SYNTAX          INTEGER
--                       { online(1), offline(2) }

SSRPortType ::=
    INTEGER { etherFast(1), gigEther(2), hssi(3), serial(4), unknown(5), 
                        sonet(6), ds1(7), ds3(8), cmt(9), e1(10), e3(11) }

-- SSRPortType ::= TEXTUAL-CONVENTION
--     STATUS          mandatory
--     DESCRIPTION     
--             "A unique value, greater than zero, for each physical port
--              type supported by the SSR series of products."
--     SYNTAX          INTEGER
--                       { etherFast(1), gigEther(2), hssi(3), serial(4), 
--                         unknown(5), sonet(6), ds1(7), ds3(8), cmt(9), 
--                         e1(10), e3(11) }

SSRPortConnectorType ::=
    INTEGER { empty(0), db9m(1), db9f(2), db15m(3), db15f(4), db25m(5), 
                        db25f(6), rj11(7), rj45(8), aui(9), ftypef(10), 
                        fiberScMM(11), v35(12), eia530(13), rs44x(14), 
                        x21(15), hssi(16), unknown(17), fiberScSM(18), 
                        fiberMTRjMM(19), fiberMTRjSM(20), bncf(21), 
                        bncm(22), rj21(23), fiberScSMLH(24) }

-- SSRPortConnectorType ::= TEXTUAL-CONVENTION
--     STATUS          mandatory
--     DESCRIPTION     
--             "A unique value, greater than zero, for each physical port
--              type supported by the SSR series of products"
--     SYNTAX          INTEGER
--                       { empty(0), db9m(1), db9f(2), db15m(3), 
--                         db15f(4), db25m(5), db25f(6), rj11(7), 
--                         rj45(8), aui(9), ftypef(10), fiberScMM(11), 
--                         v35(12), eia530(13), rs44x(14), x21(15), 
--                         hssi(16), unknown(17), fiberScSM(18), 
--                         fiberMTRjMM(19), fiberMTRjSM(20), bncf(21), 
--                         bncm(22), rj21(23), fiberScSMLH(24) }

SSRserviceType ::=
    OCTET STRING (SIZE(0..7))

-- SSRserviceType ::= TEXTUAL-CONVENTION
--     STATUS          mandatory
--     DESCRIPTION     
--             "A string that is unique to a module in production. This string
--              is used by Cabletron Service and Manufacturing as 
--              to identify shipped inventory."
--     SYNTAX          OCTET STRING (SIZE(0..7))

SSRmemorySize ::=
    INTEGER (-1..2147483647)

-- SSRmemorySize ::= TEXTUAL-CONVENTION
--     STATUS          mandatory
--     DESCRIPTION     
--             "An integer that represents the size of memory in Megabytes. -1
--              represents not-available or not-applicable value."
--     SYNTAX          INTEGER (-1..2147483647)

SSRSwitchingFabricInfo ::=
    INTEGER (0..63)

-- SSRSwitchingFabricInfo ::= TEXTUAL-CONVENTION
--     STATUS          mandatory
--     DESCRIPTION     
--             "A bit string that represents the status of Switching Fabric 
--              in the shelf/chassis. Switching Fabric #1 is first 2 bits 0-1,  
--              #2 is 2-3.
--              
--              For example, given a 16 slot SSR 8600 which has one 
--               Switching Fabric in Switching Fabric Slot #1 
--              (lowest full length midplane slot) the
--              integer value 0x00000007 translates into (bits):
--                    0 0 0 0 0 1 1 1 
--                            | | | |
--                            | | | +--- switching fabric #1 is present
--                            | | +----- switching fabric is primary
--                            | + ------ switching fabric #2 is present 
--                            +--------- switching fabric is standby"
--     SYNTAX          INTEGER (0..63)

SSRCmLedState ::=
    INTEGER (0..15)

-- SSRCmLedState ::= TEXTUAL-CONVENTION
--     STATUS          mandatory
--     DESCRIPTION     
--             "A bit string that represents the status of the active Control Module.
--              Each LED occupies a bit. The value 1 indicates LED is on, 0 is off.
--                    The integer value 0x00000015 translates into (bits):
--                    0 0 0 0 1 1 1 1 
--                            | | | |
--                            | | | +- System OK  -- SYS OK 
--                            | | +--- Heartbeat  -- HB
--                            | +----- Error      -- ERR
--                            + ------ Diagnostic -- Diag"
--     SYNTAX          INTEGER (0..15)

SSRBackupCMState ::=
    INTEGER { unknown(1), inactive(2), standby(3), notInstalled(4), 
                        active(5) }

-- SSRBackupCMState ::= TEXTUAL-CONVENTION
--     STATUS          mandatory
--     DESCRIPTION     
--             "A enumeration that represents the state of the backup control module.
--              
--              A backup control module prom will boot the system firmware to an 
--              intermediate state and begins sending hello messages to the main cpu
--              and assume the monitor(3) state. If the prom does not boot the 
--              backup control module, the active control module will report the
--              status as inactive(2). inactive(2) indicates a failed state as it 
--              means the backup control module can not take over for the active
--              control module.
--              
--              If the main cpu fails to respond to the backup control module's 
--              periodic status checks and the backup control module is in the 
--              standby(3) state, the backup control module will reset the active
--              control module, then reset all line cards and then finish a normal
--              boot sequence so that it becomes the master. At this point, the
--              value of this object is active(5).
--              
--              Flows in the hardware must be reprogrammed and all control protocols
--              will have to reestablish. An enterprise trap may also be sent.
--              
--              Normally, slot: CM will be the primary control module. CM/1 is
--              the slot for the backup control module. If some other line card
--              exists in slot CM/1 or no card exists, the state of this object
--               is notInstalled(4)."
--     SYNTAX          INTEGER
--                       { unknown(1), inactive(2), standby(3), 
--                         notInstalled(4), active(5) }

PowerSupplyBits ::=
    INTEGER (0..255)

-- PowerSupplyBits ::= TEXTUAL-CONVENTION
--     STATUS          mandatory
--     DESCRIPTION     
--             "The encoding of the bits are as follows :
--              Each power supply in the system is represented by two bits.
--              The lower bit reflecting the presence of the power supply and
--              the higher bit representing it's state. A 1 reflects a properly
--              working power supply a 0 one which is down.
--              This encoding allows for a maximum of 16 power supplies.
--              
--              For example :
--              The integer value 0x00000007 translates into
--              
--              0 0 0 0 0 1 1 1 in bits
--                      | | | |
--                      | | | +- power supply 1 is present
--                      | | +--- power supply 1 is working normally
--                      | +----- power supply 2 is present
--                      +------- power supply 2 is down"
--     SYNTAX          INTEGER (0..255)

sysHwGroup OBJECT IDENTIFIER
    ::= { ssrMibs 1 }

sysHwNumSlots OBJECT-TYPE
    SYNTAX          INTEGER (0..64)
    ACCESS          read-only
    STATUS          mandatory
    DESCRIPTION     
            "The number of slots present in the Shelf/Chassis."
    ::= { sysHwGroup 1 }

sysHwModuleTable OBJECT-TYPE
    SYNTAX          SEQUENCE OF SysHwModuleEntry
    ACCESS          not-accessible
    STATUS          mandatory
    DESCRIPTION     
            "A list of module entries."
    ::= { sysHwGroup 2 }

sysHwModuleEntry OBJECT-TYPE
    SYNTAX          SysHwModuleEntry
    ACCESS          not-accessible
    STATUS          mandatory
    DESCRIPTION     
            "An entry containing management information applicable
             to a particular module."
    INDEX           { sysHwModuleSlotNumber }
    ::= { sysHwModuleTable 1 }

SysHwModuleEntry ::=
    SEQUENCE {
        sysHwModuleSlotNumber           INTEGER,
        sysHwModuleType                 SSRModuleType,
        sysHwModuleDesc                 OCTET STRING,
        sysHwModuleNumPorts             INTEGER,
        sysHwModuleVersion              OCTET STRING,
        sysHwModuleMemory               SSRmemorySize,
        sysHwModuleService              SSRserviceType,
        sysHwModuleStatus               SSRModuleStatus
    }

sysHwModuleSlotNumber OBJECT-TYPE
    SYNTAX          INTEGER (1..65)
    ACCESS          read-only
    STATUS          mandatory
    DESCRIPTION     
            "The physical slot number of the module in the Shelf/Chassis."
    ::= { sysHwModuleEntry 1 }

sysHwModuleType OBJECT-TYPE
    SYNTAX          SSRModuleType
    ACCESS          read-only
    STATUS          mandatory
    DESCRIPTION     
            "The physical module type."
    ::= { sysHwModuleEntry 2 }

sysHwModuleDesc OBJECT-TYPE
    SYNTAX          OCTET STRING (SIZE(0..255))
    ACCESS          read-only
    STATUS          mandatory
    DESCRIPTION     
            "The description of the module with it's version number etc.
             For the Control Module it should have the software version, the 
             amount of dynamic RAM, flash RAM."
    ::= { sysHwModuleEntry 3 }

sysHwModuleNumPorts OBJECT-TYPE
    SYNTAX          INTEGER (0..256)
    ACCESS          read-only
    STATUS          mandatory
    DESCRIPTION     
            "The number of physical ports on this Card/Module."
    ::= { sysHwModuleEntry 4 }

sysHwModuleVersion OBJECT-TYPE
    SYNTAX          OCTET STRING (SIZE(1))
    ACCESS          read-only
    STATUS          mandatory
    DESCRIPTION     
            "The alpha-numeric version string for this Card/Module."
    ::= { sysHwModuleEntry 5 }

sysHwModuleMemory OBJECT-TYPE
    SYNTAX          SSRmemorySize
    ACCESS          read-only
    STATUS          mandatory
    DESCRIPTION     
            "System Memory size available on the Module. Reports
             -1 if no memory exists on this module, such as power supplies."
    ::= { sysHwModuleEntry 6 }

sysHwModuleService OBJECT-TYPE
    SYNTAX          SSRserviceType
    ACCESS          read-only
    STATUS          mandatory
    DESCRIPTION     
            "The Cabletron service identifier string for this Card/Module.The board serial
             number is appended to the string too."
    ::= { sysHwModuleEntry 8 }

sysHwModuleStatus OBJECT-TYPE
    SYNTAX          SSRModuleStatus
    ACCESS          read-only
    STATUS          mandatory
    DESCRIPTION     
            "The current status of this module, online or offline."
    ::= { sysHwModuleEntry 9 }

sysHwPortTable OBJECT-TYPE
    SYNTAX          SEQUENCE OF SysHwPortEntry
    ACCESS          not-accessible
    STATUS          mandatory
    DESCRIPTION     
            "A list of module entries."
    ::= { sysHwGroup 3 }

sysHwPortEntry OBJECT-TYPE
    SYNTAX          SysHwPortEntry
    ACCESS          not-accessible
    STATUS          mandatory
    DESCRIPTION     
            "An entry containing management information applicable
             to a particular module."
    INDEX           { sysHwPortSlotNumber, sysHwPortNumber }
    ::= { sysHwPortTable 1 }

SysHwPortEntry ::=
    SEQUENCE {
        sysHwPortSlotNumber             INTEGER,
        sysHwPortNumber                 INTEGER,
        sysHwPortType                   SSRPortType,
        sysHwPortConnectorType          SSRPortConnectorType,
        sysHwPortIfIndex                SSRInterfaceIndex
    }

sysHwPortSlotNumber OBJECT-TYPE
    SYNTAX          INTEGER (1..255)
    ACCESS          read-only
    STATUS          mandatory
    DESCRIPTION     
            "The physical slot number of the module in the Chassis."
    ::= { sysHwPortEntry 1 }

sysHwPortNumber OBJECT-TYPE
    SYNTAX          INTEGER (1..255)
    ACCESS          read-only
    STATUS          mandatory
    DESCRIPTION     
            "The port number of the physical port in the Card/Module."
    ::= { sysHwPortEntry 2 }

sysHwPortType OBJECT-TYPE
    SYNTAX          SSRPortType
    ACCESS          read-only
    STATUS          mandatory
    DESCRIPTION     
            "The physical port type."
    ::= { sysHwPortEntry 3 }

sysHwPortConnectorType OBJECT-TYPE
    SYNTAX          SSRPortConnectorType
    ACCESS          read-only
    STATUS          mandatory
    DESCRIPTION     
            "The physical port connector type."
    ::= { sysHwPortEntry 4 }

sysHwPortIfIndex OBJECT-TYPE
    SYNTAX          SSRInterfaceIndex
    ACCESS          read-only
    STATUS          mandatory
    DESCRIPTION     
            "The value of ifIndex used to access this port in the Interface MIB."
    ::= { sysHwPortEntry 5 }

sysHwPowerSupply OBJECT-TYPE
    SYNTAX          PowerSupplyBits
    ACCESS          read-only
    STATUS          mandatory
    DESCRIPTION     
            "The number and status of power supplies powering the Shelf/Chassis."
    ::= { sysHwGroup 4 }

sysHwFan OBJECT-TYPE
    SYNTAX          INTEGER { working(1), notWorking(2), unknown(3) }
    ACCESS          read-only
    STATUS          mandatory
    DESCRIPTION     
            "The current state of the fans located inside the Shelf/Chassis."
    ::= { sysHwGroup 5 }

sysHwTemperature OBJECT-TYPE
    SYNTAX          INTEGER { normal(1), outOfRange(2), unknown(3) }
    ACCESS          read-only
    STATUS          mandatory
    DESCRIPTION     
            "The current temperature status of the Shelf/Chassis."
    ::= { sysHwGroup 6 }

sysHwChassisId OBJECT-TYPE
    SYNTAX          OCTET STRING (SIZE(0..255))
    ACCESS          read-only
    STATUS          mandatory
    DESCRIPTION     
            "Operator defined serial number for this particular chassis/shelf."
    ::= { sysHwGroup 7 }

-- sysHwTotalInOctets OBJECT-TYPE
--     SYNTAX          Counter64
--     ACCESS          read-only
--     STATUS          deprecated
--     DESCRIPTION     
--             "The total number of octets into the switch."
--     ::= { sysHwGroup 10 }

-- sysHwTotalOutOctets OBJECT-TYPE
--     SYNTAX          Counter64
--     ACCESS          read-only
--     STATUS          deprecated
--     DESCRIPTION     
--             "The total number of octets out of the switch."
--     ::= { sysHwGroup 11 }

-- sysHwTotalInFrames OBJECT-TYPE
--     SYNTAX          Counter64
--     ACCESS          read-only
--     STATUS          deprecated
--     DESCRIPTION     
--             "The total number of frames into the switch."
--     ::= { sysHwGroup 12 }

-- sysHwTotalOutFrames OBJECT-TYPE
--     SYNTAX          Counter64
--     ACCESS          read-only
--     STATUS          deprecated
--     DESCRIPTION     
--             "The total number of frames out of the switch."
--     ::= { sysHwGroup 13 }

-- sysHwTotalL2SwitchedFrames OBJECT-TYPE
--     SYNTAX          Counter64
--     ACCESS          read-only
--     STATUS          deprecated
--     DESCRIPTION     
--             "The current number of frames switched at Layer 2 (transport)."
--     ::= { sysHwGroup 14 }

-- sysHwTotalL3SwitchedFrames OBJECT-TYPE
--     SYNTAX          Counter64
--     ACCESS          read-only
--     STATUS          deprecated
--     DESCRIPTION     
--             "The current number of frames switched at IETF Layers 3 (transport) and
--              4 (application)."
--     ::= { sysHwGroup 15 }

sysHwSwitchingFabric OBJECT-TYPE
    SYNTAX          SSRSwitchingFabricInfo
    ACCESS          read-only
    STATUS          mandatory
    DESCRIPTION     
            "Status of Switching Fabric in shelf/chassis."
    ::= { sysHwGroup 19 }

sysHwControlModuleLED OBJECT-TYPE
    SYNTAX          SSRCmLedState
    ACCESS          read-only
    STATUS          mandatory
    DESCRIPTION     
            "Status of the shelf/chassis Active Control Module's four LED displays."
    ::= { sysHwGroup 20 }

sysHwControlModuleBackupState OBJECT-TYPE
    SYNTAX          SSRBackupCMState
    ACCESS          read-only
    STATUS          mandatory
    DESCRIPTION     
            "Status of the the backup Control Module as interpreted from the 
             active control module. CLI: system show hardware will present
             the following data: Redundant CPU slot : Not present"
    ::= { sysHwGroup 21 }

sysHwLastHotSwapEvent OBJECT-TYPE
    SYNTAX          TimeTicks
    ACCESS          read-only
    STATUS          mandatory
    DESCRIPTION     
            "The value of sysUpTime when the last hotswap of a physical module event occured."
    ::= { sysHwGroup 22 }

hwConformance OBJECT IDENTIFIER
    ::= { hardwareMIB 2 }

hwCompliances OBJECT IDENTIFIER
    ::= { hwConformance 1 }

hwGroups OBJECT IDENTIFIER
    ::= { hwConformance 2 }

hwConfGroupV10 OBJECT IDENTIFIER
    ::= { hwGroups 1 }

-- hwConfGroupV10 OBJECT-GROUP
--     OBJECTS         { sysHwNumSlots, sysHwModuleSlotNumber, 
--                       sysHwModuleType, sysHwModuleDesc, 
--                       sysHwModuleNumPorts, sysHwModuleVersion, 
--                       sysHwPortSlotNumber, sysHwPortNumber, 
--                       sysHwPortType, sysHwPortConnectorType, 
--                       sysHwPortIfIndex, sysHwPowerSupply, sysHwFan, 
--                       sysHwTemperature, sysHwChassisId, 
--                       sysHwTotalInOctets, sysHwTotalOutOctets, 
--                       sysHwTotalInFrames, sysHwTotalOutFrames, 
--                       sysHwTotalL2SwitchedFrames, 
--                       sysHwTotalL3SwitchedFrames }
--     STATUS          deprecated
--     DESCRIPTION     
--             "A set of managed objects that make up version 1.0 of the SSR Hardware mib."
--     ::= { hwGroups 1 }

hwConfGroupV11 OBJECT IDENTIFIER
    ::= { hwGroups 2 }

-- hwConfGroupV11 OBJECT-GROUP
--     OBJECTS         { sysHwNumSlots, sysHwModuleSlotNumber, 
--                       sysHwModuleType, sysHwModuleDesc, 
--                       sysHwModuleNumPorts, sysHwModuleVersion, 
--                       sysHwModuleMemory, sysHwModuleService, 
--                       sysHwPortSlotNumber, sysHwPortNumber, 
--                       sysHwPortType, sysHwPortConnectorType, 
--                       sysHwPortIfIndex, sysHwPowerSupply, sysHwFan, 
--                       sysHwTemperature, sysHwChassisId, 
--                       sysHwSwitchingFabric, sysHwControlModuleLED }
--     STATUS          deprecated
--     DESCRIPTION     
--             "A set of managed objects that make up version 1.1 of the SSR Hardware mib."
--     ::= { hwGroups 2 }

hwConfGroupV12 OBJECT IDENTIFIER
    ::= { hwGroups 3 }

-- hwConfGroupV12 OBJECT-GROUP
--     OBJECTS         { sysHwNumSlots, sysHwModuleSlotNumber, 
--                       sysHwModuleType, sysHwModuleDesc, 
--                       sysHwModuleNumPorts, sysHwModuleVersion, 
--                       sysHwModuleMemory, sysHwModuleService, 
--                       sysHwModuleStatus, sysHwPortSlotNumber, 
--                       sysHwPortNumber, sysHwPortType, 
--                       sysHwPortConnectorType, sysHwPortIfIndex, 
--                       sysHwPowerSupply, sysHwFan, sysHwTemperature, 
--                       sysHwChassisId, sysHwSwitchingFabric, 
--                       sysHwControlModuleLED }
--     STATUS          deprecated
--     DESCRIPTION     
--             "A set of managed objects that make up version 1.2 of the SSR Hardware mib."
--     ::= { hwGroups 3 }

hwConfGroupV30 OBJECT IDENTIFIER
    ::= { hwGroups 4 }

-- hwConfGroupV30 OBJECT-GROUP
--     OBJECTS         { sysHwNumSlots, sysHwModuleSlotNumber, 
--                       sysHwModuleType, sysHwModuleDesc, 
--                       sysHwModuleNumPorts, sysHwModuleVersion, 
--                       sysHwModuleMemory, sysHwModuleService, 
--                       sysHwModuleStatus, sysHwPortSlotNumber, 
--                       sysHwPortNumber, sysHwPortType, 
--                       sysHwPortConnectorType, sysHwPortIfIndex, 
--                       sysHwPowerSupply, sysHwFan, sysHwTemperature, 
--                       sysHwChassisId, sysHwSwitchingFabric, 
--                       sysHwControlModuleLED, 
--                       sysHwControlModuleBackupState, 
--                       sysHwLastHotSwapEvent }
--     STATUS          mandatory
--     DESCRIPTION     
--             "A set of managed objects that make up version 3.0 of the SSR Hardware mib."
--     ::= { hwGroups 4 }

hwComplianceV10 OBJECT IDENTIFIER
    ::= { hwConfGroupV10 1 }

-- hwComplianceV10 MODULE-COMPLIANCE
--     STATUS          deprecated
--     DESCRIPTION     
--             "The compliance statement for the SSR-HARDWARE-MIB."

--     MODULE          -- -- this module

--         MANDATORY-GROUPS    { hwConfGroupV10 }

--     ::= { hwConfGroupV10 1 }

hwComplianceV11 OBJECT IDENTIFIER
    ::= { hwConfGroupV11 2 }

-- hwComplianceV11 MODULE-COMPLIANCE
--     STATUS          deprecated
--     DESCRIPTION     
--             "The compliance statement for the SSR-HARDWARE-MIB."

--     MODULE          -- -- this module

--         MANDATORY-GROUPS    { hwConfGroupV11 }

--     ::= { hwConfGroupV11 2 }

hwComplianceV12 OBJECT IDENTIFIER
    ::= { hwConfGroupV11 3 }

-- hwComplianceV12 MODULE-COMPLIANCE
--     STATUS          deprecated
--     DESCRIPTION     
--             "The compliance statement for the SSR-HARDWARE-MIB."

--     MODULE          -- -- this module

--         MANDATORY-GROUPS    { hwConfGroupV11 }

--     ::= { hwConfGroupV11 3 }

hwComplianceV30 OBJECT IDENTIFIER
    ::= { hwConfGroupV11 4 }

-- hwComplianceV30 MODULE-COMPLIANCE
--     STATUS          mandatory
--     DESCRIPTION     
--             "The compliance statement for the SSR-HARDWARE-MIB."

--     MODULE          -- -- this module

--         MANDATORY-GROUPS    { hwConfGroupV30 }

--     ::= { hwConfGroupV11 4 }

END -- end of module CTRON-SSR-HARDWARE-MIB.
