--
-- This SMIv1 module has been generated by smidump 0.2-cvs. Do not edit.
--

SONUS-DS3THRESHOLD-MIB DEFINITIONS ::= BEGIN

IMPORTS
    OBJECT-TYPE
        FROM RFC-1212
    TRAP-TYPE
        FROM RFC-1215
    sonusDs3Index, sonusEventClass, sonusEventDescription, 
    sonusEventLevel, sonusEventTime, sonusPortIndex, sonusSequenceId, 
    sonusShelfIndex, sonusSlotIndex
        FROM SONUS-COMMON-MIB
    sonusDs3ThresholdType, sonusDsx3MIBNotificationsObjects, 
    sonusDsx3MIBNotificationsPrefix, sonusDsx3MIBObjects
        FROM SONUS-DS3-MIB
    sonusCircuitMIBs
        FROM SONUS-SMI
    SonusAdminState, SonusShelfIndex, SonusSlotIndex
        FROM SONUS-TC;

sonusDsx3ThresholdMIB OBJECT IDENTIFIER
    ::= { sonusCircuitMIBs 6 }

-- sonusDsx3ThresholdMIB MODULE-IDENTITY
--     LAST-UPDATED    "200703280000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module DS3 management."
--     ::= { sonusCircuitMIBs 6 }


sonusDsx3Threshold OBJECT IDENTIFIER
    ::= { sonusDsx3MIBObjects 11 }

sonusDsx3ThresholdTable OBJECT-TYPE
    SYNTAX          SEQUENCE OF SonusDsx3ThresholdEntry
    ACCESS          not-accessible
    STATUS          mandatory
    DESCRIPTION     
            " "
    ::= { sonusDsx3Threshold 1 }

sonusDsx3ThresholdEntry OBJECT-TYPE
    SYNTAX          SonusDsx3ThresholdEntry
    ACCESS          not-accessible
    STATUS          mandatory
    DESCRIPTION     
            "Entry in Sonus Dsx3 Threshold Table"
    INDEX           { sonusDsx3ThresholdShelfIndex, 
                      sonusDsx3ThresholdSlotIndex, 
                      sonusDsx3ThresholdPortIndex, 
                      sonusDsx3ThresholdDs3Index }
    ::= { sonusDsx3ThresholdTable 1 }

SonusDsx3ThresholdEntry ::=
    SEQUENCE {
        sonusDsx3ThresholdShelfIndex    SonusShelfIndex,
        sonusDsx3ThresholdSlotIndex     SonusSlotIndex,
        sonusDsx3ThresholdPortIndex     INTEGER,
        sonusDsx3ThresholdDs3Index      INTEGER,
        sonusDsx3ThresholdMinorLCVThreshold   INTEGER,
        sonusDsx3ThresholdMinorLESThreshold   INTEGER,
        sonusDsx3ThresholdMinorLSESThreshold    INTEGER,
        sonusDsx3ThresholdMinorPCVThreshold   INTEGER,
        sonusDsx3ThresholdMinorPESThreshold   INTEGER,
        sonusDsx3ThresholdMinorPSESThreshold    INTEGER,
        sonusDsx3ThresholdMinorUASThreshold   INTEGER,
        sonusDsx3ThresholdDayMinorLCVThreshold      INTEGER,
        sonusDsx3ThresholdDayMinorLESThreshold      INTEGER,
        sonusDsx3ThresholdDayMinorLSESThreshold       INTEGER,
        sonusDsx3ThresholdDayMinorPCVThreshold      INTEGER,
        sonusDsx3ThresholdDayMinorPESThreshold      INTEGER,
        sonusDsx3ThresholdDayMinorPSESThreshold       INTEGER,
        sonusDsx3ThresholdDayMinorUASThreshold      INTEGER,
        sonusDsx3ThresholdMajorLCVThreshold   INTEGER,
        sonusDsx3ThresholdMajorLESThreshold   INTEGER,
        sonusDsx3ThresholdMajorLSESThreshold    INTEGER,
        sonusDsx3ThresholdMajorPCVThreshold   INTEGER,
        sonusDsx3ThresholdMajorPESThreshold   INTEGER,
        sonusDsx3ThresholdMajorPSESThreshold    INTEGER,
        sonusDsx3ThresholdMajorUASThreshold   INTEGER,
        sonusDsx3ThresholdDayMajorLCVThreshold      INTEGER,
        sonusDsx3ThresholdDayMajorLESThreshold      INTEGER,
        sonusDsx3ThresholdDayMajorLSESThreshold       INTEGER,
        sonusDsx3ThresholdDayMajorPCVThreshold      INTEGER,
        sonusDsx3ThresholdDayMajorPESThreshold      INTEGER,
        sonusDsx3ThresholdDayMajorPSESThreshold       INTEGER,
        sonusDsx3ThresholdDayMajorUASThreshold      INTEGER,
        sonusDsx3ThresholdCriticalLCVThreshold      INTEGER,
        sonusDsx3ThresholdCriticalLESThreshold      INTEGER,
        sonusDsx3ThresholdCriticalLSESThreshold       INTEGER,
        sonusDsx3ThresholdCriticalPCVThreshold      INTEGER,
        sonusDsx3ThresholdCriticalPESThreshold      INTEGER,
        sonusDsx3ThresholdCriticalPSESThreshold       INTEGER,
        sonusDsx3ThresholdCriticalUASThreshold      INTEGER,
        sonusDsx3ThresholdDayCriticalLCVThreshold         INTEGER,
        sonusDsx3ThresholdDayCriticalLESThreshold         INTEGER,
        sonusDsx3ThresholdDayCriticalLSESThreshold          INTEGER,
        sonusDsx3ThresholdDayCriticalPCVThreshold         INTEGER,
        sonusDsx3ThresholdDayCriticalPESThreshold         INTEGER,
        sonusDsx3ThresholdDayCriticalPSESThreshold          INTEGER,
        sonusDsx3ThresholdDayCriticalUASThreshold         INTEGER,
        sonusDsx3ThresholdLCVTcaFilter  SonusAdminState,
        sonusDsx3ThresholdLESTcaFilter  SonusAdminState,
        sonusDsx3ThresholdLSESTcaFilter SonusAdminState,
        sonusDsx3ThresholdPCVTcaFilter  SonusAdminState,
        sonusDsx3ThresholdPESTcaFilter  SonusAdminState,
        sonusDsx3ThresholdPSESTcaFilter SonusAdminState,
        sonusDsx3ThresholdUASTcaFilter  SonusAdminState,
        sonusDsx3ThresholdReportMinorCriticalTca        SonusAdminState,
        sonusDsx3ThresholdReportDs3OosTca SonusAdminState
    }

sonusDsx3ThresholdShelfIndex OBJECT-TYPE
    SYNTAX          SonusShelfIndex
    ACCESS          read-only
    STATUS          mandatory
    DESCRIPTION     
            "Shelf index for this table"
    ::= { sonusDsx3ThresholdEntry 1 }

sonusDsx3ThresholdSlotIndex OBJECT-TYPE
    SYNTAX          SonusSlotIndex
    ACCESS          read-only
    STATUS          mandatory
    DESCRIPTION     
            "Slot index for this table"
    ::= { sonusDsx3ThresholdEntry 2 }

sonusDsx3ThresholdPortIndex OBJECT-TYPE
    SYNTAX          INTEGER
    ACCESS          read-only
    STATUS          mandatory
    DESCRIPTION     
            "Port index for this table"
    ::= { sonusDsx3ThresholdEntry 3 }

sonusDsx3ThresholdDs3Index OBJECT-TYPE
    SYNTAX          INTEGER
    ACCESS          read-only
    STATUS          mandatory
    DESCRIPTION     
            "Ds3 Index into this table"
    ::= { sonusDsx3ThresholdEntry 4 }

sonusDsx3ThresholdMinorLCVThreshold OBJECT-TYPE
    SYNTAX          INTEGER (1..16383)
    ACCESS          read-write
    STATUS          mandatory
    DESCRIPTION     
            "Line Code Violations Minor threshold value for 15 minute interval."
    DEFVAL          { 310 }
    ::= { sonusDsx3ThresholdEntry 5 }

sonusDsx3ThresholdMinorLESThreshold OBJECT-TYPE
    SYNTAX          INTEGER (1..900)
    ACCESS          read-write
    STATUS          mandatory
    DESCRIPTION     
            "Line Errored Seconds Minor threshold value for 15 minute interval."
    DEFVAL          { 20 }
    ::= { sonusDsx3ThresholdEntry 6 }

sonusDsx3ThresholdMinorLSESThreshold OBJECT-TYPE
    SYNTAX          INTEGER (1..900)
    ACCESS          read-write
    STATUS          mandatory
    DESCRIPTION     
            "Line Severely Errored Seconds Minor threshold value for 15 minute interval."
    DEFVAL          { 3 }
    ::= { sonusDsx3ThresholdEntry 7 }

sonusDsx3ThresholdMinorPCVThreshold OBJECT-TYPE
    SYNTAX          INTEGER (1..16383)
    ACCESS          read-write
    STATUS          mandatory
    DESCRIPTION     
            "Path Code Violations Minor threshold value for 15 minute interval, for both
             P-bit and CP-bit."
    DEFVAL          { 306 }
    ::= { sonusDsx3ThresholdEntry 8 }

sonusDsx3ThresholdMinorPESThreshold OBJECT-TYPE
    SYNTAX          INTEGER (1..900)
    ACCESS          read-write
    STATUS          mandatory
    DESCRIPTION     
            "Path Errored Seconds Minor threshold value for 15 minute interval, for both
             P-bit and CP-bit."
    DEFVAL          { 20 }
    ::= { sonusDsx3ThresholdEntry 9 }

sonusDsx3ThresholdMinorPSESThreshold OBJECT-TYPE
    SYNTAX          INTEGER (1..900)
    ACCESS          read-write
    STATUS          mandatory
    DESCRIPTION     
            "Path Severely Errored Seconds Minor threshold value for 15 minute interval, for both
             P-bit and CP-bit."
    DEFVAL          { 3 }
    ::= { sonusDsx3ThresholdEntry 10 }

sonusDsx3ThresholdMinorUASThreshold OBJECT-TYPE
    SYNTAX          INTEGER (1..900)
    ACCESS          read-write
    STATUS          mandatory
    DESCRIPTION     
            "Path Unavailable Seconds Minor threshold value for 15 minute interval, for both
             P-bit and CP-bit."
    DEFVAL          { 8 }
    ::= { sonusDsx3ThresholdEntry 11 }

sonusDsx3ThresholdDayMinorLCVThreshold OBJECT-TYPE
    SYNTAX          INTEGER (1..1048575)
    ACCESS          read-write
    STATUS          mandatory
    DESCRIPTION     
            "Line Code Violations Minor threshold value for 24 hour interval."
    DEFVAL          { 3092 }
    ::= { sonusDsx3ThresholdEntry 12 }

sonusDsx3ThresholdDayMinorLESThreshold OBJECT-TYPE
    SYNTAX          INTEGER (1..65535)
    ACCESS          read-write
    STATUS          mandatory
    DESCRIPTION     
            "Line Errored Seconds Minor threshold value for 24 hour interval."
    DEFVAL          { 200 }
    ::= { sonusDsx3ThresholdEntry 13 }

sonusDsx3ThresholdDayMinorLSESThreshold OBJECT-TYPE
    SYNTAX          INTEGER (1..65535)
    ACCESS          read-write
    STATUS          mandatory
    DESCRIPTION     
            "Line Severely Errored Seconds Minor threshold value for 24 hour interval."
    DEFVAL          { 32 }
    ::= { sonusDsx3ThresholdEntry 14 }

sonusDsx3ThresholdDayMinorPCVThreshold OBJECT-TYPE
    SYNTAX          INTEGER (1..65535)
    ACCESS          read-write
    STATUS          mandatory
    DESCRIPTION     
            "Path Code Violations Minor threshold value for 24 hour interval, for both
             P-bit and CP-bit."
    DEFVAL          { 3056 }
    ::= { sonusDsx3ThresholdEntry 15 }

sonusDsx3ThresholdDayMinorPESThreshold OBJECT-TYPE
    SYNTAX          INTEGER (1..65535)
    ACCESS          read-write
    STATUS          mandatory
    DESCRIPTION     
            "Path Errored Seconds Minor threshold value for 24 hour interval, for both
             P-bit and CP-bit."
    DEFVAL          { 200 }
    ::= { sonusDsx3ThresholdEntry 16 }

sonusDsx3ThresholdDayMinorPSESThreshold OBJECT-TYPE
    SYNTAX          INTEGER (1..65535)
    ACCESS          read-write
    STATUS          mandatory
    DESCRIPTION     
            "Path Severely Errored Seconds Minor threshold value for 24 hour interval, for both
             P-bit and CP-bit."
    DEFVAL          { 32 }
    ::= { sonusDsx3ThresholdEntry 17 }

sonusDsx3ThresholdDayMinorUASThreshold OBJECT-TYPE
    SYNTAX          INTEGER (1..65535)
    ACCESS          read-write
    STATUS          mandatory
    DESCRIPTION     
            "Path Unavailable Seconds Minor threshold value for 24 hour interval, for both
             P-bit and CP-bit."
    DEFVAL          { 8 }
    ::= { sonusDsx3ThresholdEntry 18 }

sonusDsx3ThresholdMajorLCVThreshold OBJECT-TYPE
    SYNTAX          INTEGER (1..16383)
    ACCESS          read-write
    STATUS          mandatory
    DESCRIPTION     
            "Line Code Violations Major threshold value for 15 minute interval."
    DEFVAL          { 387 }
    ::= { sonusDsx3ThresholdEntry 19 }

sonusDsx3ThresholdMajorLESThreshold OBJECT-TYPE
    SYNTAX          INTEGER (1..900)
    ACCESS          read-write
    STATUS          mandatory
    DESCRIPTION     
            "Line Errored Seconds Major threshold value for 15 minute interval."
    DEFVAL          { 25 }
    ::= { sonusDsx3ThresholdEntry 20 }

sonusDsx3ThresholdMajorLSESThreshold OBJECT-TYPE
    SYNTAX          INTEGER (1..900)
    ACCESS          read-write
    STATUS          mandatory
    DESCRIPTION     
            "Line Severely Errored Seconds Major threshold value for 15 minute interval."
    DEFVAL          { 4 }
    ::= { sonusDsx3ThresholdEntry 21 }

sonusDsx3ThresholdMajorPCVThreshold OBJECT-TYPE
    SYNTAX          INTEGER (1..16383)
    ACCESS          read-write
    STATUS          mandatory
    DESCRIPTION     
            "Path Code Violations Major threshold value for 15 minute interval, for both
             P-bit and CP-bit."
    DEFVAL          { 382 }
    ::= { sonusDsx3ThresholdEntry 22 }

sonusDsx3ThresholdMajorPESThreshold OBJECT-TYPE
    SYNTAX          INTEGER (1..900)
    ACCESS          read-write
    STATUS          mandatory
    DESCRIPTION     
            "Path Errored Seconds Major threshold value for 15 minute interval, for both
             P-bit and CP-bit."
    DEFVAL          { 25 }
    ::= { sonusDsx3ThresholdEntry 23 }

sonusDsx3ThresholdMajorPSESThreshold OBJECT-TYPE
    SYNTAX          INTEGER (1..900)
    ACCESS          read-write
    STATUS          mandatory
    DESCRIPTION     
            "Path Severely Errored Seconds Major threshold value for 15 minute interval, for both
             P-bit and CP-bit."
    DEFVAL          { 4 }
    ::= { sonusDsx3ThresholdEntry 24 }

sonusDsx3ThresholdMajorUASThreshold OBJECT-TYPE
    SYNTAX          INTEGER (1..900)
    ACCESS          read-write
    STATUS          mandatory
    DESCRIPTION     
            "Path Unavailable Seconds Major threshold value for 15 minute interval, for both
             P-bit and CP-bit."
    DEFVAL          { 10 }
    ::= { sonusDsx3ThresholdEntry 25 }

sonusDsx3ThresholdDayMajorLCVThreshold OBJECT-TYPE
    SYNTAX          INTEGER (1..1048575)
    ACCESS          read-write
    STATUS          mandatory
    DESCRIPTION     
            "Line Code Violations Major threshold value for 24 hour interval."
    DEFVAL          { 3865 }
    ::= { sonusDsx3ThresholdEntry 26 }

sonusDsx3ThresholdDayMajorLESThreshold OBJECT-TYPE
    SYNTAX          INTEGER (1..65535)
    ACCESS          read-write
    STATUS          mandatory
    DESCRIPTION     
            "Line Errored Seconds Major threshold value for 24 hour interval."
    DEFVAL          { 250 }
    ::= { sonusDsx3ThresholdEntry 27 }

sonusDsx3ThresholdDayMajorLSESThreshold OBJECT-TYPE
    SYNTAX          INTEGER (1..65535)
    ACCESS          read-write
    STATUS          mandatory
    DESCRIPTION     
            "Line Severely Errored Seconds Major threshold value for 24 hour interval."
    DEFVAL          { 40 }
    ::= { sonusDsx3ThresholdEntry 28 }

sonusDsx3ThresholdDayMajorPCVThreshold OBJECT-TYPE
    SYNTAX          INTEGER (1..65535)
    ACCESS          read-write
    STATUS          mandatory
    DESCRIPTION     
            "Path Code Violations Major threshold value for 24 hour interval, for both
             P-bit and CP-bit."
    DEFVAL          { 3820 }
    ::= { sonusDsx3ThresholdEntry 29 }

sonusDsx3ThresholdDayMajorPESThreshold OBJECT-TYPE
    SYNTAX          INTEGER (1..65535)
    ACCESS          read-write
    STATUS          mandatory
    DESCRIPTION     
            "Path Errored Seconds Major threshold value for 24 hour interval, for both
             P-bit and CP-bit."
    DEFVAL          { 250 }
    ::= { sonusDsx3ThresholdEntry 30 }

sonusDsx3ThresholdDayMajorPSESThreshold OBJECT-TYPE
    SYNTAX          INTEGER (1..65535)
    ACCESS          read-write
    STATUS          mandatory
    DESCRIPTION     
            "Path Severely Errored Seconds Major threshold value for 24 hour interval, for both
             P-bit and CP-bit."
    DEFVAL          { 40 }
    ::= { sonusDsx3ThresholdEntry 31 }

sonusDsx3ThresholdDayMajorUASThreshold OBJECT-TYPE
    SYNTAX          INTEGER (1..65535)
    ACCESS          read-write
    STATUS          mandatory
    DESCRIPTION     
            "Path Unavailable Seconds Major threshold value for 24 hour interval, for both
             P-bit and CP-bit."
    DEFVAL          { 10 }
    ::= { sonusDsx3ThresholdEntry 32 }

sonusDsx3ThresholdCriticalLCVThreshold OBJECT-TYPE
    SYNTAX          INTEGER (1..16383)
    ACCESS          read-write
    STATUS          mandatory
    DESCRIPTION     
            "Line Code Violations Critical threshold value for 15 minute interval."
    DEFVAL          { 464 }
    ::= { sonusDsx3ThresholdEntry 33 }

sonusDsx3ThresholdCriticalLESThreshold OBJECT-TYPE
    SYNTAX          INTEGER (1..900)
    ACCESS          read-write
    STATUS          mandatory
    DESCRIPTION     
            "Line Errored Seconds Critical threshold value for 15 minute interval."
    DEFVAL          { 30 }
    ::= { sonusDsx3ThresholdEntry 34 }

sonusDsx3ThresholdCriticalLSESThreshold OBJECT-TYPE
    SYNTAX          INTEGER (1..900)
    ACCESS          read-write
    STATUS          mandatory
    DESCRIPTION     
            "Line Severely Errored Seconds Critical threshold value for 15 minute interval."
    DEFVAL          { 5 }
    ::= { sonusDsx3ThresholdEntry 35 }

sonusDsx3ThresholdCriticalPCVThreshold OBJECT-TYPE
    SYNTAX          INTEGER (1..16383)
    ACCESS          read-write
    STATUS          mandatory
    DESCRIPTION     
            "Path Code Violations Critical threshold value for 15 minute interval, for both
             P-bit and CP-bit."
    DEFVAL          { 458 }
    ::= { sonusDsx3ThresholdEntry 36 }

sonusDsx3ThresholdCriticalPESThreshold OBJECT-TYPE
    SYNTAX          INTEGER (1..900)
    ACCESS          read-write
    STATUS          mandatory
    DESCRIPTION     
            "Path Errored Seconds Critical threshold value for 15 minute interval, for both
             P-bit and CP-bit."
    DEFVAL          { 30 }
    ::= { sonusDsx3ThresholdEntry 37 }

sonusDsx3ThresholdCriticalPSESThreshold OBJECT-TYPE
    SYNTAX          INTEGER (1..900)
    ACCESS          read-write
    STATUS          mandatory
    DESCRIPTION     
            "Path Severely Errored Seconds Critical threshold value for 15 minute interval, for both
             P-bit and CP-bit."
    DEFVAL          { 5 }
    ::= { sonusDsx3ThresholdEntry 38 }

sonusDsx3ThresholdCriticalUASThreshold OBJECT-TYPE
    SYNTAX          INTEGER (1..900)
    ACCESS          read-write
    STATUS          mandatory
    DESCRIPTION     
            "Path Unavailable Seconds Critical threshold value for 15 minute interval, for both
             P-bit and CP-bit."
    DEFVAL          { 12 }
    ::= { sonusDsx3ThresholdEntry 39 }

sonusDsx3ThresholdDayCriticalLCVThreshold OBJECT-TYPE
    SYNTAX          INTEGER (1..1048575)
    ACCESS          read-write
    STATUS          mandatory
    DESCRIPTION     
            "Line Code Violations Critical threshold value for 24 hour interval."
    DEFVAL          { 4638 }
    ::= { sonusDsx3ThresholdEntry 40 }

sonusDsx3ThresholdDayCriticalLESThreshold OBJECT-TYPE
    SYNTAX          INTEGER (1..65535)
    ACCESS          read-write
    STATUS          mandatory
    DESCRIPTION     
            "Line Errored Seconds Critical threshold value for 24 hour interval."
    DEFVAL          { 300 }
    ::= { sonusDsx3ThresholdEntry 41 }

sonusDsx3ThresholdDayCriticalLSESThreshold OBJECT-TYPE
    SYNTAX          INTEGER (1..65535)
    ACCESS          read-write
    STATUS          mandatory
    DESCRIPTION     
            "Line Severely Errored Seconds Critical threshold value for 24 hour interval."
    DEFVAL          { 48 }
    ::= { sonusDsx3ThresholdEntry 42 }

sonusDsx3ThresholdDayCriticalPCVThreshold OBJECT-TYPE
    SYNTAX          INTEGER (1..65535)
    ACCESS          read-write
    STATUS          mandatory
    DESCRIPTION     
            "Path Code Violations Critical threshold value for 24 hour interval, for both
             P-bit and CP-bit."
    DEFVAL          { 4584 }
    ::= { sonusDsx3ThresholdEntry 43 }

sonusDsx3ThresholdDayCriticalPESThreshold OBJECT-TYPE
    SYNTAX          INTEGER (1..65535)
    ACCESS          read-write
    STATUS          mandatory
    DESCRIPTION     
            "Path Errored Seconds Critical threshold value for 24 hour interval, for both
             P-bit and CP-bit."
    DEFVAL          { 300 }
    ::= { sonusDsx3ThresholdEntry 44 }

sonusDsx3ThresholdDayCriticalPSESThreshold OBJECT-TYPE
    SYNTAX          INTEGER (1..65535)
    ACCESS          read-write
    STATUS          mandatory
    DESCRIPTION     
            "Path Severely Errored Seconds Critical threshold value for 24 hour interval, for both
             P-bit and CP-bit."
    DEFVAL          { 48 }
    ::= { sonusDsx3ThresholdEntry 45 }

sonusDsx3ThresholdDayCriticalUASThreshold OBJECT-TYPE
    SYNTAX          INTEGER (1..65535)
    ACCESS          read-write
    STATUS          mandatory
    DESCRIPTION     
            "Path Unavailable Seconds Critical threshold value for 24 hour interval, for both
             P-bit and CP-bit."
    DEFVAL          { 12 }
    ::= { sonusDsx3ThresholdEntry 46 }

sonusDsx3ThresholdLCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 47 }

sonusDsx3ThresholdLESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 48 }

sonusDsx3ThresholdLSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 49 }

sonusDsx3ThresholdPCVTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 50 }

sonusDsx3ThresholdPESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 51 }

sonusDsx3ThresholdPSESTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 52 }

sonusDsx3ThresholdUASTcaFilter OBJECT-TYPE
    SYNTAX          SonusAdminState
    ACCESS          read-write
    STATUS          mandatory
    DESCRIPTION     
            "Controls whether a threshold Crossing Alert (TCA) is reported (via
             an event log and trap). Setting this object to Enabled will prevent
             the TCA from being reported (i.e will Filter the TCA report)."
    DEFVAL          { disabled }
    ::= { sonusDsx3ThresholdEntry 53 }

sonusDsx3ThresholdReportMinorCriticalTca OBJECT-TYPE
    SYNTAX          SonusAdminState
    ACCESS          read-write
    STATUS          mandatory
    DESCRIPTION     
            "Controls whether Minor-level and Critical-level threshold Crossing
             Alerts (TCA) are reported (via an event log and trap). Setting this
             object to Disabled will prevent all Minor and Critical TCAs from being
             reported."
    DEFVAL          { disabled }
    ::= { sonusDsx3ThresholdEntry 54 }

sonusDsx3ThresholdReportDs3OosTca OBJECT-TYPE
    SYNTAX          SonusAdminState
    ACCESS          read-write
    STATUS          mandatory
    DESCRIPTION     
            "Controls whether threshold Crossing Alerts (TCA) are reported
             (via an event log and trap) while the DS3 is Out of Service. Setting
             this object to Enabled allows TCAs to be reported while the DS3 is
             Out of Service."
    DEFVAL          { disabled }
    ::= { sonusDsx3ThresholdEntry 55 }

sonusDs3PmonIntervalType OBJECT-TYPE
    SYNTAX          INTEGER { fifteenMin(1), day(2) }
    ACCESS          read-only
    STATUS          mandatory
    DESCRIPTION     
            "Pmon interval type."
    ::= { sonusDsx3MIBNotificationsObjects 6 }

sonusDsx3ThresholdCrossingNotification TRAP-TYPE
    ENTERPRISE      sonusDsx3MIBNotifications
    VARIABLES       { sonusShelfIndex, sonusSlotIndex, sonusPortIndex, 
                      sonusDs3Index, sonusDs3ThresholdType, 
                      sonusEventDescription, sonusEventClass, 
                      sonusEventLevel, sonusSequenceId, sonusEventTime }
--     STATUS          mandatory
    DESCRIPTION     
            "A sonusDsx3ThresholdCrossingNotification trap indicates that a DS3
             threshold has been crossed. The type indicates the type of threshold."
    ::= 3

sonusDsx3PerfmonIntervalStartedNotification TRAP-TYPE
    ENTERPRISE      sonusDsx3MIBNotifications
    VARIABLES       { sonusShelfIndex, sonusSlotIndex, sonusPortIndex, 
                      sonusDs3Index, sonusDs3PmonIntervalType, 
                      sonusEventDescription, sonusEventClass, 
                      sonusEventLevel, sonusSequenceId, sonusEventTime }
--     STATUS          mandatory
    DESCRIPTION     
            "A  sonusDsx3PerfmonIntervalStartedNotification trap indicates that a new
             15 minute or 24 hour performance monitoring interval has started."
    ::= 5

END -- end of module SONUS-DS3THRESHOLD-MIB.
