--
-- This SMIv1 module has been generated by smidump 0.2-cvs. Do not edit.
--

SONUS-SOFTSWITCH-CLIENT-SERVICES-MIB DEFINITIONS ::= BEGIN

IMPORTS
    Ipv6Address
        FROM IPV6-TC
    OBJECT-TYPE
        FROM RFC-1212
    TRAP-TYPE
        FROM RFC-1215
    Counter, IpAddress
        FROM RFC1155-SMI
    DisplayString, RowStatus
        FROM SNMPv2-TC
    sonusEventClass, sonusEventDescription, sonusEventLevel, 
    sonusEventTime, sonusSequenceId
        FROM SONUS-COMMON-MIB
    sonusServicesMIBs
        FROM SONUS-SMI
    SonusAdminState, SonusName, SonusNameReference
        FROM SONUS-TC;

sonusSoftswitchClientServicesMIB OBJECT IDENTIFIER
    ::= { sonusServicesMIBs 6 }

-- sonusSoftswitchClientServicesMIB MODULE-IDENTITY
--     LAST-UPDATED    "201209070000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for Softswitch Client Services Management."
--     ::= { sonusServicesMIBs 6 }


sonusSoftswitchClientServicesMIBObjects OBJECT IDENTIFIER
    ::= { sonusSoftswitchClientServicesMIB 1 }

sonusSoftswitch OBJECT IDENTIFIER
    ::= { sonusSoftswitchClientServicesMIBObjects 1 }

sonusPscsConfigObjects OBJECT IDENTIFIER
    ::= { sonusSoftswitch 1 }

sonusPscsReconnectTimeOut OBJECT-TYPE
    SYNTAX          INTEGER (1..3600)
    ACCESS          read-write
    STATUS          mandatory
    DESCRIPTION     
            "The timer parameter for re-attempting connection to a Softswitch  
             that is in the enabled state in seconds."
    DEFVAL          { 10 }
    ::= { sonusPscsConfigObjects 1 }

sonusPscsSwitchOver OBJECT-TYPE
    SYNTAX          INTEGER { automatic(1), manual(2) }
    ACCESS          read-write
    STATUS          mandatory
    DESCRIPTION     
            "Automatic means retries to the previously ACTIVE Softswitch after a switch over."
    DEFVAL          { automatic }
    ::= { sonusPscsConfigObjects 2 }

sonusPscsCongestionControl OBJECT-TYPE
    SYNTAX          INTEGER { enabled(1), disabled(2) }
    ACCESS          read-write
    STATUS          mandatory
    DESCRIPTION     
            "The GSX throttles the sending or Policy Requests to either active or standby PSX when this field is enabled."
    DEFVAL          { disabled }
    ::= { sonusPscsConfigObjects 3 }

sonusPscsNifGroupName OBJECT-TYPE
    SYNTAX          SonusNameReference
    ACCESS          read-write
    STATUS          mandatory
    DESCRIPTION     
            "The NIF Group to use for communicating with PSXes. If empty, use any NIF."
    ::= { sonusPscsConfigObjects 4 }

sonusPscsUdpChecksumState OBJECT-TYPE
    SYNTAX          SonusAdminState
    ACCESS          read-write
    STATUS          mandatory
    DESCRIPTION     
            "UDP packet checksum flag is set/clear while communication with PXEs"
    DEFVAL          { disabled }
    ::= { sonusPscsConfigObjects 5 }

sonusPscsRetryServerCount OBJECT-TYPE
    SYNTAX          INTEGER (0..10)
    ACCESS          read-write
    STATUS          mandatory
    DESCRIPTION     
            "The number of servers that has to be retried on policy request timeout."
    DEFVAL          { 1 }
    ::= { sonusPscsConfigObjects 6 }

sonusPscsAdmn OBJECT IDENTIFIER
    ::= { sonusSoftswitch 2 }

sonusPscsAdmnNextIndex OBJECT-TYPE
    SYNTAX          INTEGER
    ACCESS          read-only
    STATUS          mandatory
    DESCRIPTION     
            "The next valid index to use when creating a new sonusPscsAdmnEntry"
    ::= { sonusPscsAdmn 1 }

sonusPscsAdmnTable OBJECT-TYPE
    SYNTAX          SEQUENCE OF SonusPscsAdmnEntry
    ACCESS          not-accessible
    STATUS          mandatory
    DESCRIPTION     
            "Table of Softswitch admin configurations."
    ::= { sonusPscsAdmn 2 }

sonusPscsAdmnEntry OBJECT-TYPE
    SYNTAX          SonusPscsAdmnEntry
    ACCESS          not-accessible
    STATUS          mandatory
    DESCRIPTION     
            "List of Softswitch configuration parameters."
    INDEX           { sonusPscsPolicyServerIndex }
    ::= { sonusPscsAdmnTable 1 }

SonusPscsAdmnEntry ::=
    SEQUENCE {
        sonusPscsPolicyServerIndex      INTEGER,
        sonusPscsPolicyServerName       SonusName,
        sonusPscsPolicyServerIpAddress  IpAddress,
        sonusPscsPolicyServerPortNum    INTEGER,
        sonusPscsPolicyServerAdmnState  INTEGER,
        sonusPscsPolicyServerMode       INTEGER,
        sonusPscsPolicyServerAction     INTEGER,
        sonusPscsTransactionTimer       INTEGER,
        sonusPscsKeepAliveTimer         INTEGER,
        sonusPscsRetryTimer             INTEGER,
        sonusPscsRetries                INTEGER,
        sonusPscsPolicyServerRowStatus  RowStatus,
        sonusPscsPolicyServerSubDataPortNum   INTEGER,
        sonusPscsPolicyServerIp6Address Ipv6Address,
        sonusPscsPolicyServerIpVersion  INTEGER
    }

sonusPscsPolicyServerIndex OBJECT-TYPE
    SYNTAX          INTEGER
    ACCESS          read-only
    STATUS          mandatory
    DESCRIPTION     
            "Identifies the Softswitch entry."
    ::= { sonusPscsAdmnEntry 1 }

sonusPscsPolicyServerName OBJECT-TYPE
    SYNTAX          SonusName
    ACCESS          read-write
    STATUS          mandatory
    DESCRIPTION     
            "The name of this Softswitch."
    ::= { sonusPscsAdmnEntry 2 }

sonusPscsPolicyServerIpAddress OBJECT-TYPE
    SYNTAX          IpAddress
    ACCESS          read-write
    STATUS          mandatory
    DESCRIPTION     
            "IP Address of the Softswitch - this is a required parameter."
    DEFVAL          { 0 }
    ::= { sonusPscsAdmnEntry 3 }

sonusPscsPolicyServerPortNum OBJECT-TYPE
    SYNTAX          INTEGER (1..65535)
    ACCESS          read-write
    STATUS          mandatory
    DESCRIPTION     
            "This is the port number assigned for the Ip address of the Softswitch."
    DEFVAL          { 3055 }
    ::= { sonusPscsAdmnEntry 4 }

sonusPscsPolicyServerAdmnState OBJECT-TYPE
    SYNTAX          INTEGER { disabled(1), enabled(2) }
    ACCESS          read-write
    STATUS          mandatory
    DESCRIPTION     
            "Admin State (disabled or enabled) of the Softswitch."
    DEFVAL          { disabled }
    ::= { sonusPscsAdmnEntry 5 }

sonusPscsPolicyServerMode OBJECT-TYPE
    SYNTAX          INTEGER { active(1), standby(2), outOfService(3), 
                        alternate(4), test(5) }
    ACCESS          read-write
    STATUS          mandatory
    DESCRIPTION     
            "Assignment of the Softswitch to have the active, standby, out of service,
             alternate or test role. This is the only parameter that may be changed when
             the Softswitch is ENABLED."
    DEFVAL          { outOfService }
    ::= { sonusPscsAdmnEntry 6 }

sonusPscsPolicyServerAction OBJECT-TYPE
    SYNTAX          INTEGER { dryUp(1), force(2) }
    ACCESS          read-write
    STATUS          mandatory
    DESCRIPTION     
            "Action assignment of this Softswitch to dry up or remove all the pending transactions 
             when the sonusPscsPolicyServerMode is set to out of service."
    DEFVAL          { dryUp }
    ::= { sonusPscsAdmnEntry 7 }

sonusPscsTransactionTimer OBJECT-TYPE
    SYNTAX          INTEGER (50..60000)
    ACCESS          read-write
    STATUS          mandatory
    DESCRIPTION     
            "The time in milliseconds that the GSX waits for a response from the Softswitch
             after sending it a transaction request."
    DEFVAL          { 2500 }
    ::= { sonusPscsAdmnEntry 8 }

sonusPscsKeepAliveTimer OBJECT-TYPE
    SYNTAX          INTEGER (1..60)
    ACCESS          read-write
    STATUS          mandatory
    DESCRIPTION     
            "The time in seconds between sending Keep Alive indications to the Softswitch."
    DEFVAL          { 5 }
    ::= { sonusPscsAdmnEntry 9 }

sonusPscsRetryTimer OBJECT-TYPE
    SYNTAX          INTEGER (50..60000)
    ACCESS          read-write
    STATUS          mandatory
    DESCRIPTION     
            "The time in milliseconds that the GSX waits for a response from the Softswitch
             after retransmitting the transaction request."
    DEFVAL          { 2500 }
    ::= { sonusPscsAdmnEntry 10 }

sonusPscsRetries OBJECT-TYPE
    SYNTAX          INTEGER (0..32)
    ACCESS          read-write
    STATUS          mandatory
    DESCRIPTION     
            "The maximum number of retransmission attempts for a transaction on this Softswitch."
    DEFVAL          { 1 }
    ::= { sonusPscsAdmnEntry 11 }

sonusPscsPolicyServerRowStatus OBJECT-TYPE
    SYNTAX          RowStatus
    ACCESS          read-write
    STATUS          mandatory
    DESCRIPTION     
            "This is for SNMP use."
    ::= { sonusPscsAdmnEntry 12 }

sonusPscsPolicyServerSubDataPortNum OBJECT-TYPE
    SYNTAX          INTEGER (1..65535)
    ACCESS          read-write
    STATUS          mandatory
    DESCRIPTION     
            "This is the port number assigned for the Ip address of the Softswitch
             for the specific purpose of communicating subscriber data."
    DEFVAL          { 3053 }
    ::= { sonusPscsAdmnEntry 13 }

sonusPscsPolicyServerIp6Address OBJECT-TYPE
    SYNTAX          Ipv6Address
    ACCESS          read-write
    STATUS          mandatory
    DESCRIPTION     
            "IP Address of the Softswitch - this is a required parameter."
    ::= { sonusPscsAdmnEntry 14 }

sonusPscsPolicyServerIpVersion OBJECT-TYPE
    SYNTAX          INTEGER { afInet(2), afInet6(24) }
    ACCESS          read-only
    STATUS          mandatory
    DESCRIPTION     
            "IP Address type  of the Softswitch ."
    ::= { sonusPscsAdmnEntry 15 }

sonusPscsStatusTable OBJECT-TYPE
    SYNTAX          SEQUENCE OF SonusPscsStatusEntry
    ACCESS          not-accessible
    STATUS          mandatory
    DESCRIPTION     
            "Status Table of the Softswitch"
    ::= { sonusSoftswitch 3 }

sonusPscsStatusEntry OBJECT-TYPE
    SYNTAX          SonusPscsStatusEntry
    ACCESS          not-accessible
    STATUS          mandatory
    DESCRIPTION     
            "List of Softswitch status elements."
    INDEX           { sonusPscsStatusIndex }
    ::= { sonusPscsStatusTable 1 }

SonusPscsStatusEntry ::=
    SEQUENCE {
        sonusPscsStatusIndex            INTEGER,
        sonusPscsOperState              INTEGER,
        sonusPscsAverageTransactionTime INTEGER,
        sonusPscsServerReconnects       Counter,
--         sonusPscsTransactionCompleted   Counter64,
        sonusPscsTransactionRetryAttempts Counter,
        sonusPscsTransactionFailedAttempts  Counter,
        sonusPscsVersion                INTEGER,
        sonusPscsRedirectRequests       Counter,
        sonusPscsReleaseRequests        Counter,
        sonusPscsDataRequests           Counter,
        sonusPscsQueriesSkippedAndServiced  Counter,
        sonusPscsQueriesSkippedAndRejected  Counter,
        sonusPscsCongestionLevel        INTEGER,
        sonusPscsAllowancePercent       INTEGER
    }

sonusPscsStatusIndex OBJECT-TYPE
    SYNTAX          INTEGER
    ACCESS          read-only
    STATUS          mandatory
    DESCRIPTION     
            "Identifies the Softswitch entry."
    ::= { sonusPscsStatusEntry 1 }

sonusPscsOperState OBJECT-TYPE
    SYNTAX          INTEGER { active(1), standby(2), congested(3), 
                        down(4), dryingup(5), alternate(6), test(7) }
    ACCESS          read-only
    STATUS          mandatory
    DESCRIPTION     
            "Operational state of the Softswitch."
    ::= { sonusPscsStatusEntry 2 }

sonusPscsAverageTransactionTime OBJECT-TYPE
    SYNTAX          INTEGER
    ACCESS          read-only
    STATUS          mandatory
    DESCRIPTION     
            "Records the average time taken in milliseconds for a Softswitch transaction."
    ::= { sonusPscsStatusEntry 3 }

sonusPscsServerReconnects OBJECT-TYPE
    SYNTAX          Counter
    ACCESS          read-only
    STATUS          mandatory
    DESCRIPTION     
            "The number of successful reconnections between the gateway and the Softswitch."
    ::= { sonusPscsStatusEntry 4 }

-- sonusPscsTransactionCompleted OBJECT-TYPE
--     SYNTAX          Counter64
--     ACCESS          read-only
--     STATUS          mandatory
--     DESCRIPTION     
--             "The number of successful transactions between the gateway and the Softswitch."
--     ::= { sonusPscsStatusEntry 5 }

sonusPscsTransactionRetryAttempts OBJECT-TYPE
    SYNTAX          Counter
    ACCESS          read-only
    STATUS          mandatory
    DESCRIPTION     
            "The number of transaction retries between the gateway and the Softswitch."
    ::= { sonusPscsStatusEntry 6 }

sonusPscsTransactionFailedAttempts OBJECT-TYPE
    SYNTAX          Counter
    ACCESS          read-only
    STATUS          mandatory
    DESCRIPTION     
            "The number of un-successful transactions between the gateway and the Softswitch."
    ::= { sonusPscsStatusEntry 7 }

sonusPscsVersion OBJECT-TYPE
    SYNTAX          INTEGER
    ACCESS          read-only
    STATUS          mandatory
    DESCRIPTION     
            "The negotiated protocol version between the gateway and the Softswitch."
    ::= { sonusPscsStatusEntry 8 }

sonusPscsRedirectRequests OBJECT-TYPE
    SYNTAX          Counter
    ACCESS          read-only
    STATUS          mandatory
    DESCRIPTION     
            "The cumulative number of redirect requests received from the Softswitch."
    ::= { sonusPscsStatusEntry 9 }

sonusPscsReleaseRequests OBJECT-TYPE
    SYNTAX          Counter
    ACCESS          read-only
    STATUS          mandatory
    DESCRIPTION     
            "The cumulative number of release-call requests received from the Softswitch."
    ::= { sonusPscsStatusEntry 10 }

sonusPscsDataRequests OBJECT-TYPE
    SYNTAX          Counter
    ACCESS          read-only
    STATUS          mandatory
    DESCRIPTION     
            "The cumulative number of data requests received from the Softswitch."
    ::= { sonusPscsStatusEntry 11 }

sonusPscsQueriesSkippedAndServiced OBJECT-TYPE
    SYNTAX          Counter
    ACCESS          read-only
    STATUS          mandatory
    DESCRIPTION     
            "The cumulative number of Policy Requests serviced by the standby PSX while the active PSX experienced congestion."
    ::= { sonusPscsStatusEntry 12 }

sonusPscsQueriesSkippedAndRejected OBJECT-TYPE
    SYNTAX          Counter
    ACCESS          read-only
    STATUS          mandatory
    DESCRIPTION     
            "The cumulative number of rejected Policy Requests while the active PSX is congested and a standby PSX is either
             congested or not available."
    ::= { sonusPscsStatusEntry 13 }

sonusPscsCongestionLevel OBJECT-TYPE
    SYNTAX          INTEGER { clear(0), low(1), medium(2), high(3) }
    ACCESS          read-only
    STATUS          mandatory
    DESCRIPTION     
            "The PSX congestion level."
    ::= { sonusPscsStatusEntry 14 }

sonusPscsAllowancePercent OBJECT-TYPE
    SYNTAX          INTEGER (0..100)
    ACCESS          read-only
    STATUS          mandatory
    DESCRIPTION     
            "The PSX allowance.  An allowance of 75% for example, means that the GSX is skipping 1 out of every 4 Policy Requests.
             This allowance is provisioned on the PSX and inforced on the GSX when PSX Congestion Control is enabled."
    ::= { sonusPscsStatusEntry 15 }

sonusSoftswitchClientServicesMIBNotifications OBJECT IDENTIFIER
    ::= { sonusSoftswitchClientServicesMIB 2 }

sonusSoftswitchClientServicesMIBNotificationsPrefix OBJECT IDENTIFIER
    ::= { sonusSoftswitchClientServicesMIBNotifications 0 }

sonusSoftswitchClientServicesMIBNotificationsObjects OBJECT IDENTIFIER
    ::= { sonusSoftswitchClientServicesMIBNotifications 1 }

sonusPscsInServiceReason OBJECT-TYPE
    SYNTAX          INTEGER { configured(1), successfulReConnect(2), 
                        automatic(3) }
    ACCESS          read-only
    STATUS          mandatory
    DESCRIPTION     
            "The reason why a softswitch is in service."
    ::= { sonusSoftswitchClientServicesMIBNotificationsObjects 1 }

sonusPscsOutOfServiceReason OBJECT-TYPE
    SYNTAX          INTEGER { configured(1), connectionLoss(2), 
                        noConnection(3), nodeNameChange(4), 
                        incompatibleVersion(5) }
    ACCESS          read-only
    STATUS          mandatory
    DESCRIPTION     
            "The reason why the softswitch is out of service."
    ::= { sonusSoftswitchClientServicesMIBNotificationsObjects 2 }

sonusPscsSwitchoverReason OBJECT-TYPE
    SYNTAX          INTEGER { configured(1), automatic(2), 
                        versionChanged(3) }
    ACCESS          read-only
    STATUS          mandatory
    DESCRIPTION     
            "The reason why the softswitch has switch to be the active softswitch."
    ::= { sonusSoftswitchClientServicesMIBNotificationsObjects 3 }

sonusPscsRouteFailureReason OBJECT-TYPE
    SYNTAX          INTEGER { routeNotFound(1), noServiceConfigured(2), 
                        databaseError(3) }
    ACCESS          read-only
    STATUS          mandatory
    DESCRIPTION     
            "The reason why a route look up has failed."
    ::= { sonusSoftswitchClientServicesMIBNotificationsObjects 4 }

sonusPscsCallInfo OBJECT-TYPE
    SYNTAX          DisplayString
    ACCESS          read-only
    STATUS          mandatory
    DESCRIPTION     
            "Call information content."
    ::= { sonusSoftswitchClientServicesMIBNotificationsObjects 5 }

sonusPscsTranErrorReason OBJECT-TYPE
    SYNTAX          INTEGER { noSoftswitchAvailable(1), 
                        transactionTimeout(2), invalidParameters(3), 
                        receiveError(4), transmitError(5), 
                        encodeApiError(6), decodeApiError(7), 
                        noMatchingReplyCbFound(8) }
    ACCESS          read-only
    STATUS          mandatory
    DESCRIPTION     
            "The reason why a transaction has failed."
    ::= { sonusSoftswitchClientServicesMIBNotificationsObjects 6 }

sonusPscsRejectIndReason OBJECT-TYPE
    SYNTAX          INTEGER { notRegistered(1), unknownGateway(2), 
                        errorAVPContent(3), errorMsgContent(4), 
                        maxClientAccount(5), miscRegFailure(6) }
    ACCESS          read-only
    STATUS          mandatory
    DESCRIPTION     
            "The reason why a reject ind received."
    ::= { sonusSoftswitchClientServicesMIBNotificationsObjects 7 }

sonusPscsCalledNumber OBJECT-TYPE
    SYNTAX          DisplayString
    ACCESS          read-only
    STATUS          mandatory
    DESCRIPTION     
            "Destination number."
    ::= { sonusSoftswitchClientServicesMIBNotificationsObjects 8 }

sonusPscsCallingNumber OBJECT-TYPE
    SYNTAX          DisplayString
    ACCESS          read-only
    STATUS          mandatory
    DESCRIPTION     
            "Originating number."
    ::= { sonusSoftswitchClientServicesMIBNotificationsObjects 9 }

sonusPscsCarrierCode OBJECT-TYPE
    SYNTAX          DisplayString
    ACCESS          read-only
    STATUS          mandatory
    DESCRIPTION     
            "Carrier code."
    ::= { sonusSoftswitchClientServicesMIBNotificationsObjects 10 }

sonusPscsGapNumber OBJECT-TYPE
    SYNTAX          DisplayString
    ACCESS          read-only
    STATUS          mandatory
    DESCRIPTION     
            "Gap number. Valid only in the case of LNP number translation."
    ::= { sonusSoftswitchClientServicesMIBNotificationsObjects 11 }

sonusPscsGcid OBJECT-TYPE
    SYNTAX          INTEGER
    ACCESS          read-only
    STATUS          mandatory
    DESCRIPTION     
            "Represents the call GCID for this session."
    ::= { sonusSoftswitchClientServicesMIBNotificationsObjects 12 }

sonusSscsInServiceNotification TRAP-TYPE
    ENTERPRISE      sonusSoftswitchClientServicesMIBNotifications
    VARIABLES       { sonusPscsPolicyServerName, sonusPscsOperState, 
                      sonusPscsInServiceReason, sonusEventDescription, 
                      sonusEventClass, sonusEventLevel, sonusSequenceId, 
                      sonusEventTime }
--     STATUS          mandatory
    DESCRIPTION     
            "This trap indicates a softswitch is now in service."
    ::= 1

sonusSscsOutOfServiceNotification TRAP-TYPE
    ENTERPRISE      sonusSoftswitchClientServicesMIBNotifications
    VARIABLES       { sonusPscsPolicyServerName, 
                      sonusPscsOutOfServiceReason, sonusEventDescription, 
                      sonusEventClass, sonusEventLevel, sonusSequenceId, 
                      sonusEventTime }
--     STATUS          mandatory
    DESCRIPTION     
            "This trap indicates a softswitch is now out of service."
    ::= 2

sonusSscsSwitchoverNotification TRAP-TYPE
    ENTERPRISE      sonusSoftswitchClientServicesMIBNotifications
    VARIABLES       { sonusPscsPolicyServerName, 
                      sonusPscsSwitchoverReason, sonusEventDescription, 
                      sonusEventClass, sonusEventLevel, sonusSequenceId, 
                      sonusEventTime }
--     STATUS          mandatory
    DESCRIPTION     
            "This trap indicates a softswitch has switched over."
    ::= 3

sonusSscsRouteFailureNotification TRAP-TYPE
    ENTERPRISE      sonusSoftswitchClientServicesMIBNotifications
    VARIABLES       { sonusPscsPolicyServerName, 
                      sonusPscsRouteFailureReason, sonusPscsCalledNumber, 
                      sonusPscsCallingNumber, sonusPscsCarrierCode, 
                      sonusEventDescription, sonusEventClass, 
                      sonusEventLevel, sonusPscsGapNumber, 
                      sonusSequenceId, sonusEventTime }
--     STATUS          mandatory
    DESCRIPTION     
            "This trap indicates a route look up has failed."
    ::= 4

sonusSscsTransErrorNotification TRAP-TYPE
    ENTERPRISE      sonusSoftswitchClientServicesMIBNotifications
    VARIABLES       { sonusPscsPolicyServerName, 
                      sonusPscsTranErrorReason, sonusEventDescription, 
                      sonusEventClass, sonusEventLevel, sonusSequenceId, 
                      sonusEventTime }
--     STATUS          mandatory
    DESCRIPTION     
            "This trap indicates a softswitch has a trans error."
    ::= 5

sonusSscsRejectIndNotification TRAP-TYPE
    ENTERPRISE      sonusSoftswitchClientServicesMIBNotifications
    VARIABLES       { sonusPscsPolicyServerName, 
                      sonusPscsRejectIndReason, sonusEventDescription, 
                      sonusEventClass, sonusEventLevel, sonusSequenceId, 
                      sonusEventTime }
--     STATUS          mandatory
    DESCRIPTION     
            "This trap indicates a reject indication has been received."
    ::= 6

sonusSscsRouteFailureWithoutGapNotification TRAP-TYPE
    ENTERPRISE      sonusSoftswitchClientServicesMIBNotifications
    VARIABLES       { sonusPscsPolicyServerName, 
                      sonusPscsRouteFailureReason, sonusPscsCalledNumber, 
                      sonusPscsCallingNumber, sonusPscsCarrierCode, 
                      sonusEventDescription, sonusEventClass, 
                      sonusEventLevel, sonusSequenceId, sonusEventTime }
--     STATUS          mandatory
    DESCRIPTION     
            "This trap indicates a route look up has failed with out GAP."
    ::= 7

sonusSscsAllPsxOutOfServiceNotification TRAP-TYPE
    ENTERPRISE      sonusSoftswitchClientServicesMIBNotifications
    VARIABLES       { sonusEventDescription, sonusEventClass, 
                      sonusEventLevel, sonusSequenceId, sonusEventTime }
--     STATUS          mandatory
    DESCRIPTION     
            "This trap indicates that all psx softswitchs are now out of service."
    ::= 8

sonusSscsCryptoFailureNotification TRAP-TYPE
    ENTERPRISE      sonusSoftswitchClientServicesMIBNotifications
    VARIABLES       { sonusPscsPolicyServerName, sonusPscsGcid, 
                      sonusEventDescription, sonusEventClass, 
                      sonusEventLevel, sonusSequenceId, sonusEventTime }
--     STATUS          mandatory
    DESCRIPTION     
            "This trap indicates a softswitch has a LI decrypt failure."
    ::= 9

sonusSscsCryptoSuccessNotification TRAP-TYPE
    ENTERPRISE      sonusSoftswitchClientServicesMIBNotifications
    VARIABLES       { sonusPscsPolicyServerName, sonusPscsGcid, 
                      sonusEventDescription, sonusEventClass, 
                      sonusEventLevel, sonusSequenceId, sonusEventTime }
--     STATUS          mandatory
    DESCRIPTION     
            "This trap indicates a softswitch has a LI decrypt Success."
    ::= 10

END -- end of module SONUS-SOFTSWITCH-CLIENT-SERVICES-MIB.
