--
-- This SMIv1 module has been generated by smidump 0.2-cvs. Do not edit.
--

SONUS-LICENSE-MIB DEFINITIONS ::= BEGIN

IMPORTS
    OBJECT-TYPE
        FROM RFC-1212
    TRAP-TYPE
        FROM RFC-1215
    sysName, sysObjectID
        FROM SNMPv2-MIB
    DateAndTime, DisplayString
        FROM SNMPv2-TC
    sonusEventClass, sonusEventDescription, sonusEventLevel, 
    sonusEventTime
        FROM SONUS-COMMON-MIB
    sonusEmsMIB
        FROM SONUS-EMS-MIB;

sonusLicMIB OBJECT IDENTIFIER
    ::= { sonusEmsMIB 3 }

-- sonusLicMIB MODULE-IDENTITY
--     LAST-UPDATED    "201505060000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for Sonus License Manager related objects."
--     ::= { sonusEmsMIB 3 }


sonusLicMIBObjects OBJECT IDENTIFIER
    ::= { sonusLicMIB 1 }

sonusLicNotifications OBJECT IDENTIFIER
    ::= { sonusLicMIB 2 }

sonusLicNotificationsPrefix OBJECT IDENTIFIER
    ::= { sonusLicNotifications 0 }

sonusLicNotificationsObjects OBJECT IDENTIFIER
    ::= { sonusLicNotifications 1 }

sonusLicTargetType OBJECT-TYPE
    SYNTAX          DisplayString
    ACCESS          read-only
    STATUS          mandatory
    DESCRIPTION     
            "The license target type."
    ::= { sonusLicNotificationsObjects 1 }

sonusLicTargetId OBJECT-TYPE
    SYNTAX          DisplayString
    ACCESS          read-only
    STATUS          mandatory
    DESCRIPTION     
            "The license target identifier"
    ::= { sonusLicNotificationsObjects 2 }

sonusLicFeatureId OBJECT-TYPE
    SYNTAX          DisplayString
    ACCESS          read-only
    STATUS          mandatory
    DESCRIPTION     
            "The license feature identifier."
    ::= { sonusLicNotificationsObjects 3 }

sonusLicExpireTime OBJECT-TYPE
    SYNTAX          DateAndTime
    ACCESS          read-only
    STATUS          mandatory
    DESCRIPTION     
            "The date/time when the license expires."
    ::= { sonusLicNotificationsObjects 4 }

sonusLicPresentValue OBJECT-TYPE
    SYNTAX          INTEGER
    ACCESS          read-only
    STATUS          mandatory
    DESCRIPTION     
            "The current license usage."
    ::= { sonusLicNotificationsObjects 5 }

sonusLicConfiguredValue OBJECT-TYPE
    SYNTAX          INTEGER
    ACCESS          read-only
    STATUS          mandatory
    DESCRIPTION     
            "The current configured maximum usage."
    ::= { sonusLicNotificationsObjects 6 }

sonusLicPPDFileName OBJECT-TYPE
    SYNTAX          DisplayString
    ACCESS          read-only
    STATUS          mandatory
    DESCRIPTION     
            "Auto-generated post-paid license usage file name."
    ::= { sonusLicNotificationsObjects 9 }

sonusLicExpiredNotification TRAP-TYPE
    ENTERPRISE      sonusLicNotifications
    VARIABLES       { sonusEventTime, sonusEventDescription, 
                      sonusEventClass, sonusEventLevel, 
                      sonusLicTargetType, sonusLicTargetId, 
                      sonusLicFeatureId, sonusLicExpireTime }
--     STATUS          mandatory
    DESCRIPTION     
            "A license identified by the tuple sonusTargetType, sonusTargetId, and sonusFeatureId has expired as of sonusLicExpireTime."
    ::= 1

sonusLicStatusNotification TRAP-TYPE
    ENTERPRISE      sonusLicNotifications
    VARIABLES       { sonusEventTime, sonusEventDescription, 
                      sonusEventClass, sonusEventLevel, 
                      sonusLicTargetType, sonusLicTargetId, 
                      sonusLicFeatureId, sonusLicExpireTime }
--     STATUS          mandatory
    DESCRIPTION     
            "A license identified by the tuple sonusTargetType, sonusTargetId, and sonusFeatureId will expire as of sonusLicExpireTime."
    ::= 2

sonusLicUsageExceededNotification TRAP-TYPE
    ENTERPRISE      sonusLicNotifications
    VARIABLES       { sonusEventTime, sonusEventDescription, 
                      sonusEventClass, sonusEventLevel, 
                      sonusLicTargetType, sonusLicTargetId, 
                      sonusLicFeatureId, sonusLicPresentValue, 
                      sonusLicConfiguredValue }
--     STATUS          mandatory
    DESCRIPTION     
            "Current usage, sonusLicPresentValue, for the license identified by the tuple sonusTargetType, sonusTargetId, and sonusFeatureId has exceeded the configured maximum value, sonusLicConfiguredValue."
    ::= 3

sonusLicUsageStatusNotification TRAP-TYPE
    ENTERPRISE      sonusLicNotifications
    VARIABLES       { sonusEventTime, sonusEventDescription, 
                      sonusEventClass, sonusEventLevel, 
                      sonusLicTargetType, sonusLicTargetId, 
                      sonusLicFeatureId, sonusLicPresentValue, 
                      sonusLicConfiguredValue }
--     STATUS          mandatory
    DESCRIPTION     
            "Current usage, sonusLicPresentValue, for the license identified by the tuple sonusTargetType, sonusTargetId, and sonusFeatureId is approching the configured maximum value, sonusLicConfiguredValue."
    ::= 4

sonusLicStatusClearNotification TRAP-TYPE
    ENTERPRISE      sonusLicNotifications
    VARIABLES       { sonusEventTime, sonusEventDescription, 
                      sonusEventClass, sonusEventLevel, 
                      sonusLicTargetType, sonusLicTargetId, 
                      sonusLicFeatureId, sonusLicExpireTime }
--     STATUS          mandatory
    DESCRIPTION     
            "Configuration pertaining to pre-expiry has changed resulting in clearing of this pre-expiry notification."
    ::= 5

sonusLicUsageStatusClearNotification TRAP-TYPE
    ENTERPRISE      sonusLicNotifications
    VARIABLES       { sonusEventTime, sonusEventDescription, 
                      sonusEventClass, sonusEventLevel, 
                      sonusLicTargetType, sonusLicTargetId, 
                      sonusLicFeatureId, sonusLicPresentValue, 
                      sonusLicConfiguredValue }
--     STATUS          mandatory
    DESCRIPTION     
            "Current usage, sonusLicPresentValue, for the license identified by the tuple sonusTargetType, sonusTargetId, and sonusFeatureId is now below the configured maximum value, sonusLicConfiguredValue."
    ::= 6

sonusLicSBCLicMismatchNotification TRAP-TYPE
    ENTERPRISE      sonusLicNotifications
    VARIABLES       { sonusEventTime, sonusEventDescription, 
                      sonusEventClass, sonusEventLevel, 
                      sonusLicTargetType }
--     STATUS          mandatory
    DESCRIPTION     
            "Installed license count of SBC-POL-RTU has exceeded that of SBC-RTU."
    ::= 7

sonusLicSBCLicMismatchClearNotification TRAP-TYPE
    ENTERPRISE      sonusLicNotifications
    VARIABLES       { sonusEventTime, sonusEventDescription, 
                      sonusEventClass, sonusEventLevel, 
                      sonusLicTargetType }
--     STATUS          mandatory
    DESCRIPTION     
            "License count mismatch of SBC-RTU and SBC-POL-RTU is rectified. Clear trap for sonusLicSBCLicMismatchNotification."
    ::= 8

sonusLicFailedToSendUsageFileNotification TRAP-TYPE
    ENTERPRISE      sonusLicNotifications
    VARIABLES       { sonusEventTime, sonusEventDescription, 
                      sonusEventClass, sonusEventLevel, 
                      sonusLicPPDFileName }
--     STATUS          mandatory
    DESCRIPTION     
            "Failed to send the autogenerated post-paid license usage file."
    ::= 9

sonusLicFailedToRegisterWithITNotification TRAP-TYPE
    ENTERPRISE      sonusLicNotifications
    VARIABLES       { sonusEventTime, sonusEventDescription, 
                      sonusEventClass, sonusEventLevel }
--     STATUS          mandatory
    DESCRIPTION     
            "Failed to register with IT."
    ::= 10

END -- end of module SONUS-LICENSE-MIB.
