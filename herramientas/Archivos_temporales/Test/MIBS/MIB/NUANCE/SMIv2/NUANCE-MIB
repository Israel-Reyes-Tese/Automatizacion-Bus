--
-- This SMIv2 module has been generated by smidump 0.2-cvs. Do not edit.
--

NUANCE-MIB DEFINITIONS ::= BEGIN

IMPORTS
    Integer32, MODULE-IDENTITY, NOTIFICATION-TYPE, OBJECT-IDENTITY, 
    OBJECT-TYPE, Unsigned32, enterprises
        FROM SNMPv2-SMI
    TEXTUAL-CONVENTION, TruthValue
        FROM SNMPv2-TC;

nuanceMIB MODULE-IDENTITY
    LAST-UPDATED    "197001010000Z"
    ORGANIZATION    
            "Nuance Communications"
    CONTACT-INFO    
            "Email:  support@nuance.com
             Phone:  +1.650.847.0000
             Postal: 1380 Willow Road
                     Menlo Park, CA 94025"
    DESCRIPTION     
            "The MIB module for managing the Nuance system"
    REVISION        "199912020000Z"
    DESCRIPTION     
            "The initial revision of the Nuance MIB module"
    REVISION        "197001010000Z"
    DESCRIPTION     
            "Update for Nuance v8.0"
    ::= { enterprises 3621 }


NTimeVal ::= TEXTUAL-CONVENTION
    STATUS          current
    DESCRIPTION     
            "Represents a local time and date string.  The
             special value '-' indicates an empty value."
    SYNTAX          OCTET STRING (SIZE(1 | 23))

NString ::= TEXTUAL-CONVENTION
    STATUS          current
    DESCRIPTION     
            "Represents an arbitrary string."
    SYNTAX          OCTET STRING (SIZE(0..4096))

watcherDaemonMib OBJECT IDENTIFIER
    ::= { nuanceMIB 100 }

wdControl OBJECT IDENTIFIER
    ::= { watcherDaemonMib 1 }

wdState OBJECT-TYPE
    SYNTAX          INTEGER { readyState(1), quiescingState(2), 
                        goQuiesce(100) }
    MAX-ACCESS      read-write
    STATUS          current
    DESCRIPTION     
            "."
    ::= { wdControl 1 }

wdVpSet OBJECT IDENTIFIER
    ::= { watcherDaemonMib 2 }

vpSetControl OBJECT IDENTIFIER
    ::= { wdVpSet 1 }

startVpArgs OBJECT-TYPE
    SYNTAX          NString
    MAX-ACCESS      read-write
    STATUS          current
    DESCRIPTION     
            "The full command line of the process to start,
             including the executable name.  The typical
             command line looks like:
             'recserver -package ${MY_PACKAGE}'
             In this case, the recserver executable will be
             found using the typical PATH search list.
             The command line may also include a watcher
             argument list of the form:
             '-wa <watcher_args> -pa <process_args>'
             In this case, the <watcher_args> are args to
             configure the way this process is managed, and
             <process_args> is the full command line of the
             process to start, including the executable name."
    ::= { vpSetControl 1 }

startVpState OBJECT-TYPE
    SYNTAX          INTEGER { nullState(1), doneState(2), goStart(100), 
                        goReset(200) }
    MAX-ACCESS      read-write
    STATUS          current
    DESCRIPTION     
            "Control starting a virtual process.  The only valid
             set values are goStart and goReset.  Set to
             goStart to start a process (based on arguments
             supplied in startVpArgs).  After starting and
             the state is doneState, startVpStatus can be
             checked for the status of the start, and
             startVpVpid can be checked for the vpid of the
             process that was started.  Set to goReset to reset
             the startVpStatus and startVpVpid, and reset the
             state back to the nullState."
    ::= { vpSetControl 2 }

startVpStatus OBJECT-TYPE
    SYNTAX          NString
    MAX-ACCESS      read-only
    STATUS          current
    DESCRIPTION     
            "The status of the last attempted start."
    ::= { vpSetControl 3 }

startVpVpid OBJECT-TYPE
    SYNTAX          Unsigned32
    MAX-ACCESS      read-only
    STATUS          current
    DESCRIPTION     
            "The vpid of the last attempted start."
    ::= { vpSetControl 4 }

vpControl OBJECT IDENTIFIER
    ::= { wdVpSet 2 }

vpcCount OBJECT-TYPE
    SYNTAX          Integer32
    MAX-ACCESS      read-only
    STATUS          current
    DESCRIPTION     
            "The number of virtual processes running
             on this machine."
    ::= { vpControl 1 }

vpcList OBJECT-TYPE
    SYNTAX          NString
    MAX-ACCESS      read-only
    STATUS          current
    DESCRIPTION     
            "A space delimited list of the vpids of the
             virtual processes running on this machine."
    ::= { vpControl 2 }

vpcTable OBJECT-TYPE
    SYNTAX          SEQUENCE OF VpcEntry
    MAX-ACCESS      not-accessible
    STATUS          current
    DESCRIPTION     
            "Table of virtual process information."
    ::= { vpControl 3 }

vpcEntry OBJECT-TYPE
    SYNTAX          VpcEntry
    MAX-ACCESS      not-accessible
    STATUS          current
    DESCRIPTION     
            "Information and control for a particular
             virtual process.  This table is indexed by vpceVpid
             (not consecutive), and the total number of conceptual
             rows in this table is vpcCount.  The vpids represented
             in this table are listed in vpcList."
    INDEX           { vpceVpid }
    ::= { vpcTable 1 }

VpcEntry ::=
    SEQUENCE {
        vpceVpid                        Unsigned32,
        vpceVpState                     INTEGER,
        vpceIsWatchable                 TruthValue,
        vpcePVpid                       Unsigned32,
        vpceAssignedTime                NTimeVal,
        vpceRestartOnFailure            TruthValue,
        vpceShutdownOnDaemonQuiesce     TruthValue,
        vpcePingTimeoutMs               Integer32,
        vpcePingTimeoutDelayMs          Integer32,
        vpceMaxMissedPings              Integer32,
        vpceQuiesceTimeoutMs            Integer32,
        vpceFailureQuiesceTimeoutMs     Integer32,
        vpceProcessType                 NString,
        vpceArgc                        Integer32,
        vpceArgv                        NString,
        vpceTotalStarts                 Integer32,
        vpceStartedTime                 NTimeVal,
        vpcePid                         Integer32,
        vpceWPid                        Integer32,
        vpceConsecutivePingsMissed      Integer32,
        vpceTotalPingsMissed            Integer32,
        vpcePingedTime                  NTimeVal,
        vpceIsConnected                 TruthValue,
        vpceStreamRemotePort            Unsigned32,
        vpceRestartAttemptedTime        NTimeVal,
        vpceQuiesceAttemptedTime        NTimeVal,
        vpceQuiescedTime                NTimeVal,
        vpceKillAttemptedTime           NTimeVal,
        vpceDiedTime                    NTimeVal,
        vpceReleasedTime                NTimeVal
    }

vpceVpid OBJECT-TYPE
    SYNTAX          Unsigned32
    MAX-ACCESS      read-only
    STATUS          current
    DESCRIPTION     
            "The virtual process id."
    ::= { vpcEntry 1 }

vpceVpState OBJECT-TYPE
    SYNTAX          INTEGER { nullState(1), startingState(2), 
                        connectingState(3), initializingState(4), 
                        readyState(5), dyingState(6), quiescingState(7), 
                        terminatingState(8), releasingState(9), 
                        goRestart(100), goQuiesce(101), goKill(102) }
    MAX-ACCESS      read-write
    STATUS          current
    DESCRIPTION     
            "The virtual process state.  The only valid set values
             are goRestart, goQuiesce and goKill.  Set to one of
             these values to trigger the appropriate action.
             Check vpceRestartAttemptedTime, vpceQuiesceAttemptedTime
             or vpceKillAttemptedTime to make sure the action was
             attempted."
    ::= { vpcEntry 2 }

vpceIsWatchable OBJECT-TYPE
    SYNTAX          TruthValue
    MAX-ACCESS      read-only
    STATUS          current
    DESCRIPTION     
            "Whether the virtual process is watchable."
    ::= { vpcEntry 3 }

vpcePVpid OBJECT-TYPE
    SYNTAX          Unsigned32
    MAX-ACCESS      read-only
    STATUS          current
    DESCRIPTION     
            "The parent virtual process id."
    ::= { vpcEntry 4 }

vpceAssignedTime OBJECT-TYPE
    SYNTAX          NTimeVal
    MAX-ACCESS      read-only
    STATUS          current
    DESCRIPTION     
            "The assigned time of the virtual process."
    ::= { vpcEntry 5 }

vpceRestartOnFailure OBJECT-TYPE
    SYNTAX          TruthValue
    MAX-ACCESS      read-only
    STATUS          current
    DESCRIPTION     
            "Whether the virtual process will be automatically
             restarted on failure."
    ::= { vpcEntry 6 }

vpceShutdownOnDaemonQuiesce OBJECT-TYPE
    SYNTAX          TruthValue
    MAX-ACCESS      read-only
    STATUS          current
    DESCRIPTION     
            "Whether the virtual process will be shutdown
             (quiesced or killed) when the WatcherDaemon quiesces."
    ::= { vpcEntry 7 }

vpcePingTimeoutMs OBJECT-TYPE
    SYNTAX          Integer32
    MAX-ACCESS      read-only
    STATUS          current
    DESCRIPTION     
            "The ping timeout in milliseconds."
    ::= { vpcEntry 8 }

vpcePingTimeoutDelayMs OBJECT-TYPE
    SYNTAX          Integer32
    MAX-ACCESS      read-only
    STATUS          current
    DESCRIPTION     
            "The ping timeout delay in milliseconds."
    ::= { vpcEntry 9 }

vpceMaxMissedPings OBJECT-TYPE
    SYNTAX          Integer32
    MAX-ACCESS      read-only
    STATUS          current
    DESCRIPTION     
            "The number of max missed pings."
    ::= { vpcEntry 10 }

vpceQuiesceTimeoutMs OBJECT-TYPE
    SYNTAX          Integer32
    MAX-ACCESS      read-only
    STATUS          current
    DESCRIPTION     
            "The quiesce timeout in milliseconds, or the time
             the WatcherDaemon will wait for a quiesce before
             the virtual process is automatically killed.  A
             value of 0 indicates the process will never be
             automatically killed."
    ::= { vpcEntry 11 }

vpceFailureQuiesceTimeoutMs OBJECT-TYPE
    SYNTAX          Integer32
    MAX-ACCESS      read-only
    STATUS          current
    DESCRIPTION     
            "The failure quiesce timeout in milliseconds, or the
             time the WatcherDaemon will wait for a quiesce before
             the virtual process is automatically killed, when the
             quiesce is triggered by a virtual process failure."
    ::= { vpcEntry 12 }

vpceProcessType OBJECT-TYPE
    SYNTAX          NString
    MAX-ACCESS      read-only
    STATUS          current
    DESCRIPTION     
            "The process type of this virtual process."
    ::= { vpcEntry 13 }

vpceArgc OBJECT-TYPE
    SYNTAX          Integer32
    MAX-ACCESS      read-only
    STATUS          current
    DESCRIPTION     
            "The number of arguments of this virtual process."
    ::= { vpcEntry 14 }

vpceArgv OBJECT-TYPE
    SYNTAX          NString
    MAX-ACCESS      read-only
    STATUS          current
    DESCRIPTION     
            "The arguments of this virtual process."
    ::= { vpcEntry 15 }

vpceTotalStarts OBJECT-TYPE
    SYNTAX          Integer32
    MAX-ACCESS      read-only
    STATUS          current
    DESCRIPTION     
            "The total number of starts for this virtual process."
    ::= { vpcEntry 16 }

vpceStartedTime OBJECT-TYPE
    SYNTAX          NTimeVal
    MAX-ACCESS      read-only
    STATUS          current
    DESCRIPTION     
            "The started time of the virtual process."
    ::= { vpcEntry 17 }

vpcePid OBJECT-TYPE
    SYNTAX          Integer32
    MAX-ACCESS      read-only
    STATUS          current
    DESCRIPTION     
            "The operating system pid (process id)."
    ::= { vpcEntry 18 }

vpceWPid OBJECT-TYPE
    SYNTAX          Integer32
    MAX-ACCESS      read-only
    STATUS          current
    DESCRIPTION     
            "The watcher pid (process id)."
    ::= { vpcEntry 19 }

vpceConsecutivePingsMissed OBJECT-TYPE
    SYNTAX          Integer32
    MAX-ACCESS      read-only
    STATUS          current
    DESCRIPTION     
            "The number of consecutive pings that have been missed."
    ::= { vpcEntry 20 }

vpceTotalPingsMissed OBJECT-TYPE
    SYNTAX          Integer32
    MAX-ACCESS      read-only
    STATUS          current
    DESCRIPTION     
            "The total number of pings that have been missed."
    ::= { vpcEntry 21 }

vpcePingedTime OBJECT-TYPE
    SYNTAX          NTimeVal
    MAX-ACCESS      read-only
    STATUS          current
    DESCRIPTION     
            "The pinged time of the virtual process."
    ::= { vpcEntry 22 }

vpceIsConnected OBJECT-TYPE
    SYNTAX          TruthValue
    MAX-ACCESS      read-only
    STATUS          current
    DESCRIPTION     
            "Whether the virtual process is connected."
    ::= { vpcEntry 23 }

vpceStreamRemotePort OBJECT-TYPE
    SYNTAX          Unsigned32
    MAX-ACCESS      read-only
    STATUS          current
    DESCRIPTION     
            "The remote TCP stream port."
    ::= { vpcEntry 24 }

vpceRestartAttemptedTime OBJECT-TYPE
    SYNTAX          NTimeVal
    MAX-ACCESS      read-only
    STATUS          current
    DESCRIPTION     
            "The restart attempted time of the virtual process."
    ::= { vpcEntry 25 }

vpceQuiesceAttemptedTime OBJECT-TYPE
    SYNTAX          NTimeVal
    MAX-ACCESS      read-only
    STATUS          current
    DESCRIPTION     
            "The quiesce attempted time of the virtual process."
    ::= { vpcEntry 26 }

vpceQuiescedTime OBJECT-TYPE
    SYNTAX          NTimeVal
    MAX-ACCESS      read-only
    STATUS          current
    DESCRIPTION     
            "The quiesced time of the virtual process."
    ::= { vpcEntry 27 }

vpceKillAttemptedTime OBJECT-TYPE
    SYNTAX          NTimeVal
    MAX-ACCESS      read-only
    STATUS          current
    DESCRIPTION     
            "The kill attempted time of the virtual process."
    ::= { vpcEntry 28 }

vpceDiedTime OBJECT-TYPE
    SYNTAX          NTimeVal
    MAX-ACCESS      read-only
    STATUS          current
    DESCRIPTION     
            "The died time of the virtual process."
    ::= { vpcEntry 29 }

vpceReleasedTime OBJECT-TYPE
    SYNTAX          NTimeVal
    MAX-ACCESS      read-only
    STATUS          current
    DESCRIPTION     
            "The released time of the virtual process."
    ::= { vpcEntry 30 }

vprInfo OBJECT IDENTIFIER
    ::= { wdVpSet 3 }

vpriCount OBJECT-TYPE
    SYNTAX          Integer32
    MAX-ACCESS      not-accessible
    STATUS          current
    DESCRIPTION     
            "The number of released virtual processes."
    ::= { vprInfo 1 }

vpriList OBJECT-TYPE
    SYNTAX          NString
    MAX-ACCESS      not-accessible
    STATUS          current
    DESCRIPTION     
            "A space delimited list of the vpids of the
             released virtual processes."
    ::= { vprInfo 2 }

wvpDefaultParams OBJECT IDENTIFIER
    ::= { wdVpSet 4 }

wvpdpCount OBJECT-TYPE
    SYNTAX          Integer32
    MAX-ACCESS      read-only
    STATUS          current
    DESCRIPTION     
            "The number of watchable virtual processes running
             on this machine."
    ::= { wvpDefaultParams 1 }

wvpdpList OBJECT-TYPE
    SYNTAX          NString
    MAX-ACCESS      read-only
    STATUS          current
    DESCRIPTION     
            "A space delimited list of the vpids of the watchable
             virtual processes running on this machine."
    ::= { wvpDefaultParams 2 }

wvpdpTable OBJECT-TYPE
    SYNTAX          SEQUENCE OF WvpdpEntry
    MAX-ACCESS      not-accessible
    STATUS          current
    DESCRIPTION     
            "Table of watchable virtual process default parameters."
    ::= { wvpDefaultParams 3 }

wvpdpEntry OBJECT-TYPE
    SYNTAX          WvpdpEntry
    MAX-ACCESS      not-accessible
    STATUS          current
    DESCRIPTION     
            "Default parameters for a particular watchable
             virtual process.  This table is indexed by
             wvpdpeProcessVpid (not consecutive), and the
              total number of conceptual rows in this table
              is wvpdpCount.  The vpids represented in this
              table are listed in wvpdpList."
    INDEX           { wvpdpeProcessVpid }
    ::= { wvpdpTable 1 }

WvpdpEntry ::=
    SEQUENCE {
        wvpdpeProcessVpid               Unsigned32,
        wvpdpeProcessBuildEnv           NString,
        wvpdpeProcessBuildName          NString,
        wvpdpeProcessBuildTime          NString,
        wvpdpeProcessCpuBusyPercentage  Integer32,
        wvpdpeProcessCpuBusySecs        Integer32,
        wvpdpeProcessCpuTotalSecs       Integer32,
        wvpdpeProcessCwd                NString,
        wvpdpeProcessLoggingLevel       NString,
        wvpdpeProcessKBytes             Integer32,
        wvpdpeProcessStartTime          NString,
        wvpdpeProcessVersionName        NString,
        wvpdpeProcessVersionNum         Integer32
    }

wvpdpeProcessVpid OBJECT-TYPE
    SYNTAX          Unsigned32
    MAX-ACCESS      read-only
    STATUS          current
    DESCRIPTION     
            "The process virtual process id."
    ::= { wvpdpEntry 1 }

wvpdpeProcessBuildEnv OBJECT-TYPE
    SYNTAX          NString
    MAX-ACCESS      read-only
    STATUS          current
    DESCRIPTION     
            "The process build environment."
    ::= { wvpdpEntry 2 }

wvpdpeProcessBuildName OBJECT-TYPE
    SYNTAX          NString
    MAX-ACCESS      read-only
    STATUS          current
    DESCRIPTION     
            "The process build name."
    ::= { wvpdpEntry 3 }

wvpdpeProcessBuildTime OBJECT-TYPE
    SYNTAX          NString
    MAX-ACCESS      read-only
    STATUS          current
    DESCRIPTION     
            "The process build time."
    ::= { wvpdpEntry 4 }

wvpdpeProcessCpuBusyPercentage OBJECT-TYPE
    SYNTAX          Integer32
    MAX-ACCESS      read-only
    STATUS          current
    DESCRIPTION     
            "The process CPU busy percentage, calculated using
             deltas of wvpdpeProcessCpuBusySecs and
             wvpdpeProcessTotalSecs over a five second interval."
    ::= { wvpdpEntry 5 }

wvpdpeProcessCpuBusySecs OBJECT-TYPE
    SYNTAX          Integer32
    MAX-ACCESS      read-only
    STATUS          current
    DESCRIPTION     
            "The process CPU busy seconds."
    ::= { wvpdpEntry 6 }

wvpdpeProcessCpuTotalSecs OBJECT-TYPE
    SYNTAX          Integer32
    MAX-ACCESS      read-only
    STATUS          current
    DESCRIPTION     
            "The process CPU total seconds."
    ::= { wvpdpEntry 7 }

wvpdpeProcessCwd OBJECT-TYPE
    SYNTAX          NString
    MAX-ACCESS      read-only
    STATUS          current
    DESCRIPTION     
            "The process current working directory."
    ::= { wvpdpEntry 8 }

wvpdpeProcessLoggingLevel OBJECT-TYPE
    SYNTAX          NString
    MAX-ACCESS      read-write
    STATUS          current
    DESCRIPTION     
            "The process logging level."
    ::= { wvpdpEntry 9 }

wvpdpeProcessKBytes OBJECT-TYPE
    SYNTAX          Integer32
    MAX-ACCESS      read-only
    STATUS          current
    DESCRIPTION     
            "The process memory size in kilobytes."
    ::= { wvpdpEntry 10 }

wvpdpeProcessStartTime OBJECT-TYPE
    SYNTAX          NString
    MAX-ACCESS      read-only
    STATUS          current
    DESCRIPTION     
            "The process start time."
    ::= { wvpdpEntry 11 }

wvpdpeProcessVersionName OBJECT-TYPE
    SYNTAX          NString
    MAX-ACCESS      read-only
    STATUS          current
    DESCRIPTION     
            "The process version name."
    ::= { wvpdpEntry 12 }

wvpdpeProcessVersionNum OBJECT-TYPE
    SYNTAX          Integer32
    MAX-ACCESS      read-only
    STATUS          current
    DESCRIPTION     
            "The process version number."
    ::= { wvpdpEntry 13 }

wvpExtraParams OBJECT IDENTIFIER
    ::= { wdVpSet 5 }

watcherDaemon OBJECT IDENTIFIER
    ::= { wvpExtraParams 1 }

wdepCount OBJECT-TYPE
    SYNTAX          Integer32
    MAX-ACCESS      read-only
    STATUS          current
    DESCRIPTION     
            "The number of watcherDaemon virtual processes
             running on this machine."
    ::= { watcherDaemon 1 }

wdepList OBJECT-TYPE
    SYNTAX          NString
    MAX-ACCESS      read-only
    STATUS          current
    DESCRIPTION     
            "A space delimited list of the vpids of the
             watcherDaemon virtual processes running on this
             machine."
    ::= { watcherDaemon 2 }

wdepTable OBJECT-TYPE
    SYNTAX          SEQUENCE OF WdepEntry
    MAX-ACCESS      not-accessible
    STATUS          current
    DESCRIPTION     
            "Table of watcherDaemon virtual process extra
             parameters."
    ::= { watcherDaemon 3 }

wdepEntry OBJECT-TYPE
    SYNTAX          WdepEntry
    MAX-ACCESS      not-accessible
    STATUS          current
    DESCRIPTION     
            "Extra parameters for a particular watcherDaemon
             virtual process.  This table is indexed by
             wvpdpeProcessVpid (from wvpdpTable), and the
             total number of conceptual rows in this table is
             wdepCount.  The vpids represented in this table are
             listed in wdepList."
    INDEX           { wvpdpeProcessVpid }
    ::= { wdepTable 1 }

WdepEntry ::=
    SEQUENCE {
        wdepeSystemCpuIdlePercentage    Integer32,
        wdepeSystemCpuKernelPercentage  Integer32,
        wdepeSystemCpuUserPercentage    Integer32,
        wdepeSystemCpuWaitPercentage    Integer32,
        wdepeSystemCpuQueueLength       Integer32,
        wdepeSystemMemoryPhysicalFreeKBytes   Integer32,
        wdepeSystemMemoryPhysicalTotalKBytes    Integer32,
        wdepeSystemMemoryVirtualFreeKBytes  Integer32,
        wdepeSystemMemoryVirtualTotalKBytes   Integer32,
        wdepeSystemNumCpus              Integer32,
        wdepeSystemNumCpusOnline        Integer32
    }

wdepeSystemCpuIdlePercentage OBJECT-TYPE
    SYNTAX          Integer32
    MAX-ACCESS      read-only
    STATUS          current
    DESCRIPTION     
            "The idle CPU percentage for this system."
    ::= { wdepEntry 1 }

wdepeSystemCpuKernelPercentage OBJECT-TYPE
    SYNTAX          Integer32
    MAX-ACCESS      read-only
    STATUS          current
    DESCRIPTION     
            "The kernel CPU percentage for this system."
    ::= { wdepEntry 2 }

wdepeSystemCpuUserPercentage OBJECT-TYPE
    SYNTAX          Integer32
    MAX-ACCESS      read-only
    STATUS          current
    DESCRIPTION     
            "The user CPU percentage for this system."
    ::= { wdepEntry 3 }

wdepeSystemCpuWaitPercentage OBJECT-TYPE
    SYNTAX          Integer32
    MAX-ACCESS      read-only
    STATUS          current
    DESCRIPTION     
            "The wait CPU percentage for this system."
    ::= { wdepEntry 4 }

wdepeSystemCpuQueueLength OBJECT-TYPE
    SYNTAX          Integer32
    MAX-ACCESS      read-only
    STATUS          current
    DESCRIPTION     
            "The CPU queue length for this system."
    ::= { wdepEntry 5 }

wdepeSystemMemoryPhysicalFreeKBytes OBJECT-TYPE
    SYNTAX          Integer32
    MAX-ACCESS      read-only
    STATUS          current
    DESCRIPTION     
            "The free physical memory in kilobytes for
             this system."
    ::= { wdepEntry 6 }

wdepeSystemMemoryPhysicalTotalKBytes OBJECT-TYPE
    SYNTAX          Integer32
    MAX-ACCESS      read-only
    STATUS          current
    DESCRIPTION     
            "The total physical memory in kilobytes for
             this system."
    ::= { wdepEntry 7 }

wdepeSystemMemoryVirtualFreeKBytes OBJECT-TYPE
    SYNTAX          Integer32
    MAX-ACCESS      read-only
    STATUS          current
    DESCRIPTION     
            "The free virtual memory in kilobytes for
             this system."
    ::= { wdepEntry 8 }

wdepeSystemMemoryVirtualTotalKBytes OBJECT-TYPE
    SYNTAX          Integer32
    MAX-ACCESS      read-only
    STATUS          current
    DESCRIPTION     
            "The total virtual memory in kilobytes for
             this system."
    ::= { wdepEntry 9 }

wdepeSystemNumCpus OBJECT-TYPE
    SYNTAX          Integer32
    MAX-ACCESS      read-only
    STATUS          current
    DESCRIPTION     
            "The number of CPUs in this system."
    ::= { wdepEntry 10 }

wdepeSystemNumCpusOnline OBJECT-TYPE
    SYNTAX          Integer32
    MAX-ACCESS      read-only
    STATUS          current
    DESCRIPTION     
            "The number of CPUs online in this system."
    ::= { wdepEntry 11 }

wdWmSet OBJECT IDENTIFIER
    ::= { watcherDaemonMib 3 }

wmSetControl OBJECT IDENTIFIER
    ::= { wdWmSet 1 }

startWmArgs OBJECT-TYPE
    SYNTAX          NString
    MAX-ACCESS      read-write
    STATUS          current
    DESCRIPTION     
            "The full command line of the module to start."
    ::= { wmSetControl 1 }

startWmState OBJECT-TYPE
    SYNTAX          INTEGER { nullState(1), doneState(2), goStart(100), 
                        goReset(200) }
    MAX-ACCESS      read-write
    STATUS          current
    DESCRIPTION     
            "Control starting a watcher module.  The only valid
             set values are goStart and goReset.  Set to
             goStart to start a module (based on arguments
             supplied in startWmArgs).  After starting and
             the state is doneState, startWmStatus can be
             checked for the status of the start, and
             startWmModuleId can be checked for the module id of the
             module that was started.  Set to goReset to reset
             the startWmStatus and startWmModuleId, and reset the
             state back to the nullState."
    ::= { wmSetControl 2 }

startWmStatus OBJECT-TYPE
    SYNTAX          NString
    MAX-ACCESS      read-only
    STATUS          current
    DESCRIPTION     
            "The status of the last attempted start."
    ::= { wmSetControl 3 }

startWmModuleId OBJECT-TYPE
    SYNTAX          Unsigned32
    MAX-ACCESS      read-only
    STATUS          current
    DESCRIPTION     
            "The module id of the last attempted start."
    ::= { wmSetControl 4 }

wmControl OBJECT IDENTIFIER
    ::= { wdWmSet 2 }

wmcCount OBJECT-TYPE
    SYNTAX          Integer32
    MAX-ACCESS      read-only
    STATUS          current
    DESCRIPTION     
            "The number of modules running in the watcher-daemon."
    ::= { wmControl 1 }

wmcList OBJECT-TYPE
    SYNTAX          NString
    MAX-ACCESS      read-only
    STATUS          current
    DESCRIPTION     
            "A space delimited list of the module ids of the
             modules running on this machine."
    ::= { wmControl 2 }

wmcTable OBJECT-TYPE
    SYNTAX          SEQUENCE OF WmcEntry
    MAX-ACCESS      not-accessible
    STATUS          current
    DESCRIPTION     
            "Table of module information."
    ::= { wmControl 3 }

wmcEntry OBJECT-TYPE
    SYNTAX          WmcEntry
    MAX-ACCESS      not-accessible
    STATUS          current
    DESCRIPTION     
            "Information and control for a particular
             module.  This table is indexed by wmceModuleId
             (not consecutive), and the total number of conceptual
             rows in this table is wmcCount.  The module ids
             represented in this table are listed in wmcList."
    INDEX           { wmceModuleId }
    ::= { wmcTable 1 }

WmcEntry ::=
    SEQUENCE {
        wmceModuleId                    Unsigned32,
        wmceModuleState                 INTEGER,
        wmceName                        NString,
        wmceArgc                        Integer32,
        wmceArgv                        NString,
        wmceQuiesceTimeoutMs            Integer32,
        wmceAssignedTime                NTimeVal,
        wmcePort                        Integer32,
        wmceQuiesceAttemptedTime        NTimeVal,
        wmceDiedTime                    NTimeVal,
        wmceReleasedTime                NTimeVal
    }

wmceModuleId OBJECT-TYPE
    SYNTAX          Unsigned32
    MAX-ACCESS      read-only
    STATUS          current
    DESCRIPTION     
            "The module id."
    ::= { wmcEntry 1 }

wmceModuleState OBJECT-TYPE
    SYNTAX          INTEGER { nullState(1), startingState(2), 
                        readyState(3), quiescingState(4), 
                        terminatingState(5), releasingState(6), 
                        goQuiesce(100) }
    MAX-ACCESS      read-write
    STATUS          current
    DESCRIPTION     
            "The module state.  The only valid set value
             is goQuiesce.  Set to quiesce the module, and
             check wmrieQuiesceAttemptedTime to make sure the
             action was attempted."
    ::= { wmcEntry 2 }

wmceName OBJECT-TYPE
    SYNTAX          NString
    MAX-ACCESS      read-only
    STATUS          current
    DESCRIPTION     
            "The name for the module."
    ::= { wmcEntry 3 }

wmceArgc OBJECT-TYPE
    SYNTAX          Integer32
    MAX-ACCESS      read-only
    STATUS          current
    DESCRIPTION     
            "The number of arguments for the module."
    ::= { wmcEntry 4 }

wmceArgv OBJECT-TYPE
    SYNTAX          NString
    MAX-ACCESS      read-only
    STATUS          current
    DESCRIPTION     
            "The arguments for the module."
    ::= { wmcEntry 5 }

wmceQuiesceTimeoutMs OBJECT-TYPE
    SYNTAX          Integer32
    MAX-ACCESS      read-only
    STATUS          current
    DESCRIPTION     
            "The quiesce timeout in milliseconds, or the time
             the WatcherDaemon will wait for a quiesce before
             the module is automatically killed."
    ::= { wmcEntry 6 }

wmceAssignedTime OBJECT-TYPE
    SYNTAX          NTimeVal
    MAX-ACCESS      read-only
    STATUS          current
    DESCRIPTION     
            "The assigned time of the module."
    ::= { wmcEntry 7 }

wmcePort OBJECT-TYPE
    SYNTAX          Integer32
    MAX-ACCESS      read-only
    STATUS          current
    DESCRIPTION     
            "The port the module is listening on."
    ::= { wmcEntry 8 }

wmceQuiesceAttemptedTime OBJECT-TYPE
    SYNTAX          NTimeVal
    MAX-ACCESS      read-only
    STATUS          current
    DESCRIPTION     
            "The quiesce attempted time of the module."
    ::= { wmcEntry 9 }

wmceDiedTime OBJECT-TYPE
    SYNTAX          NTimeVal
    MAX-ACCESS      read-only
    STATUS          current
    DESCRIPTION     
            "The died time of the module."
    ::= { wmcEntry 10 }

wmceReleasedTime OBJECT-TYPE
    SYNTAX          NTimeVal
    MAX-ACCESS      read-only
    STATUS          current
    DESCRIPTION     
            "The released time of the module."
    ::= { wmcEntry 11 }

wmrInfo OBJECT IDENTIFIER
    ::= { wdWmSet 3 }

wmriCount OBJECT-TYPE
    SYNTAX          Integer32
    MAX-ACCESS      not-accessible
    STATUS          current
    DESCRIPTION     
            "The number of released modules."
    ::= { wmrInfo 1 }

wmriList OBJECT-TYPE
    SYNTAX          NString
    MAX-ACCESS      not-accessible
    STATUS          current
    DESCRIPTION     
            "A space delimited list of the module ids of the
             released modules."
    ::= { wmrInfo 2 }

wdNotifications OBJECT IDENTIFIER
    ::= { watcherDaemonMib 100 }

wdNotificationPrefix OBJECT IDENTIFIER
    ::= { wdNotifications 0 }

wdNotificationObjects OBJECT IDENTIFIER
    ::= { wdNotifications 1 }

wdnoClapiSeverity OBJECT-TYPE
    SYNTAX          INTEGER { criticalAlarm(1), majorAlarm(2), 
                        minorAlarm(4), fatal(8), error(16), warning(32), 
                        userError(64), userWarning(128), status(256), 
                        info(1024), detailedInfo(4096), 
                        veryDetailedInfo(16384) }
    MAX-ACCESS      read-only
    STATUS          current
    DESCRIPTION     
            "The severity of the clapi notification."
    ::= { wdNotificationObjects 1 }

wdnoClapiMessageId OBJECT-TYPE
    SYNTAX          NString
    MAX-ACCESS      read-only
    STATUS          current
    DESCRIPTION     
            "The message ID of the clapi notification."
    ::= { wdNotificationObjects 2 }

wdnoClapiMessage OBJECT-TYPE
    SYNTAX          NString
    MAX-ACCESS      read-only
    STATUS          current
    DESCRIPTION     
            "The message of the clapi notification."
    ::= { wdNotificationObjects 3 }

wdnoClapiHostName OBJECT-TYPE
    SYNTAX          NString
    MAX-ACCESS      read-only
    STATUS          current
    DESCRIPTION     
            "The host name of the clapi notification."
    ::= { wdNotificationObjects 4 }

wdnoClapiServiceName OBJECT-TYPE
    SYNTAX          NString
    MAX-ACCESS      read-only
    STATUS          current
    DESCRIPTION     
            "The service name of the clapi notification."
    ::= { wdNotificationObjects 5 }

wdStartNotification NOTIFICATION-TYPE
    STATUS          current
    DESCRIPTION     
            "This notification is generated when the snmp-watcher-
             module is loaded and initialized."
    ::= { wdNotificationPrefix 1 }

wdDaemonQuiesceNotification NOTIFICATION-TYPE
    STATUS          current
    DESCRIPTION     
            "This notification is generated when the watcher-daemon
             starts quiescing."
    ::= { wdNotificationPrefix 2 }

wdClapiNotification NOTIFICATION-TYPE
    OBJECTS         { wdnoClapiSeverity, wdnoClapiMessageId, 
                      wdnoClapiMessage, wdnoClapiHostName, 
                      wdnoClapiServiceName }
    STATUS          current
    DESCRIPTION     
            "This notification is generated on clapi events."
    ::= { wdNotificationPrefix 3 }

END -- end of module NUANCE-MIB.
