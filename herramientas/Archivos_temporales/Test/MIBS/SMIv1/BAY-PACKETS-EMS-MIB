--
-- This SMIv1 module has been generated by smidump 0.2-cvs. Do not edit.
--

BAY-PACKETS-EMS-MIB DEFINITIONS ::= BEGIN

IMPORTS
    OBJECT-TYPE
        FROM RFC-1212
    TRAP-TYPE
        FROM RFC-1215
    Counter
        FROM RFC1155-SMI
    enterprises
        FROM SNMPv2-SMI
    DisplayString, RowStatus
        FROM SNMPv2-TC;

rsiCommonMib OBJECT IDENTIFIER
    ::= { rsiMib 1 }

-- rsiCommonMib MODULE-IDENTITY
--     LAST-UPDATED    "197001010000Z"
--     ORGANIZATION    
--             "BayPackets, Inc."
--     CONTACT-INFO    
--             " Technical Support
--              Postal: 47266 Benicia Street, 2nd Floor
--                      Fremont, CA 94538
--              Tel   : +1 510 743 2500
--              Fax   : +1 510 743 2505
--              E-mail: support@baypackets.com "
--     DESCRIPTION     
--             "The MIB represents an RSI agent. It enables the
--              externalapplication to do SNMP get and set requests:
--               1. to start/stop different components
--               2. to get/set configurable parameters of components
--                  as well as performance parameters
--               3. to receive alarms generated by the system (sent as
--                  traps)
--              
--               There are some Oids which are configurable only statically,
--               i.e. when the system is stopped.
--               These OIDs have two type of values: 
--                 (a) New and 
--                 (b) Current 
--               The New Value is read-write, and gets read/used by the
--               subsystem after a restart.
--               The Current Value is read-only, and is the value being
--               used by the subsystem currently. i.e., the value of the
--               OID set before this subsystem was started.
--              
--               The oids in subsystem tables are grouped in 5 groups :
--               1. performance oids. These set of OIDs are read only 
--                  (with values 2xx)
--               2. Oids which are configurable statically as well as
--                  at run time. These set of OIDs are read-write
--                  (with values 3xx)
--               3. New value of the Non-Runtime Configurable OIDs 
--                  These set of OIDs are read-write 
--                  (with values 4xx)
--               4. Oids which are not configurable. .These sets of OIDs are
--                  read only. 
--                  (with values 5xx)
--               5. Current value of the Non-Runtime Configurable OIDs 
--                  These set of OIDs are read-only 
--                  (with values 6xx)"
--     ::= { rsiMib 1 }


TimeOfDay ::=
    DisplayString (SIZE(8))

-- TimeOfDay ::= TEXTUAL-CONVENTION
--     STATUS          mandatory
--     DESCRIPTION     
--             "A value in the format hh:mm:ss. The time is
--              expressed as a 24 hour clock. "
--     SYNTAX          DisplayString (SIZE(8))

bayPackets OBJECT IDENTIFIER
    ::= { enterprises 7186 }

bpPrivate OBJECT IDENTIFIER
    ::= { bayPackets 1 }

bpGeneric OBJECT IDENTIFIER
    ::= { bayPackets 2 }

bpPublic OBJECT IDENTIFIER
    ::= { bayPackets 3 }

rsiMib OBJECT IDENTIFIER
    ::= { bpPublic 1 }

rsiComponentTable OBJECT-TYPE
    SYNTAX          SEQUENCE OF RsiComponentEntry
    ACCESS          not-accessible
    STATUS          mandatory
    DESCRIPTION     
            "This table stores the RSI components. This is the
             master table which contains information about all
             the components. A component is uniquely idenitified
             by a component id. The component type and subtype
             help identify the hierarchy at which the component
             is located. This table contains the generic information
             corresponding to a component. Given the component
             type, the specific table needs to be referred for
             component type specific information. For ex: if the
             component type is 'subsystem' and component sub type
             is 'SLEE', then the 'rsiSubsystem' table needs to 
             be referred for generic subsystem specific details. 
             For detailed SLEE specific details, rsiSlee table
             needs to be referred."
    ::= { rsiCommonMib 2 }

rsiComponentEntry OBJECT-TYPE
    SYNTAX          RsiComponentEntry
    ACCESS          not-accessible
    STATUS          mandatory
    DESCRIPTION     
            "Description of an RSI component"
    INDEX           { rsiCompId }
    ::= { rsiComponentTable 1 }

RsiComponentEntry ::=
    SEQUENCE {
        rsiCompId                       INTEGER,
        rsiCompName                     OCTET STRING,
        rsiCompType                     INTEGER,
        rsiCompSubType                  INTEGER,
        rsiCompChildren                 OCTET STRING,
        rsiCompParent                   INTEGER,
        rsiCompHosts                    OCTET STRING,
        rsiCompAdminState               INTEGER,
        rsiCompOperState                INTEGER,
        rsiCompAlarmCount               OCTET STRING,
        rsiCompUsageState               INTEGER
    }

rsiCompId OBJECT-TYPE
    SYNTAX          INTEGER
    ACCESS          read-only
    STATUS          mandatory
    DESCRIPTION     
            "This is the unique id of a component"
    ::= { rsiComponentEntry 1 }

rsiCompName OBJECT-TYPE
    SYNTAX          OCTET STRING
    ACCESS          read-only
    STATUS          mandatory
    DESCRIPTION     
            "This is the display name of a component,
             and will be unique within its parent structure"
    ::= { rsiComponentEntry 2 }

rsiCompType OBJECT-TYPE
    SYNTAX          INTEGER { domain(0), cluster(1), system(2), 
                        functionalUnitGroup(3), functionalUnit(4), 
                        subsystem(5), subcomponent(7), host(6) }
    ACCESS          read-only
    STATUS          mandatory
    DESCRIPTION     
            "This is the type of the component"
    ::= { rsiComponentEntry 3 }

rsiCompSubType OBJECT-TYPE
    SYNTAX          INTEGER { noSubtype(0), mediatePlatform(1), 
                        networkServicesPlatform(2), ems(3), reports(4), 
                        callProcessingUnitGroup(5), 
                        applicationUnitGroup(6), 
                        provisioningUnitGroup(7), messageStoreGroup(8), 
                        messagingUnitGroup(9), databaseGroup(10), 
                        mediationUnitGroup(11), adapterUnitGroup(12), 
                        networkResourceGroup(13), mediationUnit(14), 
                        adapterUnit(15), callProcessingUnit(16), 
                        applicationUnit(17), provisioningUnit(18), 
                        messagingUnit(19), databaseUnit(20), 
                        messageStoreUnit(21), ivrUnit(22), 
                        mediatePlatformNetworkResource(23), 
                        networkServicesNetworkResource(24), 
                        bayMediator(25), bayCorrelator(26), 
                        bayNEAdapter(27), bayManager(28), daiAdapter(29), 
                        tibcoAdapter(30), serviceLogicExecutionEnv(31), 
                        serviceProvisioningSubscriptionInterface(32), 
                        callModelManager(33), messagingManager(34), 
                        soapAdapter(35), provider(36), switch(37), 
                        ivr(38), networkElement(39), realTimeAdapter(40), 
                        iPlanet(41), database(42), popUpServer(43), 
                        host(44), 
                        simpleMessagingDeskInterfaceApplication(45), 
                        lecSwitch(46), smpp(47), sipSwitch(48), 
                        directoryServer(49) }
    ACCESS          read-only
    STATUS          mandatory
    DESCRIPTION     
            "This is the Sub type of the component, i.e., 
             a subsystem can be bayMediator/bayNEAdapter, etc.
             Similarly a Functional Unit can be Call Processing
             Unit (CPU), Application Unit (AU), etc."
    ::= { rsiComponentEntry 4 }

rsiCompChildren OBJECT-TYPE
    SYNTAX          OCTET STRING
    ACCESS          read-only
    STATUS          mandatory
    DESCRIPTION     
            "This is the list of child components for a given
             component. For ex: for a cluster instance, it
             contains the list of systems in the given cluster.
             This is a comma seperated list, and could have 
             been described as sequence of integers."
    ::= { rsiComponentEntry 5 }

rsiCompParent OBJECT-TYPE
    SYNTAX          INTEGER
    ACCESS          read-only
    STATUS          mandatory
    DESCRIPTION     
            "This is the parent component for a given
             component. For ex: for a cluster instance, this 
             contains the domain which contains this cluster."
    ::= { rsiComponentEntry 6 }

rsiCompHosts OBJECT-TYPE
    SYNTAX          OCTET STRING
    ACCESS          read-only
    STATUS          mandatory
    DESCRIPTION     
            "This is the list of hosts on which the given  
             component is running. 
             This will be a comma seperated list, and could have 
             been described as sequence of integers."
    ::= { rsiComponentEntry 7 }

rsiCompAdminState OBJECT-TYPE
    SYNTAX          INTEGER { locked(0), unlocked(1), shuttingdown(2), 
                        unknown(3) }
    ACCESS          read-write
    STATUS          mandatory
    DESCRIPTION     
            "This reflects the intended state of a component. 
             Setting this status to 'down' stops the component and 
             its children. Setting this status to 'up' starts the 
             component and its children. "
    ::= { rsiComponentEntry 8 }

rsiCompOperState OBJECT-TYPE
    SYNTAX          INTEGER { loaded(0), running(1), stopped(2), 
                        partiallyDegraded(3), unknown(4), error(5) }
    ACCESS          read-only
    STATUS          mandatory
    DESCRIPTION     
            "This reflects the current operational state of a 
             component. "
    ::= { rsiComponentEntry 9 }

rsiCompAlarmCount OBJECT-TYPE
    SYNTAX          OCTET STRING
    ACCESS          read-only
    STATUS          mandatory
    DESCRIPTION     
            "This is a comma seperated list of alarm counts based
             on their severity. The order of the alarm counts will
             be critical, major, minor, warning, normal.
             This will be a comma seperated list, and can 
             be described as sequence of integers."
    ::= { rsiComponentEntry 10 }

rsiCompUsageState OBJECT-TYPE
    SYNTAX          INTEGER { idle(0), active(1), busy(2) }
    ACCESS          read-only
    STATUS          mandatory
    DESCRIPTION     
            "This reflects the current usage state of a component. "
    ::= { rsiComponentEntry 11 }

rsiLinkTable OBJECT-TYPE
    SYNTAX          SEQUENCE OF RsiLinkEntry
    ACCESS          not-accessible
    STATUS          mandatory
    DESCRIPTION     
            "This table stores the link info between RSI components"
    ::= { rsiCommonMib 3 }

rsiLinkEntry OBJECT-TYPE
    SYNTAX          RsiLinkEntry
    ACCESS          not-accessible
    STATUS          mandatory
    DESCRIPTION     
            "Description of one link between 2 RSI components"
    INDEX           { rsiLinkEndPoint1CompId, rsiLinkEndPoint2CompId }
    ::= { rsiLinkTable 1 }

RsiLinkEntry ::=
    SEQUENCE {
        rsiLinkEndPoint1CompId          INTEGER,
        rsiLinkEndPoint2CompId          INTEGER,
        rsiLinkStatus                   INTEGER
    }

rsiLinkEndPoint1CompId OBJECT-TYPE
    SYNTAX          INTEGER
    ACCESS          read-only
    STATUS          mandatory
    DESCRIPTION     
            "This is the component id of LinkEndPoint1"
    ::= { rsiLinkEntry 1 }

rsiLinkEndPoint2CompId OBJECT-TYPE
    SYNTAX          INTEGER
    ACCESS          read-only
    STATUS          mandatory
    DESCRIPTION     
            "This is the component id of EndPoint2"
    ::= { rsiLinkEntry 2 }

rsiLinkStatus OBJECT-TYPE
    SYNTAX          INTEGER { down(0), up(1), partial(2), unknown(3) }
    ACCESS          read-only
    STATUS          mandatory
    DESCRIPTION     
            "This is the type of the component"
    ::= { rsiLinkEntry 3 }

rsiAlarmTable OBJECT-TYPE
    SYNTAX          SEQUENCE OF RsiAlarmEntry
    ACCESS          not-accessible
    STATUS          mandatory
    DESCRIPTION     
            "This table stores the RSI alarms. These alarms have
             already been notified as traps."
    ::= { rsiCommonMib 4 }

rsiAlarmEntry OBJECT-TYPE
    SYNTAX          RsiAlarmEntry
    ACCESS          not-accessible
    STATUS          mandatory
    DESCRIPTION     
            "Description of an alarm raised by a RSI component"
    INDEX           { rsiAlarmId }
    ::= { rsiAlarmTable 1 }

RsiAlarmEntry ::=
    SEQUENCE {
        rsiAlarmId                      INTEGER,
        rsiRelatedAlarmId               INTEGER,
        rsiAlarmDateTime                DisplayString,
        rsiAlarmErrorCode               INTEGER,
        rsiAlarmContent                 OCTET STRING,
        rsiOriginatingSubsystemId       INTEGER,
        rsiOriginatingSubsystemName     OCTET STRING,
        rsiTroublingSubsystemId         INTEGER,
        rsiTroublingSubsystemName       OCTET STRING,
        rsiAlarmStatus                  INTEGER,
        rsiAlarmSeverity                INTEGER,
        rsiAlarmAcknowledgedBy          OCTET STRING,
        rsiAcknowledgementDateTime      DisplayString,
        rsiAlarmClearedBy               OCTET STRING,
        rsiClearingDateTime             DisplayString,
        rsiOrigSystemId                 INTEGER,
        rsiOrigSystemName               OCTET STRING,
        rsiOrigHostId                   INTEGER,
        rsiOrigHostName                 OCTET STRING
    }

rsiAlarmId OBJECT-TYPE
    SYNTAX          INTEGER
    ACCESS          read-only
    STATUS          mandatory
    DESCRIPTION     
            "This is the unique id of the alarm."
    ::= { rsiAlarmEntry 1 }

rsiRelatedAlarmId OBJECT-TYPE
    SYNTAX          INTEGER
    ACCESS          read-only
    STATUS          mandatory
    DESCRIPTION     
            "If the severity of this alarm is 'clear', then this
             entry will have meaningful value. In that case, this
             entry will contain the alarm id of the alarm, for which
             this clear has been raised."
    ::= { rsiAlarmEntry 2 }

rsiAlarmDateTime OBJECT-TYPE
    SYNTAX          DisplayString (SIZE(19))
    ACCESS          read-only
    STATUS          mandatory
    DESCRIPTION     
            "This is the time of the alarm in 
             'YYYY:MM:DD HH:MM:SS' format"
    ::= { rsiAlarmEntry 3 }

rsiAlarmErrorCode OBJECT-TYPE
    SYNTAX          INTEGER
    ACCESS          read-only
    STATUS          mandatory
    DESCRIPTION     
            "This is the errorCode of the alarm"
    ::= { rsiAlarmEntry 4 }

rsiAlarmContent OBJECT-TYPE
    SYNTAX          OCTET STRING
    ACCESS          read-only
    STATUS          mandatory
    DESCRIPTION     
            "This is the content string of the alarm, in i18n form"
    ::= { rsiAlarmEntry 5 }

rsiOriginatingSubsystemId OBJECT-TYPE
    SYNTAX          INTEGER
    ACCESS          read-only
    STATUS          mandatory
    DESCRIPTION     
            "This is the Id of the subsystem raising the alarm"
    ::= { rsiAlarmEntry 6 }

rsiOriginatingSubsystemName OBJECT-TYPE
    SYNTAX          OCTET STRING
    ACCESS          read-only
    STATUS          mandatory
    DESCRIPTION     
            "This is the name of the subsystem raising the alarm"
    ::= { rsiAlarmEntry 7 }

rsiTroublingSubsystemId OBJECT-TYPE
    SYNTAX          INTEGER
    ACCESS          read-only
    STATUS          mandatory
    DESCRIPTION     
            "This is the Id of the subsystem which has failed, and
             because of which this alarm has been raised"
    ::= { rsiAlarmEntry 8 }

rsiTroublingSubsystemName OBJECT-TYPE
    SYNTAX          OCTET STRING
    ACCESS          read-only
    STATUS          mandatory
    DESCRIPTION     
            "This is the name of the subsystem which has failed, and
             because of which this alarm has been raised"
    ::= { rsiAlarmEntry 9 }

rsiAlarmStatus OBJECT-TYPE
    SYNTAX          INTEGER { rsiAlarmAcked(1), rsiAlarmUnacked(0), 
                        rsiAlarmCleared(2), rsiAlarmUnknown(3) }
    ACCESS          read-write
    STATUS          mandatory
    DESCRIPTION     
            "The status of the alarm"
    ::= { rsiAlarmEntry 10 }

rsiAlarmSeverity OBJECT-TYPE
    SYNTAX          INTEGER { critical(0), major(1), minor(2), 
                        warning(3), normal(4), unknown(5), clear(6) }
    ACCESS          read-only
    STATUS          mandatory
    DESCRIPTION     
            "This is the severity level of the alarm.  The unknown sevrity is depricated. normal severity relates to informational alarms."
    ::= { rsiAlarmEntry 11 }

rsiAlarmAcknowledgedBy OBJECT-TYPE
    SYNTAX          OCTET STRING
    ACCESS          read-only
    STATUS          mandatory
    DESCRIPTION     
            "Name of the person who acknowledged the alarm "
    ::= { rsiAlarmEntry 12 }

rsiAcknowledgementDateTime OBJECT-TYPE
    SYNTAX          DisplayString (SIZE(19))
    ACCESS          read-only
    STATUS          mandatory
    DESCRIPTION     
            "This is the time when this alarm was acknowledged, in
             'YYYY:MM:DD HH:MM:SS' format"
    ::= { rsiAlarmEntry 13 }

rsiAlarmClearedBy OBJECT-TYPE
    SYNTAX          OCTET STRING
    ACCESS          read-only
    STATUS          mandatory
    DESCRIPTION     
            " Name of the person who cleared the alarm "
    ::= { rsiAlarmEntry 14 }

rsiClearingDateTime OBJECT-TYPE
    SYNTAX          DisplayString (SIZE(19))
    ACCESS          read-only
    STATUS          mandatory
    DESCRIPTION     
            "This is the time when this alarm was cleared, in
             'YYYY:MM:DD HH:MM:SS' format"
    ::= { rsiAlarmEntry 15 }

rsiOrigSystemId OBJECT-TYPE
    SYNTAX          INTEGER
    ACCESS          read-only
    STATUS          mandatory
    DESCRIPTION     
            "This is the Id of the system which contains the
             subsystem which has raised this alarm"
    ::= { rsiAlarmEntry 16 }

rsiOrigSystemName OBJECT-TYPE
    SYNTAX          OCTET STRING
    ACCESS          read-only
    STATUS          mandatory
    DESCRIPTION     
            "This is the name of the system which contains the
             subsystem which has raised this alarm"
    ::= { rsiAlarmEntry 17 }

rsiOrigHostId OBJECT-TYPE
    SYNTAX          INTEGER
    ACCESS          read-only
    STATUS          mandatory
    DESCRIPTION     
            "This is the Id of the host on which the 
             subsystem which has raised this alarm is running"
    ::= { rsiAlarmEntry 18 }

rsiOrigHostName OBJECT-TYPE
    SYNTAX          OCTET STRING
    ACCESS          read-only
    STATUS          mandatory
    DESCRIPTION     
            "This is the name of the host on which the 
             subsystem which has raised this alarm is running"
    ::= { rsiAlarmEntry 19 }

rsiAlarmSeverityTable OBJECT-TYPE
    SYNTAX          SEQUENCE OF RsiAlarmSeverityEntry
    ACCESS          not-accessible
    STATUS          mandatory
    DESCRIPTION     
            "This table stores the table of alarm severity"
    ::= { rsiCommonMib 5 }

rsiAlarmSeverityEntry OBJECT-TYPE
    SYNTAX          RsiAlarmSeverityEntry
    ACCESS          not-accessible
    STATUS          mandatory
    DESCRIPTION     
            "Description of an alarm severity entry"
    INDEX           { rsiErrorCode }
    ::= { rsiAlarmSeverityTable 1 }

RsiAlarmSeverityEntry ::=
    SEQUENCE {
        rsiErrorCode                    INTEGER,
        rsiSeverity                     INTEGER,
        rsiToBeClearedErrorCode         INTEGER,
        rsiTrapGenerationFlag           INTEGER,
        rsiTrapCategory                 INTEGER,
        rsiErrorCodeDesc                OCTET STRING,
        rsiAlarmSeverityRowStatus       RowStatus
    }

rsiErrorCode OBJECT-TYPE
    SYNTAX          INTEGER
    ACCESS          read-write
    STATUS          mandatory
    DESCRIPTION     
            "This is the errorCode of the alarm"
    ::= { rsiAlarmSeverityEntry 1 }

rsiSeverity OBJECT-TYPE
    SYNTAX          INTEGER { critical(0), major(1), minor(2), 
                        warning(3), normal(4), unknown(5), clear(6) }
    ACCESS          read-write
    STATUS          mandatory
    DESCRIPTION     
            "This is the severity level of the alarm. 
             This severity can be modified at run time. By changing 
             this severity, any NEW alarm raised for this error code,
             will have this new severity. All existing alarms for the
             given error code will have the old severity.
             If the severity of an alarm is CLEAR, then this denotes
             that this alarm will act as an auto-clear for an existing
             alarm with error code same as the value of 
             rsiToBeClearedErrorCode for this entry. 
             Also, in this case the severity cannot be modified. 
              The unknown sevrity is depricated. normal severity relates 
             to informational alarms"
    ::= { rsiAlarmSeverityEntry 2 }

rsiToBeClearedErrorCode OBJECT-TYPE
    SYNTAX          INTEGER
    ACCESS          read-write
    STATUS          mandatory
    DESCRIPTION     
            "If the severity of this alarm is CLEAR, then this alarm
             will act as an auto-clear for an alarm with this error 
             code.
             If the severity of this alarm is not CLEAR, then this
             will have the value of 0."
    ::= { rsiAlarmSeverityEntry 3 }

rsiTrapGenerationFlag OBJECT-TYPE
    SYNTAX          INTEGER { trapToBeGenerated(1), 
                        trapNotToBeGenerated(2) }
    ACCESS          read-write
    STATUS          obsolete
    DESCRIPTION     
            "Flag to indicate whether trap is to be generated
             for an alarm with this error code.
             
             This object is deprecated and is kept here for backward compatibility
             All get to this object will result in zero and all set will fail"
    ::= { rsiAlarmSeverityEntry 4 }

rsiTrapCategory OBJECT-TYPE
    SYNTAX          INTEGER { communicationFailureTrap(0), 
                        configurationErrorTrap(1), systemFaultsTrap(2), 
                        systemCapacityTrap(3), resourceFailureTrap(4), 
                        applicationErrorTrap(5), thresholdAlarmTrap(6), 
                        securityAlarmTrap(7) }
    ACCESS          read-write
    STATUS          mandatory
    DESCRIPTION     
            " It describes the trap category."
    ::= { rsiAlarmSeverityEntry 5 }

rsiErrorCodeDesc OBJECT-TYPE
    SYNTAX          OCTET STRING
    ACCESS          read-write
    STATUS          mandatory
    DESCRIPTION     
            "It describes the error code"
    ::= { rsiAlarmSeverityEntry 6 }

rsiAlarmSeverityRowStatus OBJECT-TYPE
    SYNTAX          RowStatus
    ACCESS          read-write
    STATUS          mandatory
    DESCRIPTION     
            "This is for dynamic addition/deletion of error codes.
             For creating a new error code, only 'createAndGo' is
             supported. Deletion an alarm is currently not 
             supported"
    ::= { rsiAlarmSeverityEntry 7 }

rsiSystemTable OBJECT-TYPE
    SYNTAX          SEQUENCE OF RsiSystemEntry
    ACCESS          not-accessible
    STATUS          mandatory
    DESCRIPTION     
            "This table stores info about all RSI systems"
    ::= { rsiCommonMib 6 }

rsiSystemEntry OBJECT-TYPE
    SYNTAX          RsiSystemEntry
    ACCESS          not-accessible
    STATUS          mandatory
    DESCRIPTION     
            "Description of an RSI system"
    INDEX           { rsiSystemId }
    ::= { rsiSystemTable 1 }

RsiSystemEntry ::=
    SEQUENCE {
        rsiSystemId                     INTEGER,
        rsiSystemDescription            OCTET STRING,
        rsiSystemContactLocation        OCTET STRING,
        rsiSystemContactPerson          OCTET STRING,
        rsiSystemContactPhoneNo         OCTET STRING,
        rsiSystemVersionId              OCTET STRING,
        rsiSystemInstallationDateTime   DisplayString,
        rsiSystemActiveSince            DisplayString
    }

rsiSystemId OBJECT-TYPE
    SYNTAX          INTEGER
    ACCESS          read-only
    STATUS          mandatory
    DESCRIPTION     
            "This is the component id of the system"
    ::= { rsiSystemEntry 1 }

rsiSystemDescription OBJECT-TYPE
    SYNTAX          OCTET STRING
    ACCESS          read-write
    STATUS          mandatory
    DESCRIPTION     
            "Textual Description of the System"
    ::= { rsiSystemEntry 2 }

rsiSystemContactLocation OBJECT-TYPE
    SYNTAX          OCTET STRING
    ACCESS          read-write
    STATUS          mandatory
    DESCRIPTION     
            "Address of the Contact Location for this System"
    ::= { rsiSystemEntry 3 }

rsiSystemContactPerson OBJECT-TYPE
    SYNTAX          OCTET STRING
    ACCESS          read-write
    STATUS          mandatory
    DESCRIPTION     
            "Name of the Contact Person for this System in the above
             mentioned Location"
    ::= { rsiSystemEntry 4 }

rsiSystemContactPhoneNo OBJECT-TYPE
    SYNTAX          OCTET STRING
    ACCESS          read-write
    STATUS          mandatory
    DESCRIPTION     
            "Phone No. of the Contact Person for this System"
    ::= { rsiSystemEntry 5 }

rsiSystemVersionId OBJECT-TYPE
    SYNTAX          OCTET STRING
    ACCESS          read-only
    STATUS          mandatory
    DESCRIPTION     
            "Version Id of the software installed on this System"
    ::= { rsiSystemEntry 6 }

rsiSystemInstallationDateTime OBJECT-TYPE
    SYNTAX          DisplayString
    ACCESS          read-only
    STATUS          mandatory
    DESCRIPTION     
            "Date of installation of the current sofware for this 
             System"
    ::= { rsiSystemEntry 7 }

rsiSystemActiveSince OBJECT-TYPE
    SYNTAX          DisplayString
    ACCESS          read-only
    STATUS          mandatory
    DESCRIPTION     
            "Date since which this System is active"
    ::= { rsiSystemEntry 8 }

rsiFunctionalUnitTable OBJECT-TYPE
    SYNTAX          SEQUENCE OF RsiFunctionalUnitEntry
    ACCESS          not-accessible
    STATUS          mandatory
    DESCRIPTION     
            "This table stores the information about all RSI FUs"
    ::= { rsiCommonMib 7 }

rsiFunctionalUnitEntry OBJECT-TYPE
    SYNTAX          RsiFunctionalUnitEntry
    ACCESS          not-accessible
    STATUS          mandatory
    DESCRIPTION     
            "Description of an RSI FU"
    INDEX           { rsiFunctionalUnitId }
    ::= { rsiFunctionalUnitTable 1 }

RsiFunctionalUnitEntry ::=
    SEQUENCE {
        rsiFunctionalUnitId             INTEGER,
        rsiFUVersionId                  OCTET STRING,
        rsiFUInstallationDateTime       DisplayString
    }

rsiFunctionalUnitId OBJECT-TYPE
    SYNTAX          INTEGER
    ACCESS          read-only
    STATUS          mandatory
    DESCRIPTION     
            "This is the component id of the Functional Unit"
    ::= { rsiFunctionalUnitEntry 1 }

rsiFUVersionId OBJECT-TYPE
    SYNTAX          OCTET STRING
    ACCESS          read-only
    STATUS          mandatory
    DESCRIPTION     
            "Version Id of the software installed on this FU"
    ::= { rsiFunctionalUnitEntry 2 }

rsiFUInstallationDateTime OBJECT-TYPE
    SYNTAX          DisplayString
    ACCESS          read-only
    STATUS          mandatory
    DESCRIPTION     
            "Date of installation of the current sofware for this FU"
    ::= { rsiFunctionalUnitEntry 3 }

rsiSubsystemTable OBJECT-TYPE
    SYNTAX          SEQUENCE OF RsiSubsystemEntry
    ACCESS          not-accessible
    STATUS          mandatory
    DESCRIPTION     
            "This table stores the information about all RSI 
             Subsystems"
    ::= { rsiCommonMib 8 }

rsiSubsystemEntry OBJECT-TYPE
    SYNTAX          RsiSubsystemEntry
    ACCESS          not-accessible
    STATUS          mandatory
    DESCRIPTION     
            "Description of an RSI Subsystem"
    INDEX           { rsiSubsystemId }
    ::= { rsiSubsystemTable 1 }

RsiSubsystemEntry ::=
    SEQUENCE {
        rsiSubsystemId                  INTEGER,
        rsiSubsystemVersionId           OCTET STRING,
        rsiSubsystemInstallationDateTime DisplayString,
        rsiSubsystemActiveSince         DisplayString,
        rsiSubsystemRole                DisplayString
    }

rsiSubsystemId OBJECT-TYPE
    SYNTAX          INTEGER
    ACCESS          read-only
    STATUS          mandatory
    DESCRIPTION     
            "This is the component id of the Subsystem"
    ::= { rsiSubsystemEntry 1 }

rsiSubsystemVersionId OBJECT-TYPE
    SYNTAX          OCTET STRING
    ACCESS          read-only
    STATUS          mandatory
    DESCRIPTION     
            "Version Id of the software installed on this Subsystem"
    ::= { rsiSubsystemEntry 2 }

rsiSubsystemInstallationDateTime OBJECT-TYPE
    SYNTAX          DisplayString
    ACCESS          read-only
    STATUS          mandatory
    DESCRIPTION     
            "Date of installation of the current sofware for this 
             Subsystem"
    ::= { rsiSubsystemEntry 3 }

rsiSubsystemActiveSince OBJECT-TYPE
    SYNTAX          DisplayString
    ACCESS          read-only
    STATUS          mandatory
    DESCRIPTION     
            "Date since which this Subsystem is active"
    ::= { rsiSubsystemEntry 4 }

rsiSubsystemRole OBJECT-TYPE
    SYNTAX          DisplayString
    ACCESS          read-only
    STATUS          mandatory
    DESCRIPTION     
            "whether this Subsystem is active/standby"
    ::= { rsiSubsystemEntry 5 }

rsiUserSecurityPolicyTable OBJECT-TYPE
    SYNTAX          SEQUENCE OF RsiUserSecurityPolicyEntry
    ACCESS          not-accessible
    STATUS          mandatory
    DESCRIPTION     
            "This table stores the information about the 
             security policies available for a user "
    ::= { rsiCommonMib 9 }

rsiUserSecurityPolicyEntry OBJECT-TYPE
    SYNTAX          RsiUserSecurityPolicyEntry
    ACCESS          not-accessible
    STATUS          mandatory
    DESCRIPTION     
            "Description of a User Security Policy Entry"
    INDEX           { rsiUserSecurityPolicyName }
    ::= { rsiUserSecurityPolicyTable 1 }

RsiUserSecurityPolicyEntry ::=
    SEQUENCE {
        rsiUserSecurityPolicyName       OCTET STRING,
        rsiUserSecurityPolicyId         INTEGER,
        rsiUserSecurityPasswdExpiryDays INTEGER,
        rsiUserSecurityMaxFailedAttempts INTEGER,
        rsiUserSecurityMinPasswordLen   INTEGER,
        rsiUserSecurityPasswdRecylingPolicy   INTEGER,
        rsiUserSecurityPasswdRecylingMinDaysToUse         INTEGER,
        rsiUserSecurityPasswdRecylingNumOfPasswds         INTEGER,
        rsiUserSecurityMinNumberOfNumericCharInPasswd             INTEGER,
        rsiUserSecurityMinNumberOfSpecialCharInPasswd             INTEGER,
        rsiNumberOfLoginsAllowed        INTEGER,
        rsiUserSecurityPolicyRowStatus  RowStatus
    }

rsiUserSecurityPolicyName OBJECT-TYPE
    SYNTAX          OCTET STRING
    ACCESS          read-only
    STATUS          mandatory
    DESCRIPTION     
            "This is the human readable name for this policy"
    ::= { rsiUserSecurityPolicyEntry 1 }

rsiUserSecurityPolicyId OBJECT-TYPE
    SYNTAX          INTEGER
    ACCESS          read-only
    STATUS          mandatory
    DESCRIPTION     
            "This is the unique id associated with this policy"
    ::= { rsiUserSecurityPolicyEntry 2 }

rsiUserSecurityPasswdExpiryDays OBJECT-TYPE
    SYNTAX          INTEGER
    ACCESS          read-write
    STATUS          mandatory
    DESCRIPTION     
            "Days after which the currentpassword would expire.
             Default Value - 30 days."
    ::= { rsiUserSecurityPolicyEntry 3 }

rsiUserSecurityMaxFailedAttempts OBJECT-TYPE
    SYNTAX          INTEGER
    ACCESS          read-write
    STATUS          mandatory
    DESCRIPTION     
            "Maximum no. of failed login attempts at one go, 
             after which the user account will be locked. 
             Default Value - 3 attempts."
    ::= { rsiUserSecurityPolicyEntry 4 }

rsiUserSecurityMinPasswordLen OBJECT-TYPE
    SYNTAX          INTEGER
    ACCESS          read-write
    STATUS          mandatory
    DESCRIPTION     
            "Maximum no. of failed login attempts at one go, 
             after which the user account will be locked. 
             Default Value - 6 characters."
    ::= { rsiUserSecurityPolicyEntry 5 }

rsiUserSecurityPasswdRecylingPolicy OBJECT-TYPE
    SYNTAX          INTEGER { timeBased(0), numberBased(1), 
                        timeAndNumberBased(2) }
    ACCESS          read-write
    STATUS          mandatory
    DESCRIPTION     
            "Old passwords of a user are saved, and based 
             on the recycling policy, the old password can be 
             reused. 
             Time Based Password Recycling: no. of days after 
             which the new password can have the same value as 
             the old password which had been previously modified. 
             Number Based Password Recycling: no. of passwords 
             that have have been changed, after which an 
             old password can be reused. 
             Default Value - timeAndNumberBased"
    ::= { rsiUserSecurityPolicyEntry 6 }

rsiUserSecurityPasswdRecylingMinDaysToUse OBJECT-TYPE
    SYNTAX          INTEGER
    ACCESS          read-write
    STATUS          mandatory
    DESCRIPTION     
            "If the Password Recycling Policy is Time Based, 
             then the number of days after which the old password 
             can be reused. 
             Default Value - 0."
    ::= { rsiUserSecurityPolicyEntry 7 }

rsiUserSecurityPasswdRecylingNumOfPasswds OBJECT-TYPE
    SYNTAX          INTEGER
    ACCESS          read-write
    STATUS          mandatory
    DESCRIPTION     
            "If the Password Recycling Policy is Number Based, 
             then the number of password changes after which the 
             old password can be reused. 
             Default Value - 0"
    ::= { rsiUserSecurityPolicyEntry 8 }

rsiUserSecurityMinNumberOfNumericCharInPasswd OBJECT-TYPE
    SYNTAX          INTEGER
    ACCESS          read-write
    STATUS          mandatory
    DESCRIPTION     
            "This defines the minimum number of numeric characters
             that need to be present in a password.
             Default Value - 0"
    ::= { rsiUserSecurityPolicyEntry 9 }

rsiUserSecurityMinNumberOfSpecialCharInPasswd OBJECT-TYPE
    SYNTAX          INTEGER
    ACCESS          read-write
    STATUS          mandatory
    DESCRIPTION     
            "This defines the minimum number of special characters
             that need to be present in a password.
             Default Value - 0"
    ::= { rsiUserSecurityPolicyEntry 10 }

rsiNumberOfLoginsAllowed OBJECT-TYPE
    SYNTAX          INTEGER
    ACCESS          read-write
    STATUS          mandatory
    DESCRIPTION     
            "This defines the maximum number of logins allowed simultaneousl"
    ::= { rsiUserSecurityPolicyEntry 11 }

rsiUserSecurityPolicyRowStatus OBJECT-TYPE
    SYNTAX          RowStatus
    ACCESS          read-write
    STATUS          mandatory
    DESCRIPTION     
            "This is for dynamic addition/deletion of policies.
             For creating a new policy, only 'createAndGo' is
             supported. For deleting an existing row, 'delete'
             is supported"
    ::= { rsiUserSecurityPolicyEntry 12 }

rsiFeatureTable OBJECT-TYPE
    SYNTAX          SEQUENCE OF RsiFeatureEntry
    ACCESS          not-accessible
    STATUS          mandatory
    DESCRIPTION     
            "This table stores the information about the
             features supported for management purposes."
    ::= { rsiCommonMib 10 }

rsiFeatureEntry OBJECT-TYPE
    SYNTAX          RsiFeatureEntry
    ACCESS          not-accessible
    STATUS          mandatory
    DESCRIPTION     
            "Description of a User Security Policy Entry"
    INDEX           { rsiFeatureId }
    ::= { rsiFeatureTable 1 }

RsiFeatureEntry ::=
    SEQUENCE {
        rsiFeatureId                    INTEGER,
        rsiFeatureName                  OCTET STRING,
        rsiAPINames                     OCTET STRING
    }

rsiFeatureId OBJECT-TYPE
    SYNTAX          INTEGER
    ACCESS          read-only
    STATUS          mandatory
    DESCRIPTION     
            "This is the unique id of the feature"
    ::= { rsiFeatureEntry 1 }

rsiFeatureName OBJECT-TYPE
    SYNTAX          OCTET STRING
    ACCESS          read-only
    STATUS          mandatory
    DESCRIPTION     
            "Name assigned to this feature"
    ::= { rsiFeatureEntry 2 }

rsiAPINames OBJECT-TYPE
    SYNTAX          OCTET STRING
    ACCESS          read-only
    STATUS          mandatory
    DESCRIPTION     
            "List of API Names which belong to the given feature.
             This will be a comma seperated list, and could have
             been described as sequence of strings."
    ::= { rsiFeatureEntry 3 }

rsiRoleTable OBJECT-TYPE
    SYNTAX          SEQUENCE OF RsiRoleEntry
    ACCESS          not-accessible
    STATUS          mandatory
    DESCRIPTION     
            "This table stores the information about the
             possible user roles."
    ::= { rsiCommonMib 11 }

rsiRoleEntry OBJECT-TYPE
    SYNTAX          RsiRoleEntry
    ACCESS          not-accessible
    STATUS          mandatory
    DESCRIPTION     
            "Description of a Role"
    INDEX           { rsiRoleName }
    ::= { rsiRoleTable 1 }

RsiRoleEntry ::=
    SEQUENCE {
        rsiRoleName                     OCTET STRING,
        rsiRoleId                       INTEGER,
        rsiFeatureIds                   OCTET STRING,
        rsiRoleRowStatus                RowStatus
    }

rsiRoleName OBJECT-TYPE
    SYNTAX          OCTET STRING
    ACCESS          read-only
    STATUS          mandatory
    DESCRIPTION     
            "Unique Name assigned to this role"
    ::= { rsiRoleEntry 1 }

rsiRoleId OBJECT-TYPE
    SYNTAX          INTEGER
    ACCESS          read-only
    STATUS          mandatory
    DESCRIPTION     
            "This is the unique id associated with this role."
    ::= { rsiRoleEntry 2 }

rsiFeatureIds OBJECT-TYPE
    SYNTAX          OCTET STRING
    ACCESS          read-write
    STATUS          mandatory
    DESCRIPTION     
            "List of Feature Ids which belong to the given role.
             This will be a comma seperated list, and could have
             been described as sequence of strings."
    ::= { rsiRoleEntry 3 }

rsiRoleRowStatus OBJECT-TYPE
    SYNTAX          RowStatus
    ACCESS          read-write
    STATUS          mandatory
    DESCRIPTION     
            "This is for dynamic addition/deletion of roles.
             For creating a new role entry, only 'createAndGo' is
             supported. For deleting an existing row, 'delete'
             is supported"
    ::= { rsiRoleEntry 4 }

rsiUserTable OBJECT-TYPE
    SYNTAX          SEQUENCE OF RsiUserEntry
    ACCESS          not-accessible
    STATUS          mandatory
    DESCRIPTION     
            "This table stores the information about all users 
             accessing the RSI solution"
    ::= { rsiCommonMib 12 }

rsiUserEntry OBJECT-TYPE
    SYNTAX          RsiUserEntry
    ACCESS          not-accessible
    STATUS          mandatory
    DESCRIPTION     
            "Description of an RSI Subsystem"
    INDEX           { rsiUserId }
    ::= { rsiUserTable 1 }

RsiUserEntry ::=
    SEQUENCE {
        rsiUserId                       OCTET STRING,
        rsiUserFirstName                OCTET STRING,
        rsiUserMiddleName               OCTET STRING,
        rsiUserLastName                 OCTET STRING,
        rsiUserActivationDate           DisplayString,
        rsiUserExpiryDate               DisplayString,
        rsiUserStatus                   INTEGER,
        rsiUserPolicyId                 INTEGER,
        rsiUserRoles                    OCTET STRING,
        rsiLoggingEnableOption          INTEGER,
        rsiUserRowStatus                RowStatus
    }

rsiUserId OBJECT-TYPE
    SYNTAX          OCTET STRING
    ACCESS          read-only
    STATUS          mandatory
    DESCRIPTION     
            "This is the unique id of a user"
    ::= { rsiUserEntry 1 }

rsiUserFirstName OBJECT-TYPE
    SYNTAX          OCTET STRING
    ACCESS          read-write
    STATUS          mandatory
    DESCRIPTION     
            "This is the First Name of the user. 
             Mandatory field for creating a new user"
    ::= { rsiUserEntry 2 }

rsiUserMiddleName OBJECT-TYPE
    SYNTAX          OCTET STRING
    ACCESS          read-write
    STATUS          mandatory
    DESCRIPTION     
            "This is the Middle Name of the user.
             Mandatory field for creating a new user"
    ::= { rsiUserEntry 3 }

rsiUserLastName OBJECT-TYPE
    SYNTAX          OCTET STRING
    ACCESS          read-write
    STATUS          mandatory
    DESCRIPTION     
            "This is the Last Name of the user.
             Mandatory field for creating a new user"
    ::= { rsiUserEntry 4 }

rsiUserActivationDate OBJECT-TYPE
    SYNTAX          DisplayString (SIZE(19))
    ACCESS          read-only
    STATUS          mandatory
    DESCRIPTION     
            "This is the time at which the user account was created.
             format is 'YYYY:MM:DD HH:MM:SS'.
             This attribute cannot be modified."
    ::= { rsiUserEntry 5 }

rsiUserExpiryDate OBJECT-TYPE
    SYNTAX          DisplayString (SIZE(19))
    ACCESS          read-only
    STATUS          mandatory
    DESCRIPTION     
            "This is the time at which the user account will expire.
             format is 'YYYY:MM:DD HH:MM:SS'. 
             This attribute cannot be modified."
    ::= { rsiUserEntry 6 }

rsiUserStatus OBJECT-TYPE
    SYNTAX          INTEGER { new(0), active(1), locked(2), inactive(3), 
                        deleted(4) }
    ACCESS          read-write
    STATUS          mandatory
    DESCRIPTION     
            "This is the user account status.
             This attribute is not needed while creating a user,
             but can be modified.
             This field holds no importance for creating a new user,
             because by default the value of status will be new."
    ::= { rsiUserEntry 7 }

rsiUserPolicyId OBJECT-TYPE
    SYNTAX          INTEGER
    ACCESS          read-write
    STATUS          mandatory
    DESCRIPTION     
            "This identifies the security policy opted for the user.
             Mandatory field for creating a new user"
    ::= { rsiUserEntry 8 }

rsiUserRoles OBJECT-TYPE
    SYNTAX          OCTET STRING
    ACCESS          read-only
    STATUS          mandatory
    DESCRIPTION     
            "This is the list of role ids assigned to a given user. 
             This will be a comma seperated list, and could have
             been described as sequence of integers.
             This attribute cannot be modified.
             By default when a user is created, he is assigned a
             role, and if a new role needs to be assigned to a
             user, then entries should be manipulated at the
             user-role table (rsiUserRoleTable)"
    ::= { rsiUserEntry 9 }

rsiLoggingEnableOption OBJECT-TYPE
    SYNTAX          INTEGER
    ACCESS          read-write
    STATUS          mandatory
    DESCRIPTION     
            "To Enable logging set the LSB to 1 and to disable logging set the LSB to 0."
    ::= { rsiUserEntry 10 }

rsiUserRowStatus OBJECT-TYPE
    SYNTAX          RowStatus
    ACCESS          read-write
    STATUS          mandatory
    DESCRIPTION     
            "This is for dynamic addition/deletion of users.
             For creating a new user entry, only 'createAndGo' is
             supported. For deleting an existing row, 'delete'
             is supported"
    ::= { rsiUserEntry 11 }

rsiUserRoleTable OBJECT-TYPE
    SYNTAX          SEQUENCE OF RsiUserRoleEntry
    ACCESS          not-accessible
    STATUS          mandatory
    DESCRIPTION     
            "This table contains the list of component Ids,
             which have been assigned to a given user for a
             given role. "
    ::= { rsiCommonMib 13 }

rsiUserRoleEntry OBJECT-TYPE
    SYNTAX          RsiUserRoleEntry
    ACCESS          not-accessible
    STATUS          mandatory
    DESCRIPTION     
            "Description of a user-role association. Note UserId
             and RoleId are index of foreign tables"
    INDEX           { rsiUserId, rsiRoleId }
    ::= { rsiUserRoleTable 1 }

RsiUserRoleEntry ::=
    SEQUENCE {
        rsiComponentIdList              OCTET STRING,
        rsiUserRoleRowStatus            RowStatus
    }

rsiComponentIdList OBJECT-TYPE
    SYNTAX          OCTET STRING
    ACCESS          read-write
    STATUS          mandatory
    DESCRIPTION     
            "This is a comma separated list of component Ids
             which can be managed by the given user with the
             given role.
             This attribute is not modifiable"
    ::= { rsiUserRoleEntry 1 }

rsiUserRoleRowStatus OBJECT-TYPE
    SYNTAX          RowStatus
    ACCESS          read-write
    STATUS          mandatory
    DESCRIPTION     
            "This is for dynamic addition/deletion of roles
             associated with a user.
             For creating a new user-role entry, only 'createAndGo' 
             is supported. For deleting an existing row, 'delete'
             is supported"
    ::= { rsiUserRoleEntry 2 }

rsiPerformanceHistoryTable OBJECT-TYPE
    SYNTAX          SEQUENCE OF RsiPerformanceHistoryEntry
    ACCESS          not-accessible
    STATUS          mandatory
    DESCRIPTION     
            "This table contains the performance history of all
             the components."
    ::= { rsiCommonMib 14 }

rsiPerformanceHistoryEntry OBJECT-TYPE
    SYNTAX          RsiPerformanceHistoryEntry
    ACCESS          not-accessible
    STATUS          mandatory
    DESCRIPTION     
            "Description of the performance oid and its value for
             a given component at a give time. 
             This table will give the value of a performance OID
             for a given component, at the given time.
             Note: rsiCompId is index of a foreign table."
    INDEX           { rsiCompId, rsiPerfOid, rsiPerfTimestamp }
    ::= { rsiPerformanceHistoryTable 1 }

RsiPerformanceHistoryEntry ::=
    SEQUENCE {
        rsiPerfTimestamp                INTEGER,
        rsiPerfOid                      OBJECT IDENTIFIER,
        rsiPerfValue                    DisplayString
    }

rsiPerfTimestamp OBJECT-TYPE
    SYNTAX          INTEGER
    ACCESS          read-only
    STATUS          mandatory
    DESCRIPTION     
            "Time at which the performance was measured.
             This is the time in seconds since the Epoch 
             (00:00:00 UTC, January 1, 1970)."
    ::= { rsiPerformanceHistoryEntry 1 }

rsiPerfOid OBJECT-TYPE
    SYNTAX          OBJECT IDENTIFIER
    ACCESS          read-only
    STATUS          mandatory
    DESCRIPTION     
            "OID in MIB for which the performance was measured."
    ::= { rsiPerformanceHistoryEntry 2 }

rsiPerfValue OBJECT-TYPE
    SYNTAX          DisplayString
    ACCESS          read-only
    STATUS          mandatory
    DESCRIPTION     
            "value of the OID for which performance was measured."
    ::= { rsiPerformanceHistoryEntry 3 }

rsiPerformanceThresholdTable OBJECT-TYPE
    SYNTAX          SEQUENCE OF RsiPerformanceThresholdEntry
    ACCESS          not-accessible
    STATUS          mandatory
    DESCRIPTION     
            "This table contains the performance thresholds for all
             the OIDs."
    ::= { rsiCommonMib 15 }

rsiPerformanceThresholdEntry OBJECT-TYPE
    SYNTAX          RsiPerformanceThresholdEntry
    ACCESS          not-accessible
    STATUS          mandatory
    DESCRIPTION     
            "Description of the performance oid and its rising
             and falling threshold values, along with the alarm
             severity of the alarm to be raised."
    INDEX           { rsiPerfThresholdOid, rsiPerfThresholdId }
    ::= { rsiPerformanceThresholdTable 1 }

RsiPerformanceThresholdEntry ::=
    SEQUENCE {
        rsiPerfThresholdOid             OBJECT IDENTIFIER,
        rsiPerfThresholdId              INTEGER,
        rsiPerfThresholdRisingVal       INTEGER,
        rsiPerfThresholdFallingVal      INTEGER,
        rsiPerfThresholdSeverity        INTEGER,
        rsiPerfThresholdRowStatus       RowStatus
    }

rsiPerfThresholdOid OBJECT-TYPE
    SYNTAX          OBJECT IDENTIFIER
    ACCESS          read-only
    STATUS          mandatory
    DESCRIPTION     
            "OID in MIB for which the performance threshold has
             been defined."
    ::= { rsiPerformanceThresholdEntry 1 }

rsiPerfThresholdId OBJECT-TYPE
    SYNTAX          INTEGER
    ACCESS          read-only
    STATUS          mandatory
    DESCRIPTION     
            "Unique identifier of the given performance threshold."
    ::= { rsiPerformanceThresholdEntry 2 }

rsiPerfThresholdRisingVal OBJECT-TYPE
    SYNTAX          INTEGER
    ACCESS          read-write
    STATUS          mandatory
    DESCRIPTION     
            "High Water Mark for the given threshold"
    ::= { rsiPerformanceThresholdEntry 3 }

rsiPerfThresholdFallingVal OBJECT-TYPE
    SYNTAX          INTEGER
    ACCESS          read-write
    STATUS          mandatory
    DESCRIPTION     
            "Low Water Mark for the given threshold"
    ::= { rsiPerformanceThresholdEntry 4 }

rsiPerfThresholdSeverity OBJECT-TYPE
    SYNTAX          INTEGER { critical(0), major(1), minor(2), 
                        warning(3), normal(4) }
    ACCESS          read-write
    STATUS          mandatory
    DESCRIPTION     
            "Severity of the alarm to be raised on crossing the
             threshold."
    ::= { rsiPerformanceThresholdEntry 5 }

rsiPerfThresholdRowStatus OBJECT-TYPE
    SYNTAX          RowStatus
    ACCESS          read-write
    STATUS          mandatory
    DESCRIPTION     
            "This is for dynamic addition/deletion of performance
             thresholds.
             For creating a new threshold entry, only 'createAndGo' is
             supported. For deleting an existing row, 'destroy'
             is supported"
    ::= { rsiPerformanceThresholdEntry 6 }

rsiAlarmPoliciesTable OBJECT-TYPE
    SYNTAX          SEQUENCE OF RsiAlarmPoliciesEntry
    ACCESS          not-accessible
    STATUS          mandatory
    DESCRIPTION     
            "This table contains the performance thresholds for all
             the OIDs."
    ::= { rsiCommonMib 16 }

rsiAlarmPoliciesEntry OBJECT-TYPE
    SYNTAX          RsiAlarmPoliciesEntry
    ACCESS          not-accessible
    STATUS          mandatory
    DESCRIPTION     
            "Description of the alarm policies associated with a 
             severity."
    INDEX           { rsiAlarmPolicySeverity }
    ::= { rsiAlarmPoliciesTable 1 }

RsiAlarmPoliciesEntry ::=
    SEQUENCE {
        rsiAlarmPolicySeverity          INTEGER,
        rsiAlarmSeverityEscalationTimeInterval      INTEGER,
        rsiAlarmAutoAckUpperThresholdLimit  INTEGER,
        rsiAlarmAutoAckRetentionTimeInterval    INTEGER
    }

rsiAlarmPolicySeverity OBJECT-TYPE
    SYNTAX          INTEGER { critical(0), major(1), minor(2), 
                        warning(3), normal(4) }
    ACCESS          read-only
    STATUS          mandatory
    DESCRIPTION     
            "severity of the alarm for which this policy has 
             been defined."
    ::= { rsiAlarmPoliciesEntry 1 }

rsiAlarmSeverityEscalationTimeInterval OBJECT-TYPE
    SYNTAX          INTEGER
    ACCESS          read-write
    STATUS          mandatory
    DESCRIPTION     
            "This signifies the time interval for which an un-acked
             alarms' severity may not be raised to the next level.
             Note the unit of this time interval is hrs.This can not be
             set for critical severity"
    ::= { rsiAlarmPoliciesEntry 2 }

rsiAlarmAutoAckUpperThresholdLimit OBJECT-TYPE
    SYNTAX          INTEGER
    ACCESS          read-write
    STATUS          mandatory
    DESCRIPTION     
            "The number of un-acked alarms that are to be retained
             for the given severity at any time."
    ::= { rsiAlarmPoliciesEntry 3 }

rsiAlarmAutoAckRetentionTimeInterval OBJECT-TYPE
    SYNTAX          INTEGER
    ACCESS          read-write
    STATUS          mandatory
    DESCRIPTION     
            "This signifies that the time interval for which all
             un-acked alarms are not auto acked.
             Note the unit of this time interval is hrs."
    ::= { rsiAlarmPoliciesEntry 4 }

rsiLoggedInUsersTable OBJECT-TYPE
    SYNTAX          SEQUENCE OF RsiLoggedInUsersEntry
    ACCESS          not-accessible
    STATUS          mandatory
    DESCRIPTION     
            "This table contains the information about the currently
             logged in users. "
    ::= { rsiCommonMib 17 }

rsiLoggedInUsersEntry OBJECT-TYPE
    SYNTAX          RsiLoggedInUsersEntry
    ACCESS          not-accessible
    STATUS          mandatory
    DESCRIPTION     
            "Description of a currently logged-in user. "
    INDEX           { rsiUserId }
    ::= { rsiLoggedInUsersTable 1 }

RsiLoggedInUsersEntry ::=
    SEQUENCE {
        rsiLoggedInUserSessionLoginTime DisplayString,
        rsiLoggedInUserLastCommandTime  DisplayString,
        rsiLoggedInUserRowStatus        RowStatus
    }

rsiLoggedInUserSessionLoginTime OBJECT-TYPE
    SYNTAX          DisplayString (SIZE(19))
    ACCESS          read-only
    STATUS          mandatory
    DESCRIPTION     
            "This is the time at which this user logged in, and is in
             'YYYY:MM:DD HH:MM:SS' format. "
    ::= { rsiLoggedInUsersEntry 1 }

rsiLoggedInUserLastCommandTime OBJECT-TYPE
    SYNTAX          DisplayString (SIZE(19))
    ACCESS          read-only
    STATUS          mandatory
    DESCRIPTION     
            "This is the time at which this user issued the last 
             command, and is in 'YYYY:MM:DD HH:MM:SS' format. "
    ::= { rsiLoggedInUsersEntry 2 }

rsiLoggedInUserRowStatus OBJECT-TYPE
    SYNTAX          RowStatus
    ACCESS          read-write
    STATUS          mandatory
    DESCRIPTION     
            "This is for forcefully logging-off a user. When set
             to 'destroy', this user will be logged off. No other
             value can be set for this RowStatus. "
    ::= { rsiLoggedInUsersEntry 3 }

rsiSessionLogTable OBJECT-TYPE
    SYNTAX          SEQUENCE OF RsiSessionLogEntry
    ACCESS          not-accessible
    STATUS          mandatory
    DESCRIPTION     
            "This table contains the information about all the
             sessions that existed or are existing in the system. "
    ::= { rsiCommonMib 18 }

rsiSessionLogEntry OBJECT-TYPE
    SYNTAX          RsiSessionLogEntry
    ACCESS          not-accessible
    STATUS          mandatory
    DESCRIPTION     
            "Description of a Session log."
    INDEX           { rsiSessionLogUser, rsiSessionLogTime, 
                      rsiSessionLogId }
    ::= { rsiSessionLogTable 1 }

RsiSessionLogEntry ::=
    SEQUENCE {
        rsiSessionLogUser               DisplayString,
        rsiSessionLogTime               INTEGER,
        rsiSessionLogId                 INTEGER,
        rsiSessionLogDisplayTime        DisplayString,
        rsiSessionLogApiName            DisplayString,
        rsiSessionLogStatus             DisplayString
    }

rsiSessionLogUser OBJECT-TYPE
    SYNTAX          DisplayString
    ACCESS          read-only
    STATUS          mandatory
    DESCRIPTION     
            "This is the name of the user for which this session log
             was created. "
    ::= { rsiSessionLogEntry 1 }

rsiSessionLogTime OBJECT-TYPE
    SYNTAX          INTEGER
    ACCESS          read-only
    STATUS          mandatory
    DESCRIPTION     
            "This is the time at which this session log was created, 
             and is in integer format. This is the time in seconds 
             since the Epoch (00:00:00 UTC, January 1, 1970). "
    ::= { rsiSessionLogEntry 2 }

rsiSessionLogId OBJECT-TYPE
    SYNTAX          INTEGER
    ACCESS          read-only
    STATUS          mandatory
    DESCRIPTION     
            "This is the unique id associated with this session log."
    ::= { rsiSessionLogEntry 3 }

rsiSessionLogDisplayTime OBJECT-TYPE
    SYNTAX          DisplayString (SIZE(19))
    ACCESS          read-only
    STATUS          mandatory
    DESCRIPTION     
            "This is the time at which this session log was created, 
             and is in 'YYYY:MM:DD HH:MM:SS' format. same as
             rsiSessionLogTime"
    ::= { rsiSessionLogEntry 4 }

rsiSessionLogApiName OBJECT-TYPE
    SYNTAX          DisplayString
    ACCESS          read-only
    STATUS          mandatory
    DESCRIPTION     
            "This is the name of the API that was invoked for this
             session log."
    ::= { rsiSessionLogEntry 5 }

rsiSessionLogStatus OBJECT-TYPE
    SYNTAX          DisplayString
    ACCESS          read-only
    STATUS          mandatory
    DESCRIPTION     
            "This is the status of this session log. It can have
             values like: AUTHORIZED, NOT AUTHORIZED, 
             OPERATION SUCCEEDED, OPERATION FAILED, AUTHENTICATED, 
             NOT AUTHENTICATED "
    ::= { rsiSessionLogEntry 6 }

rsiAuditLogTable OBJECT-TYPE
    SYNTAX          SEQUENCE OF RsiAuditLogEntry
    ACCESS          not-accessible
    STATUS          mandatory
    DESCRIPTION     
            "This table contains the information about all the
             sessions that existed or are existing in the system. "
    ::= { rsiCommonMib 19 }

rsiAuditLogEntry OBJECT-TYPE
    SYNTAX          RsiAuditLogEntry
    ACCESS          not-accessible
    STATUS          mandatory
    DESCRIPTION     
            "Description of an audit log."
    INDEX           { rsiSessionLogId }
    ::= { rsiAuditLogTable 1 }

RsiAuditLogEntry ::=
    SEQUENCE {
        rsiAuditChangeInfo              DisplayString
    }

rsiAuditChangeInfo OBJECT-TYPE
    SYNTAX          DisplayString
    ACCESS          read-only
    STATUS          mandatory
    DESCRIPTION     
            "This is the description of the change done by the user."
    ::= { rsiAuditLogEntry 1 }

rsiCLLICodeTable OBJECT-TYPE
    SYNTAX          SEQUENCE OF RsiCLLICodeEntry
    ACCESS          not-accessible
    STATUS          mandatory
    DESCRIPTION     
            "This table contains the information about all the
             CLLI Codes existing in the system. "
    ::= { rsiCommonMib 20 }

rsiCLLICodeEntry OBJECT-TYPE
    SYNTAX          RsiCLLICodeEntry
    ACCESS          not-accessible
    STATUS          mandatory
    DESCRIPTION     
            "Description of a CLLI Code."
    INDEX           { rsiCompId }
    ::= { rsiCLLICodeTable 1 }

RsiCLLICodeEntry ::=
    SEQUENCE {
        rsiCLLICodeHostName             DisplayString,
        rsiCLLICode                     DisplayString
    }

rsiCLLICodeHostName OBJECT-TYPE
    SYNTAX          DisplayString
    ACCESS          read-only
    STATUS          mandatory
    DESCRIPTION     
            "This is the host name of the machine to which the CLLI
             Code has been assigned."
    ::= { rsiCLLICodeEntry 1 }

rsiCLLICode OBJECT-TYPE
    SYNTAX          DisplayString
    ACCESS          read-only
    STATUS          mandatory
    DESCRIPTION     
            "This is the CLLI Code that has been assigned to this 
             host."
    ::= { rsiCLLICodeEntry 2 }

rsiAutoAckAlgoExecInterval OBJECT-TYPE
    SYNTAX          INTEGER
    ACCESS          read-write
    STATUS          mandatory
    DESCRIPTION     
            "The interval after which the algo for auto-acking 
             alarms is executed at regular time.
             Note the unit of this time interval is seconds."
    ::= { rsiCommonMib 31 }

rsiSevEscalationAlgoExecInterval OBJECT-TYPE
    SYNTAX          INTEGER
    ACCESS          read-write
    STATUS          mandatory
    DESCRIPTION     
            "The interval after which the algo for alarm severity 
             escalation is executed at regular time.
             Note the unit of this time interval is seconds."
    ::= { rsiCommonMib 32 }

rsiInactiveUserLogOffTimeInterval OBJECT-TYPE
    SYNTAX          INTEGER
    ACCESS          read-write
    STATUS          mandatory
    DESCRIPTION     
            "The interval for which if a user remains inactive, he/she
             will be logged off.
             Note the unit of this time interval is seconds."
    ::= { rsiCommonMib 33 }

rsiPerformanceCollectionInterval OBJECT-TYPE
    SYNTAX          INTEGER
    ACCESS          read-write
    STATUS          mandatory
    DESCRIPTION     
            "The interval after which the performance statistics of
             components will be fetched and put in as performance
             history data. 
             Note the unit of this time interval is seconds."
    ::= { rsiCommonMib 34 }

rsiCLEICode OBJECT-TYPE
    SYNTAX          DisplayString
    ACCESS          read-only
    STATUS          mandatory
    DESCRIPTION     
            "COMMON LANGUAGE Equipment Identification Code."
    ::= { rsiCommonMib 35 }

rsiAlarmGroupTable OBJECT-TYPE
    SYNTAX          SEQUENCE OF RsiAlarmGroupEntry
    ACCESS          not-accessible
    STATUS          mandatory
    DESCRIPTION     
            "This table stores the information about the defined Alarm Groups."
    ::= { rsiCommonMib 36 }

rsiAlarmGroupEntry OBJECT-TYPE
    SYNTAX          RsiAlarmGroupEntry
    ACCESS          not-accessible
    STATUS          mandatory
    DESCRIPTION     
            "Description of a AlarmGroup"
    INDEX           { rsiAlarmGroupId }
    ::= { rsiAlarmGroupTable 1 }

RsiAlarmGroupEntry ::=
    SEQUENCE {
        rsiAlarmGroupId                 INTEGER,
        rsiAlarmGroupName               DisplayString,
        rsiAlarmGroupRowStatus          RowStatus
    }

rsiAlarmGroupId OBJECT-TYPE
    SYNTAX          INTEGER
    ACCESS          not-accessible
    STATUS          mandatory
    DESCRIPTION     
            "This is the unique id associated with this Alarm Group."
    ::= { rsiAlarmGroupEntry 1 }

rsiAlarmGroupName OBJECT-TYPE
    SYNTAX          DisplayString
    ACCESS          read-write
    STATUS          mandatory
    DESCRIPTION     
            "Name assigned to the Alarm Group"
    ::= { rsiAlarmGroupEntry 2 }

rsiAlarmGroupRowStatus OBJECT-TYPE
    SYNTAX          RowStatus
    ACCESS          read-write
    STATUS          mandatory
    DESCRIPTION     
            "This is for dynamic addition/deletion of Alarm Group(s). For creating a new Alarm Group entry, only 'createAndGo' is supported. For deleting an existing row, 'delete' is supported"
    ::= { rsiAlarmGroupEntry 3 }

rsiAlarmGroupErrorMapTable OBJECT-TYPE
    SYNTAX          SEQUENCE OF RsiAlarmGroupErrorMapEntry
    ACCESS          not-accessible
    STATUS          mandatory
    DESCRIPTION     
            "This table stores the information of the mapping between the Alarm Group and the Error Codes, where Alarm Group is from rsiAlarmGroupTable and the ErrorCode is from rsiAlarmTable."
    ::= { rsiCommonMib 37 }

rsiAlarmGroupErrorMapEntry OBJECT-TYPE
    SYNTAX          RsiAlarmGroupErrorMapEntry
    ACCESS          not-accessible
    STATUS          mandatory
    DESCRIPTION     
            "Description of the mapping between the Alarm Group and the Error Code, where Alarm Group is from rsiAlarmGroupTable and the ErrorCode is from rsiAlarmTable. "
    INDEX           { rsiAlarmGroupId, rsiAlarmErrorCode }
    ::= { rsiAlarmGroupErrorMapTable 1 }

RsiAlarmGroupErrorMapEntry ::=
    SEQUENCE {
        rsiAlarmGroupErrorMapRowStatus  RowStatus
    }

rsiAlarmGroupErrorMapRowStatus OBJECT-TYPE
    SYNTAX          RowStatus
    ACCESS          read-write
    STATUS          mandatory
    DESCRIPTION     
            "This is for dynamic addition/deletion of Alarm Group Error Map. For creating a new Alarm Group Error Map entry, only 'createAndGo' is supported. For deleting an existing row, 'delete' is supported"
    ::= { rsiAlarmGroupErrorMapEntry 1 }

rsiAlarmDestTable OBJECT-TYPE
    SYNTAX          SEQUENCE OF RsiAlarmDestEntry
    ACCESS          not-accessible
    STATUS          mandatory
    DESCRIPTION     
            "This table contains the alarm  destination information."
    ::= { rsiCommonMib 38 }

rsiAlarmDestEntry OBJECT-TYPE
    SYNTAX          RsiAlarmDestEntry
    ACCESS          not-accessible
    STATUS          mandatory
    DESCRIPTION     
            "Description of a Alarm Destination"
    INDEX           { rsiAlarmDestId }
    ::= { rsiAlarmDestTable 1 }

RsiAlarmDestEntry ::=
    SEQUENCE {
        rsiAlarmDestId                  INTEGER,
        rsiAlarmDestGroupId             INTEGER,
        rsiAlarmDestTODStart            DisplayString,
        rsiAlarmDestTODEnd              DisplayString,
        rsiAlarmDestDOFWeek             DisplayString,
        rsiAlarmDestEntryType           INTEGER,
        rsiAlarmDestType                INTEGER,
        rsiAlarmDest                    DisplayString,
        rsiAlarmDestRowStatus           RowStatus
    }

rsiAlarmDestId OBJECT-TYPE
    SYNTAX          INTEGER
    ACCESS          not-accessible
    STATUS          mandatory
    DESCRIPTION     
            "This is autogenerated Identifier for the Alarm Destination."
    ::= { rsiAlarmDestEntry 1 }

rsiAlarmDestGroupId OBJECT-TYPE
    SYNTAX          INTEGER
    ACCESS          read-write
    STATUS          mandatory
    DESCRIPTION     
            "This is Alarm Group Id."
    ::= { rsiAlarmDestEntry 2 }

rsiAlarmDestTODStart OBJECT-TYPE
    SYNTAX          DisplayString (SIZE(19))
    ACCESS          read-write
    STATUS          mandatory
    DESCRIPTION     
            "Start time: For exactRule Format is YYYY:MM:DD HH:MM:SS. For dowRule and alldays Format is XXXX:XX:XX HH:MM:SS"
    ::= { rsiAlarmDestEntry 3 }

rsiAlarmDestTODEnd OBJECT-TYPE
    SYNTAX          DisplayString (SIZE(19))
    ACCESS          read-write
    STATUS          mandatory
    DESCRIPTION     
            "End time: For exactRule Format is YYYY:MM:DD HH:MM:SS. For dowRule and alldays Format is XXXX:XX:XX HH:MM:SS"
    ::= { rsiAlarmDestEntry 4 }

rsiAlarmDestDOFWeek OBJECT-TYPE
    SYNTAX          DisplayString
    ACCESS          read-write
    STATUS          mandatory
    DESCRIPTION     
            "This is a hexadecimal bit mask field depending on the day of the week. The bit mask is as per the rule ALL 0x0, MON 0x0001, TUE 0x0002, WED 0x0004, THU 0x0008, FRI 0x0010, SAT 0x0020, SUN 0x0040"
    ::= { rsiAlarmDestEntry 5 }

rsiAlarmDestEntryType OBJECT-TYPE
    SYNTAX          INTEGER { exactRule(0), dowRule(1), alldays(2) }
    ACCESS          read-write
    STATUS          mandatory
    DESCRIPTION     
            "This is entry type of the rule.exactRule is on the basis of exact timing,dowRule is on the basis of day of week and time of the day and alldays is on the basis of time of the day for all days."
    ::= { rsiAlarmDestEntry 6 }

rsiAlarmDestType OBJECT-TYPE
    SYNTAX          INTEGER { snmpTrap(0), smtpMail(1) }
    ACCESS          read-write
    STATUS          mandatory
    DESCRIPTION     
            "This is Destination Type for the alarm."
    ::= { rsiAlarmDestEntry 7 }

rsiAlarmDest OBJECT-TYPE
    SYNTAX          DisplayString
    ACCESS          read-write
    STATUS          mandatory
    DESCRIPTION     
            "This is the alarm destination.For SNMP Trap it will be a IP Address and for SMTP Mail it will be a Mail Id."
    ::= { rsiAlarmDestEntry 8 }

rsiAlarmDestRowStatus OBJECT-TYPE
    SYNTAX          RowStatus
    ACCESS          read-write
    STATUS          mandatory
    DESCRIPTION     
            "."
    ::= { rsiAlarmDestEntry 10 }

rsiInventoryProductRepositoryTable OBJECT-TYPE
    SYNTAX          SEQUENCE OF RsiInventoryProductRepositoryEntry
    ACCESS          not-accessible
    STATUS          mandatory
    DESCRIPTION     
            "This table contains the information of the products which are there in the repository."
    ::= { rsiCommonMib 39 }

rsiInventoryProductRepositoryEntry OBJECT-TYPE
    SYNTAX          RsiInventoryProductRepositoryEntry
    ACCESS          not-accessible
    STATUS          mandatory
    DESCRIPTION     
            "Description of a product entry in the repository"
    INDEX           { rsiProductId, rsiProductVersion, rsiSystemType }
    ::= { rsiInventoryProductRepositoryTable 1 }

RsiInventoryProductRepositoryEntry ::=
    SEQUENCE {
        rsiProductId                    DisplayString,
        rsiProductVersion               DisplayString,
        rsiSystemType                   INTEGER,
        rsiProductName                  DisplayString,
        rsiProductCLEICode              DisplayString,
        rsiProductAcceptanceDate        DisplayString,
        rsiProductWarrantyPeriod        INTEGER,
        rsiProductExpiryDate            DisplayString,
        rsiProductLicenseKey            DisplayString,
        rsiProductVendor                DisplayString,
        rsiProductState                 INTEGER,
        rsiProductDescription           DisplayString,
        rsiProductBinaryPath            DisplayString,
        rsiProductBinaryType            INTEGER,
        rsiInventoryProductRepositoryRowStatus      RowStatus
    }

rsiProductId OBJECT-TYPE
    SYNTAX          DisplayString
    ACCESS          read-write
    STATUS          mandatory
    DESCRIPTION     
            "The Product identifier."
    ::= { rsiInventoryProductRepositoryEntry 1 }

rsiProductVersion OBJECT-TYPE
    SYNTAX          DisplayString
    ACCESS          read-write
    STATUS          mandatory
    DESCRIPTION     
            "The Product Version."
    ::= { rsiInventoryProductRepositoryEntry 2 }

rsiSystemType OBJECT-TYPE
    SYNTAX          INTEGER
    ACCESS          read-write
    STATUS          mandatory
    DESCRIPTION     
            "Type of the System."
    ::= { rsiInventoryProductRepositoryEntry 3 }

rsiProductName OBJECT-TYPE
    SYNTAX          DisplayString
    ACCESS          read-write
    STATUS          mandatory
    DESCRIPTION     
            "Name of the Product."
    ::= { rsiInventoryProductRepositoryEntry 4 }

rsiProductCLEICode OBJECT-TYPE
    SYNTAX          DisplayString
    ACCESS          read-write
    STATUS          mandatory
    DESCRIPTION     
            "CLEI code for the Product."
    ::= { rsiInventoryProductRepositoryEntry 5 }

rsiProductAcceptanceDate OBJECT-TYPE
    SYNTAX          DisplayString (SIZE(19))
    ACCESS          read-write
    STATUS          mandatory
    DESCRIPTION     
            "Acceptance date by the user. Format YYYY:MM:DD HH:MM:SS"
    ::= { rsiInventoryProductRepositoryEntry 6 }

rsiProductWarrantyPeriod OBJECT-TYPE
    SYNTAX          INTEGER
    ACCESS          read-write
    STATUS          mandatory
    DESCRIPTION     
            "Warranty Period Given to the User."
    ::= { rsiInventoryProductRepositoryEntry 7 }

rsiProductExpiryDate OBJECT-TYPE
    SYNTAX          DisplayString (SIZE(19))
    ACCESS          read-write
    STATUS          mandatory
    DESCRIPTION     
            "Expiry date of the Product. Format YYYY:MM:DD HH:MM:SS"
    ::= { rsiInventoryProductRepositoryEntry 8 }

rsiProductLicenseKey OBJECT-TYPE
    SYNTAX          DisplayString
    ACCESS          read-write
    STATUS          mandatory
    DESCRIPTION     
            "License key for the Product. This is now depricated and any request to fetch it will return NONE and any request to set it will fail."
    ::= { rsiInventoryProductRepositoryEntry 9 }

rsiProductVendor OBJECT-TYPE
    SYNTAX          DisplayString
    ACCESS          read-write
    STATUS          mandatory
    DESCRIPTION     
            "Name of the Product vendor."
    ::= { rsiInventoryProductRepositoryEntry 10 }

rsiProductState OBJECT-TYPE
    SYNTAX          INTEGER
    ACCESS          read-write
    STATUS          mandatory
    DESCRIPTION     
            "State of the Product."
    ::= { rsiInventoryProductRepositoryEntry 11 }

rsiProductDescription OBJECT-TYPE
    SYNTAX          DisplayString
    ACCESS          read-write
    STATUS          mandatory
    DESCRIPTION     
            "Description of the Product."
    ::= { rsiInventoryProductRepositoryEntry 12 }

rsiProductBinaryPath OBJECT-TYPE
    SYNTAX          DisplayString
    ACCESS          read-write
    STATUS          mandatory
    DESCRIPTION     
            "Path where the Product binary is kept."
    ::= { rsiInventoryProductRepositoryEntry 13 }

rsiProductBinaryType OBJECT-TYPE
    SYNTAX          INTEGER
    ACCESS          read-write
    STATUS          mandatory
    DESCRIPTION     
            "Type of binary."
    ::= { rsiInventoryProductRepositoryEntry 14 }

rsiInventoryProductRepositoryRowStatus OBJECT-TYPE
    SYNTAX          RowStatus
    ACCESS          read-write
    STATUS          mandatory
    DESCRIPTION     
            "This is for dynamic addition/deletion of Products in the inventory. For creating a new Products entry in the inventory, only 'createAndGo' is supported. For deleting an existing row, 'delete' is supported."
    ::= { rsiInventoryProductRepositoryEntry 15 }

rsiInventoryInstalledProductTable OBJECT-TYPE
    SYNTAX          SEQUENCE OF RsiInventoryInstalledProductEntry
    ACCESS          not-accessible
    STATUS          mandatory
    DESCRIPTION     
            "This table contains the information of the products which are installed somewhere in the domain, the rsiProductId, rsiProductVersion, rsiSystemType are taken from the rsiInventoryProductRepositoryTable."
    ::= { rsiCommonMib 40 }

rsiInventoryInstalledProductEntry OBJECT-TYPE
    SYNTAX          RsiInventoryInstalledProductEntry
    ACCESS          not-accessible
    STATUS          mandatory
    DESCRIPTION     
            "Description of a product entry installed in the domain"
    INDEX           { rsiProductId, rsiProductVersion, rsiSystemType, 
                      rsiClusterId }
    ::= { rsiInventoryInstalledProductTable 1 }

RsiInventoryInstalledProductEntry ::=
    SEQUENCE {
        rsiClusterId                    INTEGER,
        rsiInsSystemId                  INTEGER,
        rsiInstallTime                  DisplayString,
        rsiInstallRoot                  DisplayString
    }

rsiClusterId OBJECT-TYPE
    SYNTAX          INTEGER
    ACCESS          read-only
    STATUS          mandatory
    DESCRIPTION     
            "Cluster in which the product is installed."
    ::= { rsiInventoryInstalledProductEntry 1 }

rsiInsSystemId OBJECT-TYPE
    SYNTAX          INTEGER
    ACCESS          read-only
    STATUS          mandatory
    DESCRIPTION     
            "System ID in which the product is installed."
    ::= { rsiInventoryInstalledProductEntry 2 }

rsiInstallTime OBJECT-TYPE
    SYNTAX          DisplayString (SIZE(19))
    ACCESS          read-only
    STATUS          mandatory
    DESCRIPTION     
            "Time at which the product is installed. Format is YYYY:MM:DD HH:MM:SS"
    ::= { rsiInventoryInstalledProductEntry 3 }

rsiInstallRoot OBJECT-TYPE
    SYNTAX          DisplayString
    ACCESS          read-only
    STATUS          mandatory
    DESCRIPTION     
            "Location where the product is installed"
    ::= { rsiInventoryInstalledProductEntry 4 }

rsiInventoryHostDetailTable OBJECT-TYPE
    SYNTAX          SEQUENCE OF RsiInventoryHostDetailEntry
    ACCESS          not-accessible
    STATUS          mandatory
    DESCRIPTION     
            "This table contains the information of the hosts present in the domain."
    ::= { rsiCommonMib 41 }

rsiInventoryHostDetailEntry OBJECT-TYPE
    SYNTAX          RsiInventoryHostDetailEntry
    ACCESS          not-accessible
    STATUS          mandatory
    DESCRIPTION     
            "Description of the hosts installed in the domain"
    INDEX           { rsiHostId, rsiHostAttribName }
    ::= { rsiInventoryHostDetailTable 1 }

RsiInventoryHostDetailEntry ::=
    SEQUENCE {
        rsiHostId                       INTEGER,
        rsiHostAttribName               DisplayString,
        rsiHostAttribValue              DisplayString
    }

rsiHostId OBJECT-TYPE
    SYNTAX          INTEGER
    ACCESS          read-only
    STATUS          mandatory
    DESCRIPTION     
            "Identifier of the host installed in the domain."
    ::= { rsiInventoryHostDetailEntry 1 }

rsiHostAttribName OBJECT-TYPE
    SYNTAX          DisplayString
    ACCESS          read-only
    STATUS          mandatory
    DESCRIPTION     
            "Name of the Attribute."
    ::= { rsiInventoryHostDetailEntry 2 }

rsiHostAttribValue OBJECT-TYPE
    SYNTAX          DisplayString
    ACCESS          read-write
    STATUS          mandatory
    DESCRIPTION     
            "Value of the Attribute.Value for 'state' attribute can be 0-3 only.
             0 is for 'In Service',1 for 'Out Of Service',2 for 'Manually Out Of Service'
             and 3 for 'Unit Under Test'."
    ::= { rsiInventoryHostDetailEntry 3 }

rsiInventoryInstalledModulesTable OBJECT-TYPE
    SYNTAX          SEQUENCE OF RsiInventoryInstalledModulesEntry
    ACCESS          not-accessible
    STATUS          mandatory
    DESCRIPTION     
            "This table contains the information of the installed modules. The rsiProductId, rsiProductVersion, rsiSystemType are taken from the rsiInventoryProductRepositoryTable, rsiSystemId from rsiSystemTable and rsiSubsystemId from rsiSubsystemTable."
    ::= { rsiCommonMib 42 }

rsiInventoryInstalledModulesEntry OBJECT-TYPE
    SYNTAX          RsiInventoryInstalledModulesEntry
    ACCESS          not-accessible
    STATUS          mandatory
    DESCRIPTION     
            "Description of an installed module."
    INDEX           { rsiProductId, rsiProductVersion, rsiSystemType, 
                      rsiClusterId, rsiSystemId, rsiSubsystemId }
    ::= { rsiInventoryInstalledModulesTable 1 }

RsiInventoryInstalledModulesEntry ::=
    SEQUENCE {
        rsiInvModuleName                DisplayString,
        rsiInvModuleHostId              INTEGER,
        rsiInvModuleStatus              INTEGER,
        rsiInvModuleVersion             DisplayString,
        rsiInvModuleThirdPartyFlag      INTEGER
    }

rsiInvModuleName OBJECT-TYPE
    SYNTAX          DisplayString
    ACCESS          read-only
    STATUS          mandatory
    DESCRIPTION     
            "The Name of the Module."
    ::= { rsiInventoryInstalledModulesEntry 1 }

rsiInvModuleHostId OBJECT-TYPE
    SYNTAX          INTEGER
    ACCESS          read-only
    STATUS          mandatory
    DESCRIPTION     
            "The identifier of the host on which the Module is installed."
    ::= { rsiInventoryInstalledModulesEntry 2 }

rsiInvModuleStatus OBJECT-TYPE
    SYNTAX          INTEGER
    ACCESS          read-only
    STATUS          mandatory
    DESCRIPTION     
            "The Status of the Module."
    ::= { rsiInventoryInstalledModulesEntry 3 }

rsiInvModuleVersion OBJECT-TYPE
    SYNTAX          DisplayString
    ACCESS          read-only
    STATUS          mandatory
    DESCRIPTION     
            "Version of the Module."
    ::= { rsiInventoryInstalledModulesEntry 4 }

rsiInvModuleThirdPartyFlag OBJECT-TYPE
    SYNTAX          INTEGER
    ACCESS          read-only
    STATUS          mandatory
    DESCRIPTION     
            "If it is a Third Party Module."
    ::= { rsiInventoryInstalledModulesEntry 5 }

rsiInventoryInstalledServicesTable OBJECT-TYPE
    SYNTAX          SEQUENCE OF RsiInventoryInstalledServicesEntry
    ACCESS          not-accessible
    STATUS          mandatory
    DESCRIPTION     
            "This table contains the information of the installed services. The rsiProductId, rsiProductVersion, rsiSystemType are taken from the rsiInventoryProductRepositoryTable, rsiSystemId from rsiSystemTable and rsiSubsystemId from rsiSubsystemTable."
    ::= { rsiCommonMib 43 }

rsiInventoryInstalledServicesEntry OBJECT-TYPE
    SYNTAX          RsiInventoryInstalledServicesEntry
    ACCESS          not-accessible
    STATUS          mandatory
    DESCRIPTION     
            "Description of an installed service."
    INDEX           { rsiProductId, rsiProductVersion, rsiSystemType, 
                      rsiClusterId, rsiSystemId, rsiSubsystemId, 
                      rsiSubcomponentId }
    ::= { rsiInventoryInstalledServicesTable 1 }

RsiInventoryInstalledServicesEntry ::=
    SEQUENCE {
        rsiSubcomponentId               INTEGER,
        rsiInvServiceName               DisplayString,
        rsiInvServiceHostId             INTEGER,
        rsiInvServiceAdminStatus        INTEGER,
        rsiInvServiceOperStatus         INTEGER,
        rsiInvServiceVersion            DisplayString,
        rsiInvServiceThirdPartyFlag     INTEGER
    }

rsiSubcomponentId OBJECT-TYPE
    SYNTAX          INTEGER
    ACCESS          read-only
    STATUS          mandatory
    DESCRIPTION     
            "Identifier of the subcomponent to which the service belongs."
    ::= { rsiInventoryInstalledServicesEntry 1 }

rsiInvServiceName OBJECT-TYPE
    SYNTAX          DisplayString
    ACCESS          read-only
    STATUS          mandatory
    DESCRIPTION     
            "Name of the Service."
    ::= { rsiInventoryInstalledServicesEntry 2 }

rsiInvServiceHostId OBJECT-TYPE
    SYNTAX          INTEGER
    ACCESS          read-only
    STATUS          mandatory
    DESCRIPTION     
            "Identifier of the subcomponent to which the service belongs."
    ::= { rsiInventoryInstalledServicesEntry 3 }

rsiInvServiceAdminStatus OBJECT-TYPE
    SYNTAX          INTEGER { installed(0), ready(1), active(2) }
    ACCESS          read-write
    STATUS          mandatory
    DESCRIPTION     
            "Admin Status of the Service. transition from installed to ready is equivalent to startService; transition from Active to ready is equivalent to deactivateService; Direct transition from  installed to active not allowed abd vice-versa, transition from ready to active is equivalent to activateService; transition from ready to installed is equivalent to stopService"
    ::= { rsiInventoryInstalledServicesEntry 4 }

rsiInvServiceOperStatus OBJECT-TYPE
    SYNTAX          INTEGER { installed(0), ready(1), active(2) }
    ACCESS          read-only
    STATUS          mandatory
    DESCRIPTION     
            "Oper Status of the Service."
    ::= { rsiInventoryInstalledServicesEntry 5 }

rsiInvServiceVersion OBJECT-TYPE
    SYNTAX          DisplayString
    ACCESS          read-only
    STATUS          mandatory
    DESCRIPTION     
            "Version of the Service."
    ::= { rsiInventoryInstalledServicesEntry 6 }

rsiInvServiceThirdPartyFlag OBJECT-TYPE
    SYNTAX          INTEGER
    ACCESS          read-only
    STATUS          mandatory
    DESCRIPTION     
            "If the service is a third party service."
    ::= { rsiInventoryInstalledServicesEntry 7 }

rsiInventoryCardDetailTable OBJECT-TYPE
    SYNTAX          SEQUENCE OF RsiInventoryCardDetailEntry
    ACCESS          not-accessible
    STATUS          mandatory
    DESCRIPTION     
            "This table contains the information of the cards present in the domain. rsiCardHostId is from table rsiInventoryHostDetailTable"
    ::= { rsiCommonMib 44 }

rsiInventoryCardDetailEntry OBJECT-TYPE
    SYNTAX          RsiInventoryCardDetailEntry
    ACCESS          not-accessible
    STATUS          mandatory
    DESCRIPTION     
            "Description of the cards installed in the domain"
    INDEX           { rsiCardId, rsiCardAttribName }
    ::= { rsiInventoryCardDetailTable 1 }

RsiInventoryCardDetailEntry ::=
    SEQUENCE {
        rsiCardHostId                   INTEGER,
        rsiCardId                       INTEGER,
        rsiCardAttribName               DisplayString,
        rsiCardAttribValue              DisplayString
    }

rsiCardHostId OBJECT-TYPE
    SYNTAX          INTEGER
    ACCESS          read-write
    STATUS          mandatory
    DESCRIPTION     
            "Identifier of the host on which the card is installed."
    ::= { rsiInventoryCardDetailEntry 1 }

rsiCardId OBJECT-TYPE
    SYNTAX          INTEGER
    ACCESS          read-only
    STATUS          mandatory
    DESCRIPTION     
            "Identifier of the card installed in the domain."
    ::= { rsiInventoryCardDetailEntry 2 }

rsiCardAttribName OBJECT-TYPE
    SYNTAX          DisplayString
    ACCESS          read-only
    STATUS          mandatory
    DESCRIPTION     
            "Name of the Attribute."
    ::= { rsiInventoryCardDetailEntry 3 }

rsiCardAttribValue OBJECT-TYPE
    SYNTAX          DisplayString
    ACCESS          read-write
    STATUS          mandatory
    DESCRIPTION     
            "Value of the Attribute.Value for 'state' attribute can be 0-3 only.
             0 is for 'In Service',1 for 'Out Of Service',2 for 'Manually Out Of Service'
             and 3 for 'Unit Under Test'."
    ::= { rsiInventoryCardDetailEntry 4 }

rsiInventoryHwHistoryTable OBJECT-TYPE
    SYNTAX          SEQUENCE OF RsiInventoryHwHistoryEntry
    ACCESS          not-accessible
    STATUS          mandatory
    DESCRIPTION     
            "This table contains the history of all the hardware, whether it be a card or a host"
    ::= { rsiCommonMib 45 }

rsiInventoryHwHistoryEntry OBJECT-TYPE
    SYNTAX          RsiInventoryHwHistoryEntry
    ACCESS          not-accessible
    STATUS          mandatory
    DESCRIPTION     
            "Description of the HOST/CARD modification in the Domain"
    INDEX           { rsiHostCardFlag, rsiHwId, rsiHwModificationTime, 
                      rsiHwSeqNum }
    ::= { rsiInventoryHwHistoryTable 1 }

RsiInventoryHwHistoryEntry ::=
    SEQUENCE {
        rsiHostCardFlag                 INTEGER,
        rsiHwId                         INTEGER,
        rsiHwSeqNum                     INTEGER,
        rsiHwState                      INTEGER,
        rsiHwModificationTime           DisplayString,
        rsiHwHistLog                    DisplayString
    }

rsiHostCardFlag OBJECT-TYPE
    SYNTAX          INTEGER { card(1), host(2) }
    ACCESS          read-only
    STATUS          mandatory
    DESCRIPTION     
            "Shows if the entry represents a CARD or a HOST."
    ::= { rsiInventoryHwHistoryEntry 1 }

rsiHwId OBJECT-TYPE
    SYNTAX          INTEGER
    ACCESS          read-only
    STATUS          mandatory
    DESCRIPTION     
            "Identifier of the CARD or the HOST depending on rsiHostCardFlag."
    ::= { rsiInventoryHwHistoryEntry 2 }

rsiHwSeqNum OBJECT-TYPE
    SYNTAX          INTEGER
    ACCESS          read-only
    STATUS          mandatory
    DESCRIPTION     
            "Sequence number to differentiate entries made at the same time."
    ::= { rsiInventoryHwHistoryEntry 3 }

rsiHwState OBJECT-TYPE
    SYNTAX          INTEGER { inService(0), outOfService(1), 
                        manuallyOutOfService(2), unitUnderTest(3) }
    ACCESS          read-only
    STATUS          mandatory
    DESCRIPTION     
            "State of the hardware unit."
    ::= { rsiInventoryHwHistoryEntry 4 }

rsiHwModificationTime OBJECT-TYPE
    SYNTAX          DisplayString (SIZE(19))
    ACCESS          read-only
    STATUS          mandatory
    DESCRIPTION     
            "Time at which the modification is made to the hardware unit. Format is YYYY:MM:DD HH:MM:SS."
    ::= { rsiInventoryHwHistoryEntry 5 }

rsiHwHistLog OBJECT-TYPE
    SYNTAX          DisplayString
    ACCESS          read-only
    STATUS          mandatory
    DESCRIPTION     
            " Description of the change."
    ::= { rsiInventoryHwHistoryEntry 6 }

rsiInventorySwHistoryTable OBJECT-TYPE
    SYNTAX          SEQUENCE OF RsiInventorySwHistoryEntry
    ACCESS          not-accessible
    STATUS          mandatory
    DESCRIPTION     
            "This table contains the history of all the hardware, whether it be a card or a host"
    ::= { rsiCommonMib 46 }

rsiInventorySwHistoryEntry OBJECT-TYPE
    SYNTAX          RsiInventorySwHistoryEntry
    ACCESS          not-accessible
    STATUS          mandatory
    DESCRIPTION     
            "Description of the HOST/CARD modification in the Domain"
    INDEX           { rsiModuleServiceFlag, rsiProductId, 
                      rsiProductVersion, rsiSystemType, rsiClusterId, 
                      rsiSystemId, rsiSubsystemId, rsiSubcomponentId, 
                      rsiSwModificationTime, rsiSwSeqNum }
    ::= { rsiInventorySwHistoryTable 1 }

RsiInventorySwHistoryEntry ::=
    SEQUENCE {
        rsiModuleServiceFlag            INTEGER,
        rsiSwSeqNum                     INTEGER,
        rsiHistHostId                   INTEGER,
        rsiSwState                      INTEGER,
        rsiSwModificationTime           DisplayString,
        rsiSwHistLog                    DisplayString
    }

rsiModuleServiceFlag OBJECT-TYPE
    SYNTAX          INTEGER { module(3), service(4), installedProduct(5), 
                        repositoryProduct(6) }
    ACCESS          read-only
    STATUS          mandatory
    DESCRIPTION     
            "Shows if the entry represents a MODULE, SERVICE or a PRODUCT."
    ::= { rsiInventorySwHistoryEntry 1 }

rsiSwSeqNum OBJECT-TYPE
    SYNTAX          INTEGER
    ACCESS          read-only
    STATUS          mandatory
    DESCRIPTION     
            "Sequence number to differentiate entries made at the same time."
    ::= { rsiInventorySwHistoryEntry 2 }

rsiHistHostId OBJECT-TYPE
    SYNTAX          INTEGER
    ACCESS          read-only
    STATUS          mandatory
    DESCRIPTION     
            "Identifier of the HOST over which the MODULE, SERVICE or the PRODUCT is installed."
    ::= { rsiInventorySwHistoryEntry 3 }

rsiSwState OBJECT-TYPE
    SYNTAX          INTEGER
    ACCESS          read-only
    STATUS          mandatory
    DESCRIPTION     
            "State of the Software unit."
    ::= { rsiInventorySwHistoryEntry 4 }

rsiSwModificationTime OBJECT-TYPE
    SYNTAX          DisplayString (SIZE(19))
    ACCESS          read-only
    STATUS          mandatory
    DESCRIPTION     
            "Time at which the modification is made to the Software unit. Format is YYYY:MM:DD HH:MM:SS."
    ::= { rsiInventorySwHistoryEntry 5 }

rsiSwHistLog OBJECT-TYPE
    SYNTAX          DisplayString
    ACCESS          read-only
    STATUS          mandatory
    DESCRIPTION     
            " Description of the change."
    ::= { rsiInventorySwHistoryEntry 6 }

rsiTODRuleTable OBJECT-TYPE
    SYNTAX          SEQUENCE OF RsiTODRuleEntry
    ACCESS          not-accessible
    STATUS          mandatory
    DESCRIPTION     
            "This table contains the rules for system access depending upon the time of the day"
    ::= { rsiCommonMib 47 }

rsiTODRuleEntry OBJECT-TYPE
    SYNTAX          RsiTODRuleEntry
    ACCESS          not-accessible
    STATUS          mandatory
    DESCRIPTION     
            "Description of the rules for system access depending upon the time of the day"
    INDEX           { rsiRuleName }
    ::= { rsiTODRuleTable 1 }

RsiTODRuleEntry ::=
    SEQUENCE {
        rsiRuleName                     DisplayString,
        rsiRuleId                       INTEGER,
        rsiRuleType                     INTEGER,
        rsiStartTime                    DisplayString,
        rsiEndTime                      DisplayString,
        rsiDOW                          DisplayString,
        rsiTODRuleRowStatus             RowStatus
    }

rsiRuleName OBJECT-TYPE
    SYNTAX          DisplayString
    ACCESS          read-write
    STATUS          mandatory
    DESCRIPTION     
            "Name for the Rule."
    ::= { rsiTODRuleEntry 1 }

rsiRuleId OBJECT-TYPE
    SYNTAX          INTEGER
    ACCESS          read-only
    STATUS          mandatory
    DESCRIPTION     
            "Autogenerated Identifier for the Rule."
    ::= { rsiTODRuleEntry 2 }

rsiRuleType OBJECT-TYPE
    SYNTAX          INTEGER { exactRule(0), dowRule(1), alldays(2) }
    ACCESS          read-write
    STATUS          mandatory
    DESCRIPTION     
            "Type of the rule. exactRule is on the basis of exact timing and the dowRule is on the basis of day of week and depend on the time of the day. And alldays depend on the time of the day only."
    ::= { rsiTODRuleEntry 3 }

rsiStartTime OBJECT-TYPE
    SYNTAX          DisplayString (SIZE(19))
    ACCESS          read-write
    STATUS          mandatory
    DESCRIPTION     
            "Start time: For exactRule Format is YYYY:MM:DD HH:MM:SS. For dowRule and alldays Format is XXXX:XX:XX HH:MM:SS"
    ::= { rsiTODRuleEntry 4 }

rsiEndTime OBJECT-TYPE
    SYNTAX          DisplayString (SIZE(19))
    ACCESS          read-write
    STATUS          mandatory
    DESCRIPTION     
            "End time: For exactRule Format is YYYY:MM:DD HH:MM:SS. For dowRule and alldays Format is XXXX:XX:XX HH:MM:SS"
    ::= { rsiTODRuleEntry 5 }

rsiDOW OBJECT-TYPE
    SYNTAX          DisplayString
    ACCESS          read-write
    STATUS          mandatory
    DESCRIPTION     
            " This is a hexadecimal bit mask field depending on the day of the week. The bit mask is as per the rule ALL 0x0, MON 0x0001, TUE 0x0002, WED 0x0004, THU 0x0008, FRI 0x0010, SAT 0x0020, SUN 0x0040"
    ::= { rsiTODRuleEntry 6 }

rsiTODRuleRowStatus OBJECT-TYPE
    SYNTAX          RowStatus
    ACCESS          read-write
    STATUS          mandatory
    DESCRIPTION     
            "This is for dynamic addition/deletion of TOD Rules.
             For creating a new TOD Rules, only 'createAndGo' is
             supported. For deleting an existing row, 'delete'
             is supported"
    ::= { rsiTODRuleEntry 7 }

rsiUserRoleTODRuleTable OBJECT-TYPE
    SYNTAX          SEQUENCE OF RsiUserRoleTODRuleEntry
    ACCESS          not-accessible
    STATUS          mandatory
    DESCRIPTION     
            "This table contains the mapping of the User, his role and the rules for system access depending upon the time of the day. rsiUserId id from the table rsiUserTable rsiRoleId is from the table rsiRoleId and rsiRuleId is from the table rsiTODRuleTable"
    ::= { rsiCommonMib 48 }

rsiUserRoleTODRuleEntry OBJECT-TYPE
    SYNTAX          RsiUserRoleTODRuleEntry
    ACCESS          not-accessible
    STATUS          mandatory
    DESCRIPTION     
            "Description of the mapping of the User, his role and the rules for system access depending upon the time of the day"
    INDEX           { rsiUserId, rsiRoleId, rsiRuleId }
    ::= { rsiUserRoleTODRuleTable 1 }

RsiUserRoleTODRuleEntry ::=
    SEQUENCE {
        rsiUserRoleTODRuleRowStatus     RowStatus
    }

rsiUserRoleTODRuleRowStatus OBJECT-TYPE
    SYNTAX          RowStatus
    ACCESS          read-write
    STATUS          mandatory
    DESCRIPTION     
            "This is for dynamic addition/deletion of the mapping of TOD Rules with the User and his role.
             For creating a new TOD Rules, only 'createAndGo' is
             supported. For deleting an existing row, 'delete'
             is supported"
    ::= { rsiUserRoleTODRuleEntry 1 }

rsiServiceStateTable OBJECT-TYPE
    SYNTAX          SEQUENCE OF RsiServiceStateEntry
    ACCESS          not-accessible
    STATUS          mandatory
    DESCRIPTION     
            "This table contains the information of different services on different subsystems."
    ::= { rsiCommonMib 51 }

rsiServiceStateEntry OBJECT-TYPE
    SYNTAX          RsiServiceStateEntry
    ACCESS          not-accessible
    STATUS          mandatory
    DESCRIPTION     
            "Description of an installed service on a particular subsystem."
    INDEX           { rsiServiceID, rsiServiceVer, rsiSystemID }
    ::= { rsiServiceStateTable 1 }

RsiServiceStateEntry ::=
    SEQUENCE {
        rsiServiceID                    DisplayString,
        rsiServiceVer                   DisplayString,
        rsiSystemID                     INTEGER,
        rsiSubsystemID                  INTEGER,
        rsiServiceAdminStatus           INTEGER,
        rsiServiceOperStatus            INTEGER,
        rsiServiceStatusOnSubsys        INTEGER
    }

rsiServiceID OBJECT-TYPE
    SYNTAX          DisplayString
    ACCESS          read-only
    STATUS          mandatory
    DESCRIPTION     
            "The Product identifier."
    ::= { rsiServiceStateEntry 1 }

rsiServiceVer OBJECT-TYPE
    SYNTAX          DisplayString
    ACCESS          read-only
    STATUS          mandatory
    DESCRIPTION     
            "The Product Version."
    ::= { rsiServiceStateEntry 2 }

rsiSystemID OBJECT-TYPE
    SYNTAX          INTEGER
    ACCESS          read-only
    STATUS          mandatory
    DESCRIPTION     
            "System on which the service is deployed."
    ::= { rsiServiceStateEntry 3 }

rsiSubsystemID OBJECT-TYPE
    SYNTAX          INTEGER
    ACCESS          read-only
    STATUS          mandatory
    DESCRIPTION     
            "Subsystem on which the status of the service is maintained."
    ::= { rsiServiceStateEntry 4 }

rsiServiceAdminStatus OBJECT-TYPE
    SYNTAX          INTEGER { installed(0), ready(1), active(2) }
    ACCESS          read-only
    STATUS          mandatory
    DESCRIPTION     
            "Admin Status of the Service."
    ::= { rsiServiceStateEntry 5 }

rsiServiceOperStatus OBJECT-TYPE
    SYNTAX          INTEGER { installed(0), ready(1), active(2) }
    ACCESS          read-only
    STATUS          mandatory
    DESCRIPTION     
            "Oper Status of the Service."
    ::= { rsiServiceStateEntry 6 }

rsiServiceStatusOnSubsys OBJECT-TYPE
    SYNTAX          INTEGER
    ACCESS          read-only
    STATUS          mandatory
    DESCRIPTION     
            "Status of the servie on that particular subsystem."
    ::= { rsiServiceStateEntry 7 }

rsiMeasurementCounterTable OBJECT-TYPE
    SYNTAX          SEQUENCE OF RsiMeasurementCounterEntry
    ACCESS          not-accessible
    STATUS          mandatory
    DESCRIPTION     
            "This table contains the information of different measurement 
             counters on different subsystems.It contains rsiSubsystemID 
             from rsiSubsystemTable."
    ::= { rsiCommonMib 52 }

rsiMeasurementCounterEntry OBJECT-TYPE
    SYNTAX          RsiMeasurementCounterEntry
    ACCESS          not-accessible
    STATUS          mandatory
    DESCRIPTION     
            "Description of a measurement counter of a particular subsystem."
    INDEX           { rsiSubsystemId, rsiMeasurementCounterID }
    ::= { rsiMeasurementCounterTable 1 }

RsiMeasurementCounterEntry ::=
    SEQUENCE {
        rsiMeasurementCounterID         DisplayString,
        rsiMeasurementCounterRefType    INTEGER,
        rsiMeasurementCounterType       INTEGER,
        rsiMeasurementCounterMeasMode   INTEGER,
        rsiMeasurementCounterScanInterval INTEGER,
        rsiMeasurementCounterOid        DisplayString,
        rsiMeasurementCounterEnable     INTEGER
    }

rsiMeasurementCounterID OBJECT-TYPE
    SYNTAX          DisplayString
    ACCESS          read-only
    STATUS          mandatory
    DESCRIPTION     
            "Measurement Counter Identifier"
    ::= { rsiMeasurementCounterEntry 1 }

rsiMeasurementCounterRefType OBJECT-TYPE
    SYNTAX          INTEGER { name(0), index(1) }
    ACCESS          read-only
    STATUS          mandatory
    DESCRIPTION     
            "Measurement Counter Reference Type.If the reference type 
             is 'name' then the platform shall enable the measurement 
             values to be referenced by measurement value names else
             by index."
    ::= { rsiMeasurementCounterEntry 2 }

rsiMeasurementCounterType OBJECT-TYPE
    SYNTAX          INTEGER { inconly(0), incdec(1) }
    ACCESS          read-only
    STATUS          mandatory
    DESCRIPTION     
            "Measurement Counter Type.'inconly' specifies that this counter 
             will increment only and 'incdec' specifies that this counter can
             increment and decrement both."
    ::= { rsiMeasurementCounterEntry 3 }

rsiMeasurementCounterMeasMode OBJECT-TYPE
    SYNTAX          INTEGER { event(0), usage(1), instantaneous(2) }
    ACCESS          read-only
    STATUS          mandatory
    DESCRIPTION     
            "This identifies the mode of a particular counter.The 
             possible values are event, usage and instantaneous."
    ::= { rsiMeasurementCounterEntry 4 }

rsiMeasurementCounterScanInterval OBJECT-TYPE
    SYNTAX          INTEGER
    ACCESS          read-only
    STATUS          mandatory
    DESCRIPTION     
            "Measurement Counter Scan Interval"
    ::= { rsiMeasurementCounterEntry 5 }

rsiMeasurementCounterOid OBJECT-TYPE
    SYNTAX          DisplayString
    ACCESS          read-only
    STATUS          mandatory
    DESCRIPTION     
            "Measurement Counter Oid"
    ::= { rsiMeasurementCounterEntry 6 }

rsiMeasurementCounterEnable OBJECT-TYPE
    SYNTAX          INTEGER { false(0), true(1) }
    ACCESS          read-only
    STATUS          mandatory
    DESCRIPTION     
            "It specifies whether a particular Measurement Counter 
             is enable or disable"
    ::= { rsiMeasurementCounterEntry 7 }

rsiMeasurementSetBaseTable OBJECT-TYPE
    SYNTAX          SEQUENCE OF RsiMeasurementSetBaseEntry
    ACCESS          not-accessible
    STATUS          mandatory
    DESCRIPTION     
            "This table contains the basic information of different measurement sets."
    ::= { rsiCommonMib 53 }

rsiMeasurementSetBaseEntry OBJECT-TYPE
    SYNTAX          RsiMeasurementSetBaseEntry
    ACCESS          not-accessible
    STATUS          mandatory
    DESCRIPTION     
            "Description of a measurement set."
    INDEX           { rsiMeasurementSetID, rsiMeasurementSetVersionId }
    ::= { rsiMeasurementSetBaseTable 1 }

RsiMeasurementSetBaseEntry ::=
    SEQUENCE {
        rsiMeasurementSetID             DisplayString,
        rsiMeasurementSetVersionId      DisplayString,
        rsiMeasurementSetAccuInterval   INTEGER,
        rsiMeasurementSetBaseRowStatus  RowStatus
    }

rsiMeasurementSetID OBJECT-TYPE
    SYNTAX          DisplayString
    ACCESS          read-write
    STATUS          mandatory
    DESCRIPTION     
            "Measurement Set Identifier"
    ::= { rsiMeasurementSetBaseEntry 1 }

rsiMeasurementSetVersionId OBJECT-TYPE
    SYNTAX          DisplayString
    ACCESS          read-only
    STATUS          mandatory
    DESCRIPTION     
            "Measurement Set Version Id.BayManager will generate unique
             version id."
    ::= { rsiMeasurementSetBaseEntry 2 }

rsiMeasurementSetAccuInterval OBJECT-TYPE
    SYNTAX          INTEGER
    ACCESS          read-write
    STATUS          mandatory
    DESCRIPTION     
            "Measurement Set Accumulation Interval"
    ::= { rsiMeasurementSetBaseEntry 3 }

rsiMeasurementSetBaseRowStatus OBJECT-TYPE
    SYNTAX          RowStatus
    ACCESS          read-write
    STATUS          mandatory
    DESCRIPTION     
            "This is for dynamic addition/deletion of Measurement
             sets.
             For creating a new row, only 'createAndGo' is 
             supported. For deleting an existing row, 'delete'
             is supported"
    ::= { rsiMeasurementSetBaseEntry 4 }

rsiMeasurementSetExtnFTPTable OBJECT-TYPE
    SYNTAX          SEQUENCE OF RsiMeasurementSetExtnFTPEntry
    ACCESS          not-accessible
    STATUS          mandatory
    DESCRIPTION     
            "This table contains the information of different FTP sites for a 
             Measurement set.It contains rsiMeasurementSetID and 
             rsiMeasurementSetVersionId from rsiMeasurementSetBaseTable"
    ::= { rsiCommonMib 54 }

rsiMeasurementSetExtnFTPEntry OBJECT-TYPE
    SYNTAX          RsiMeasurementSetExtnFTPEntry
    ACCESS          not-accessible
    STATUS          mandatory
    DESCRIPTION     
            "Description of a FTP site of a measurement set."
    INDEX           { rsiMeasurementSetID, rsiMeasurementSetVersionId, 
                      rsiMeasurementSetFTPHost, 
                      rsiMeasurementSetFTPUserId, 
                      rsiMeasurementSetFTPPasswd, 
                      rsiMeasurementSetFTPLocation }
    ::= { rsiMeasurementSetExtnFTPTable 1 }

RsiMeasurementSetExtnFTPEntry ::=
    SEQUENCE {
        rsiMeasurementSetFTPHost        DisplayString,
        rsiMeasurementSetFTPUserId      DisplayString,
        rsiMeasurementSetFTPPasswd      DisplayString,
        rsiMeasurementSetFTPLocation    DisplayString,
        rsiMeasurementSetFTPRowStatus   RowStatus
    }

rsiMeasurementSetFTPHost OBJECT-TYPE
    SYNTAX          DisplayString
    ACCESS          read-write
    STATUS          mandatory
    DESCRIPTION     
            "This is Host name of FTP site"
    ::= { rsiMeasurementSetExtnFTPEntry 1 }

rsiMeasurementSetFTPUserId OBJECT-TYPE
    SYNTAX          DisplayString
    ACCESS          read-write
    STATUS          mandatory
    DESCRIPTION     
            "This is user id for FTP site"
    ::= { rsiMeasurementSetExtnFTPEntry 2 }

rsiMeasurementSetFTPPasswd OBJECT-TYPE
    SYNTAX          DisplayString
    ACCESS          read-write
    STATUS          mandatory
    DESCRIPTION     
            "This is password for FTP site"
    ::= { rsiMeasurementSetExtnFTPEntry 3 }

rsiMeasurementSetFTPLocation OBJECT-TYPE
    SYNTAX          DisplayString
    ACCESS          read-write
    STATUS          mandatory
    DESCRIPTION     
            "This is directory location for FTP site"
    ::= { rsiMeasurementSetExtnFTPEntry 4 }

rsiMeasurementSetFTPRowStatus OBJECT-TYPE
    SYNTAX          RowStatus
    ACCESS          read-write
    STATUS          mandatory
    DESCRIPTION     
            "This is for dynamic addition/deletion of FTP sites 
             for Measurement Set.
             For creating a new row, only 'createAndGo' is 
             supported. For deleting an existing row, 'delete'
             is supported"
    ::= { rsiMeasurementSetExtnFTPEntry 5 }

rsiMeasurementSetExtnCounterTable OBJECT-TYPE
    SYNTAX          SEQUENCE OF RsiMeasurementSetExtnCounterEntry
    ACCESS          not-accessible
    STATUS          mandatory
    DESCRIPTION     
            "This table contains the information of different Measurement counters
             associated with a Measurement set.
             It contains rsiMeasurementSetID and rsiMeasurementSetVersionId from 
             rsiMeasurementSetBaseTable,rsiSubsystemID from rsiSubsystemTable and
             rsiMeasurementCounterID from rsiMeasurementCounterTable."
    ::= { rsiCommonMib 55 }

rsiMeasurementSetExtnCounterEntry OBJECT-TYPE
    SYNTAX          RsiMeasurementSetExtnCounterEntry
    ACCESS          not-accessible
    STATUS          mandatory
    DESCRIPTION     
            "Description of a measurement set."
    INDEX           { rsiMeasurementSetID, rsiMeasurementSetVersionId, 
                      rsiSubsystemID, rsiMeasurementCounterID }
    ::= { rsiMeasurementSetExtnCounterTable 1 }

RsiMeasurementSetExtnCounterEntry ::=
    SEQUENCE {
        rsiMeasurementSetExtnCounterRowStatus     RowStatus
    }

rsiMeasurementSetExtnCounterRowStatus OBJECT-TYPE
    SYNTAX          RowStatus
    ACCESS          read-write
    STATUS          mandatory
    DESCRIPTION     
            "This is for dynamic addition/deletion of Measurement
             counter within Measurement Sets.
             For creating a new row, only 'createAndGo' is 
             supported. For deleting an existing row, 'delete'
             is supported"
    ::= { rsiMeasurementSetExtnCounterEntry 1 }

rsiMeasurementSetDataCollectionTable OBJECT-TYPE
    SYNTAX          SEQUENCE OF RsiMeasurementSetDataCollectionEntry
    ACCESS          not-accessible
    STATUS          mandatory
    DESCRIPTION     
            "This table contains measurement set data timestamps.It contains 
             rsiMeasurementSetID from rsiMeasurementSetBaseTable."
    ::= { rsiCommonMib 56 }

rsiMeasurementSetDataCollectionEntry OBJECT-TYPE
    SYNTAX          RsiMeasurementSetDataCollectionEntry
    ACCESS          not-accessible
    STATUS          mandatory
    DESCRIPTION     
            "Description of a measurement set data timestamps"
    INDEX           { rsiMeasurementSetID, rsiMeasurementSetVersionId, 
                      rsiMeasurementSetDataTimeStamp }
    ::= { rsiMeasurementSetDataCollectionTable 1 }

RsiMeasurementSetDataCollectionEntry ::=
    SEQUENCE {
        rsiMeasurementSetDataTimeStamp  INTEGER
    }

rsiMeasurementSetDataTimeStamp OBJECT-TYPE
    SYNTAX          INTEGER
    ACCESS          read-only
    STATUS          mandatory
    DESCRIPTION     
            "This is timestamp of measurement counter data in UTC"
    ::= { rsiMeasurementSetDataCollectionEntry 1 }

rsiMeasurementSetDataTable OBJECT-TYPE
    SYNTAX          SEQUENCE OF RsiMeasurementSetDataEntry
    ACCESS          not-accessible
    STATUS          mandatory
    DESCRIPTION     
            "This table contains measurement counter data.It contains rsiMeasurementSetID
             and rsiMeasurementSetDataTimeStamp from rsiMeasurementSetBaseTable, 
             rsiSubsystemID from SubsystemTable, rsiMeasurementCounterID from 
             rsiMeasurementCounterTable."
    ::= { rsiCommonMib 57 }

rsiMeasurementSetDataEntry OBJECT-TYPE
    SYNTAX          RsiMeasurementSetDataEntry
    ACCESS          not-accessible
    STATUS          mandatory
    DESCRIPTION     
            "Description of a measurement counter data."
    INDEX           { rsiMeasurementSetID, rsiMeasurementSetVersionId, 
                      rsiMeasurementSetDataTimeStamp, 
                      rsiMeasurementSetEntityId, rsiSubsystemID, 
                      rsiMeasurementCounterID, 
                      rsiMeasurementCounterValueId }
    ::= { rsiMeasurementSetDataTable 1 }

RsiMeasurementSetDataEntry ::=
    SEQUENCE {
        rsiMeasurementSetEntityId       DisplayString,
        rsiMeasurementCounterValueId    DisplayString,
        rsiMeasurementCounterValue      INTEGER,
        rsiMeasurementSetDataFlags      INTEGER
    }

rsiMeasurementSetEntityId OBJECT-TYPE
    SYNTAX          DisplayString
    ACCESS          read-only
    STATUS          mandatory
    DESCRIPTION     
            "This is entity Id"
    ::= { rsiMeasurementSetDataEntry 1 }

rsiMeasurementCounterValueId OBJECT-TYPE
    SYNTAX          DisplayString
    ACCESS          read-only
    STATUS          mandatory
    DESCRIPTION     
            "This is value id"
    ::= { rsiMeasurementSetDataEntry 2 }

rsiMeasurementCounterValue OBJECT-TYPE
    SYNTAX          INTEGER
    ACCESS          read-only
    STATUS          mandatory
    DESCRIPTION     
            "This is value of rsiMeasurementCounterID/rsiSystemID/rsiMeasurementCounterValueId"
    ::= { rsiMeasurementSetDataEntry 3 }

rsiMeasurementSetDataFlags OBJECT-TYPE
    SYNTAX          INTEGER
    ACCESS          read-only
    STATUS          mandatory
    DESCRIPTION     
            "This is flags of measurement counter data"
    ::= { rsiMeasurementSetDataEntry 5 }

rsiThresholdCounterTable OBJECT-TYPE
    SYNTAX          SEQUENCE OF RsiThresholdCounterEntry
    ACCESS          not-accessible
    STATUS          mandatory
    DESCRIPTION     
            "This table contains threshold counter information.It contains 
             rsiSubsystemID from rsiSubsystemTable and rsiAlarmId from rsiAlarmTable"
    ::= { rsiCommonMib 58 }

rsiThresholdCounterEntry OBJECT-TYPE
    SYNTAX          RsiThresholdCounterEntry
    ACCESS          not-accessible
    STATUS          mandatory
    DESCRIPTION     
            "Description of a threshold counter."
    INDEX           { rsiSubsystemID, rsiThresholdID }
    ::= { rsiThresholdCounterTable 1 }

RsiThresholdCounterEntry ::=
    SEQUENCE {
        rsiThresholdID                  DisplayString,
        rsiThresholdOid                 DisplayString,
        rsiThresholdType                INTEGER,
        rsiThresholdMode                INTEGER,
        rsiThresholdLeakValue           INTEGER,
        rsiThresholdLowValue            INTEGER,
        rsiThresholdValue               INTEGER,
        rsiThresholdAssociatedId        DisplayString,
        rsiThresholdAction              INTEGER,
        rsiThresholdTimeDifference      INTEGER,
        rsiThresholdScanInterval        INTEGER,
        rsiThresholdModeInterval        INTEGER,
        rsiThresholdEntityType          DisplayString,
        rsiThresholdEntityId            DisplayString,
        rsiThresholdDeferredProcessing  INTEGER,
        rsiThresholdEnable              INTEGER
    }

rsiThresholdID OBJECT-TYPE
    SYNTAX          DisplayString
    ACCESS          read-only
    STATUS          mandatory
    DESCRIPTION     
            "This is threshold id"
    ::= { rsiThresholdCounterEntry 1 }

rsiThresholdOid OBJECT-TYPE
    SYNTAX          DisplayString
    ACCESS          read-only
    STATUS          mandatory
    DESCRIPTION     
            "This is threshold oid"
    ::= { rsiThresholdCounterEntry 2 }

rsiThresholdType OBJECT-TYPE
    SYNTAX          INTEGER { absolute(0), timediff(1), percent(2), 
                        timediffpercent(3) }
    ACCESS          read-only
    STATUS          mandatory
    DESCRIPTION     
            "This identifies the type of a particular threshold.The 
             possible values are absolute, timediff, percent and timediffpercent"
    ::= { rsiThresholdCounterEntry 3 }

rsiThresholdMode OBJECT-TYPE
    SYNTAX          INTEGER { reset(0), leak(1), none(2) }
    ACCESS          read-only
    STATUS          mandatory
    DESCRIPTION     
            "This identifies the threshold mode .The 
             possible values are reset, leak and none."
    ::= { rsiThresholdCounterEntry 4 }

rsiThresholdLeakValue OBJECT-TYPE
    SYNTAX          INTEGER
    ACCESS          read-write
    STATUS          mandatory
    DESCRIPTION     
            "This identifies the threshold leak value.It will always be greater than zero."
    ::= { rsiThresholdCounterEntry 5 }

rsiThresholdLowValue OBJECT-TYPE
    SYNTAX          INTEGER
    ACCESS          read-write
    STATUS          mandatory
    DESCRIPTION     
            "This identifies the threshold's low value.It will always less than 
             rsiThresholdValue.If it is equal to rsiThresholdValue and rsiThresholdDeferredProcessing 
             is true,then alarms can be sent at regular intervals"
    ::= { rsiThresholdCounterEntry 6 }

rsiThresholdValue OBJECT-TYPE
    SYNTAX          INTEGER
    ACCESS          read-write
    STATUS          mandatory
    DESCRIPTION     
            "This identifies the threshold's value.It will always be greater than zero."
    ::= { rsiThresholdCounterEntry 7 }

rsiThresholdAssociatedId OBJECT-TYPE
    SYNTAX          DisplayString
    ACCESS          read-only
    STATUS          mandatory
    DESCRIPTION     
            "This identifies the threshold's associated id.This is used for 'percent'
             and 'timediffpercent' resiThresholdType only."
    ::= { rsiThresholdCounterEntry 8 }

rsiThresholdAction OBJECT-TYPE
    SYNTAX          INTEGER { alarmAndLog(0), logOnly(1) }
    ACCESS          read-write
    STATUS          mandatory
    DESCRIPTION     
            "This identifies the threshold action .The 
             possible values are alarm and log."
    ::= { rsiThresholdCounterEntry 9 }

rsiThresholdTimeDifference OBJECT-TYPE
    SYNTAX          INTEGER
    ACCESS          read-only
    STATUS          mandatory
    DESCRIPTION     
            "This identifies the threshold's time difference."
    ::= { rsiThresholdCounterEntry 11 }

rsiThresholdScanInterval OBJECT-TYPE
    SYNTAX          INTEGER
    ACCESS          read-write
    STATUS          mandatory
    DESCRIPTION     
            "This identifies the threshold's scan interval."
    ::= { rsiThresholdCounterEntry 12 }

rsiThresholdModeInterval OBJECT-TYPE
    SYNTAX          INTEGER
    ACCESS          read-write
    STATUS          mandatory
    DESCRIPTION     
            "This identifies the threshold's mode interval.It is used for 'leak' and 
             'reset' modes only.It will always be greater than zero."
    ::= { rsiThresholdCounterEntry 13 }

rsiThresholdEntityType OBJECT-TYPE
    SYNTAX          DisplayString
    ACCESS          read-only
    STATUS          mandatory
    DESCRIPTION     
            "This identifies the threshold's entity type"
    ::= { rsiThresholdCounterEntry 14 }

rsiThresholdEntityId OBJECT-TYPE
    SYNTAX          DisplayString
    ACCESS          read-only
    STATUS          mandatory
    DESCRIPTION     
            "This identifies the threshold's entity id"
    ::= { rsiThresholdCounterEntry 15 }

rsiThresholdDeferredProcessing OBJECT-TYPE
    SYNTAX          INTEGER { false(0), true(1) }
    ACCESS          read-write
    STATUS          mandatory
    DESCRIPTION     
            "It specifies whether subsystem will generate repeat alarms before crossing
             high / low threshold or not"
    ::= { rsiThresholdCounterEntry 16 }

rsiThresholdEnable OBJECT-TYPE
    SYNTAX          INTEGER { false(0), true(1) }
    ACCESS          read-write
    STATUS          mandatory
    DESCRIPTION     
            "It specifies whether a particulat threshold is enable or not."
    ::= { rsiThresholdCounterEntry 17 }

rsiThresholdCounterReportMapTable OBJECT-TYPE
    SYNTAX          SEQUENCE OF RsiThresholdCounterReportMapEntry
    ACCESS          not-accessible
    STATUS          mandatory
    DESCRIPTION     
            "This table contains threshold counter report map.It contains
             rsiAlarmErrorCode from rsiAlarmEntry,rsiThresholdID from 
             rsiThresholdCounterTable and rsiSubsystemID from rsiSubsystemTable"
    ::= { rsiCommonMib 59 }

rsiThresholdCounterReportMapEntry OBJECT-TYPE
    SYNTAX          RsiThresholdCounterReportMapEntry
    ACCESS          not-accessible
    STATUS          mandatory
    DESCRIPTION     
            "Description of a measurement counter report map"
    INDEX           { rsiSubsystemID, rsiThresholdID, rsiAlarmErrorCode }
    ::= { rsiThresholdCounterReportMapTable 1 }

RsiThresholdCounterReportMapEntry ::=
    SEQUENCE {
        rsiThresholdCounterReportMapRowStatus     RowStatus
    }

rsiThresholdCounterReportMapRowStatus OBJECT-TYPE
    SYNTAX          RowStatus
    ACCESS          read-write
    STATUS          mandatory
    DESCRIPTION     
            "
             For creating a new policy, only 'createAndGo' is
             supported. For deleting an existing row, 'delete'
             is supported"
    ::= { rsiThresholdCounterReportMapEntry 5 }

rsiAlarmRetentionInterval OBJECT-TYPE
    SYNTAX          INTEGER
    ACCESS          read-write
    STATUS          mandatory
    DESCRIPTION     
            "The interval after which the alarms
             will be cleared from the database.
             Note the unit of this time interval is days."
    ::= { rsiCommonMib 60 }

rsiAINTrunkTable OBJECT-TYPE
    SYNTAX          SEQUENCE OF RsiAINTrunkEntry
    ACCESS          not-accessible
    STATUS          mandatory
    DESCRIPTION     
            "This table contains information about AIN Trunks.
             It contains rsiHostId from rsiInventoryHostDetailTable
             table"
    ::= { rsiCommonMib 61 }

rsiAINTrunkEntry OBJECT-TYPE
    SYNTAX          RsiAINTrunkEntry
    ACCESS          not-accessible
    STATUS          mandatory
    DESCRIPTION     
            "Description of a AIN Trunks"
    INDEX           { rsiAINTrunkName }
    ::= { rsiAINTrunkTable 1 }

RsiAINTrunkEntry ::=
    SEQUENCE {
        rsiAINTrunkName                 DisplayString,
        rsiAINHostName                  DisplayString,
        rsiAINPort                      INTEGER,
        rsiAINCardId                    INTEGER,
        rsiAINTrunkType                 INTEGER,
        rsiAINBaudRate                  INTEGER,
        rsiAINFraming                   INTEGER,
        rsiAINLineCoding                INTEGER,
        rsiAINTDMAmode                  INTEGER,
        rsiAINClockSource               INTEGER,
        rsiAINTrunkConfigStatus         INTEGER,
        rsiAINTrunkRowStatus            RowStatus
    }

rsiAINTrunkName OBJECT-TYPE
    SYNTAX          DisplayString
    ACCESS          read-write
    STATUS          mandatory
    DESCRIPTION     
            "This identifies a unique name for a trunk"
    ::= { rsiAINTrunkEntry 1 }

rsiAINHostName OBJECT-TYPE
    SYNTAX          DisplayString
    ACCESS          read-write
    STATUS          mandatory
    DESCRIPTION     
            "This is the name of the host on which the trunk exists"
    ::= { rsiAINTrunkEntry 2 }

rsiAINPort OBJECT-TYPE
    SYNTAX          INTEGER
    ACCESS          read-write
    STATUS          mandatory
    DESCRIPTION     
            "It specifies port associated with a trunk"
    ::= { rsiAINTrunkEntry 3 }

rsiAINCardId OBJECT-TYPE
    SYNTAX          INTEGER
    ACCESS          read-write
    STATUS          mandatory
    DESCRIPTION     
            "It specifies the Id of card associated with trunk"
    ::= { rsiAINTrunkEntry 4 }

rsiAINTrunkType OBJECT-TYPE
    SYNTAX          INTEGER { e1(0), t1(1) }
    ACCESS          read-write
    STATUS          mandatory
    DESCRIPTION     
            "It specifies type of trunk"
    ::= { rsiAINTrunkEntry 5 }

rsiAINBaudRate OBJECT-TYPE
    SYNTAX          INTEGER { baud64(0), baud56(1), baud48(2) }
    ACCESS          read-write
    STATUS          mandatory
    DESCRIPTION     
            "It specifies baud rate"
    ::= { rsiAINTrunkEntry 6 }

rsiAINFraming OBJECT-TYPE
    SYNTAX          INTEGER { esf(0), d4(1), e1(2), crc4(3) }
    ACCESS          read-write
    STATUS          mandatory
    DESCRIPTION     
            "It specifies type of framing"
    ::= { rsiAINTrunkEntry 7 }

rsiAINLineCoding OBJECT-TYPE
    SYNTAX          INTEGER { b8zs(0), ami(1), hdb3(2) }
    ACCESS          read-write
    STATUS          mandatory
    DESCRIPTION     
            "It specifies type of line encoding"
    ::= { rsiAINTrunkEntry 8 }

rsiAINTDMAmode OBJECT-TYPE
    SYNTAX          INTEGER { twomhz(0), eightmhzm(1), eightmhznm(2) }
    ACCESS          read-write
    STATUS          mandatory
    DESCRIPTION     
            "It specifies TDMA mode"
    ::= { rsiAINTrunkEntry 9 }

rsiAINClockSource OBJECT-TYPE
    SYNTAX          INTEGER { adaxexttrunk1(0), adaxexttrunk2(1), 
                        adaxexttrunk3(2), adaxexttrunk4(3), 
                        adaxsrcinternal(4), trunkall(6) }
    ACCESS          read-write
    STATUS          mandatory
    DESCRIPTION     
            "It specifies type of clock source"
    ::= { rsiAINTrunkEntry 10 }

rsiAINTrunkConfigStatus OBJECT-TYPE
    SYNTAX          INTEGER { addinprogress(0), addok(1), adderror(2), 
                        addpartial(3), delinprogress(4), delok(5), 
                        delerror(6), delpartial(7), modinprogress(8), 
                        modok(9), moderror(10), modpartial(11) }
    ACCESS          read-only
    STATUS          mandatory
    DESCRIPTION     
            "It specifies trunk status"
    ::= { rsiAINTrunkEntry 11 }

rsiAINTrunkRowStatus OBJECT-TYPE
    SYNTAX          RowStatus
    ACCESS          read-write
    STATUS          mandatory
    DESCRIPTION     
            "
             For creating a new AIN Trunk, only 'createAndGo' is
             supported. For deleting an existing row, 'delete'
             is supported"
    ::= { rsiAINTrunkEntry 12 }

rsiAINLinkSetTable OBJECT-TYPE
    SYNTAX          SEQUENCE OF RsiAINLinkSetEntry
    ACCESS          not-accessible
    STATUS          mandatory
    DESCRIPTION     
            "This table contains information about AIN Link Sets.
             It contains rsiCompId from rsiComponentTable table where component
             is a functional unit group"
    ::= { rsiCommonMib 62 }

rsiAINLinkSetEntry OBJECT-TYPE
    SYNTAX          RsiAINLinkSetEntry
    ACCESS          not-accessible
    STATUS          mandatory
    DESCRIPTION     
            "Description of a AIN Link Set"
    INDEX           { rsiCompId, rsiAINLinkSetName }
    ::= { rsiAINLinkSetTable 1 }

RsiAINLinkSetEntry ::=
    SEQUENCE {
        rsiAINLinkSetName               DisplayString,
        rsiAINLinkSetFamily             INTEGER,
        rsiAINLinkSetNI                 INTEGER,
        rsiAINLocalPC                   DisplayString,
        rsiAINAdjacantPC                DisplayString,
        rsiAINIsSTP                     INTEGER,
        rsiAINNumLoadedLinks            INTEGER,
        rsiAINLinkSetStatus             INTEGER,
        rsiAINLinkSetConfigStatus       INTEGER,
        rsiAINLinkSetRowStatus          RowStatus
    }

rsiAINLinkSetName OBJECT-TYPE
    SYNTAX          DisplayString
    ACCESS          read-write
    STATUS          mandatory
    DESCRIPTION     
            "This identifies a unique name for a link set"
    ::= { rsiAINLinkSetEntry 2 }

rsiAINLinkSetFamily OBJECT-TYPE
    SYNTAX          INTEGER { ansi(0) }
    ACCESS          read-write
    STATUS          mandatory
    DESCRIPTION     
            "It specifies family of link set"
    ::= { rsiAINLinkSetEntry 3 }

rsiAINLinkSetNI OBJECT-TYPE
    SYNTAX          INTEGER { national(0) }
    ACCESS          read-write
    STATUS          mandatory
    DESCRIPTION     
            "It specifies network indicator"
    ::= { rsiAINLinkSetEntry 4 }

rsiAINLocalPC OBJECT-TYPE
    SYNTAX          DisplayString
    ACCESS          read-write
    STATUS          mandatory
    DESCRIPTION     
            "It specifies local point code.It has sytax as x-x-x"
    ::= { rsiAINLinkSetEntry 5 }

rsiAINAdjacantPC OBJECT-TYPE
    SYNTAX          DisplayString
    ACCESS          read-write
    STATUS          mandatory
    DESCRIPTION     
            "It specifies adjacant point code.It has sytax as x-x-x"
    ::= { rsiAINLinkSetEntry 6 }

rsiAINIsSTP OBJECT-TYPE
    SYNTAX          INTEGER { false(0), true(1) }
    ACCESS          read-write
    STATUS          mandatory
    DESCRIPTION     
            "It specifies  whether this is STP"
    ::= { rsiAINLinkSetEntry 7 }

rsiAINNumLoadedLinks OBJECT-TYPE
    SYNTAX          INTEGER
    ACCESS          read-only
    STATUS          mandatory
    DESCRIPTION     
            "It specifies no of loaded links in this link set"
    ::= { rsiAINLinkSetEntry 8 }

rsiAINLinkSetStatus OBJECT-TYPE
    SYNTAX          INTEGER { active(0), inactive(1) }
    ACCESS          read-write
    STATUS          mandatory
    DESCRIPTION     
            "It specifies status of this link set"
    ::= { rsiAINLinkSetEntry 9 }

rsiAINLinkSetConfigStatus OBJECT-TYPE
    SYNTAX          INTEGER { addinprogress(0), addok(1), adderror(2), 
                        addpartial(3), delinprogress(4), delok(5), 
                        delerror(6), delpartial(7), modinprogress(8), 
                        modok(9), moderror(10), modpartial(11) }
    ACCESS          read-only
    STATUS          mandatory
    DESCRIPTION     
            "It specifies configured status of this link set"
    ::= { rsiAINLinkSetEntry 10 }

rsiAINLinkSetRowStatus OBJECT-TYPE
    SYNTAX          RowStatus
    ACCESS          read-write
    STATUS          mandatory
    DESCRIPTION     
            "
             For creating a new AIN Link Set, only 'createAndGo' is
             supported. For deleting an existing row, 'delete'
             is supported"
    ::= { rsiAINLinkSetEntry 11 }

rsiAINLinkSetDetailTable OBJECT-TYPE
    SYNTAX          SEQUENCE OF RsiAINLinkSetDetailEntry
    ACCESS          not-accessible
    STATUS          mandatory
    DESCRIPTION     
            "This table contains detail information about AIN Link Sets.
             It contains rsiCompId from rsiComponentTable table where component
             is a functional unit group. It contains rsiAINLinkSetName from 
             rsiAINLinkSetTable."
    ::= { rsiCommonMib 63 }

rsiAINLinkSetDetailEntry OBJECT-TYPE
    SYNTAX          RsiAINLinkSetDetailEntry
    ACCESS          not-accessible
    STATUS          mandatory
    DESCRIPTION     
            "Detail Description of a AIN Link Set"
    INDEX           { rsiAINLinkSetName, rsiCompId, rsiLinkSetOMCCompId }
    ::= { rsiAINLinkSetDetailTable 1 }

RsiAINLinkSetDetailEntry ::=
    SEQUENCE {
        rsiLinkSetOMCCompId             INTEGER,
        rsiAINLinkSetDetailStatus       INTEGER,
        rsiAINLinkSetDetailConfigStatus INTEGER
    }

rsiLinkSetOMCCompId OBJECT-TYPE
    SYNTAX          INTEGER
    ACCESS          read-only
    STATUS          mandatory
    DESCRIPTION     
            "It specifies component id of OMC"
    ::= { rsiAINLinkSetDetailEntry 1 }

rsiAINLinkSetDetailStatus OBJECT-TYPE
    SYNTAX          INTEGER { active(0), inactive(1) }
    ACCESS          read-only
    STATUS          mandatory
    DESCRIPTION     
            "It specifies status of this link set"
    ::= { rsiAINLinkSetDetailEntry 2 }

rsiAINLinkSetDetailConfigStatus OBJECT-TYPE
    SYNTAX          INTEGER { addinprogress(0), addok(1), adderror(2), 
                        delinprogress(4), delok(5), delerror(6), 
                        modinprogress(8), modok(9), moderror(10) }
    ACCESS          read-only
    STATUS          mandatory
    DESCRIPTION     
            "It specifies configured status of this link set"
    ::= { rsiAINLinkSetDetailEntry 3 }

rsiAINLinkTable OBJECT-TYPE
    SYNTAX          SEQUENCE OF RsiAINLinkEntry
    ACCESS          not-accessible
    STATUS          mandatory
    DESCRIPTION     
            "This table contains information about AIN Link.
             .It contains rsiAINTrunkName from rsiAINTrunkTable 
             table and rsiAINLinkSetName from rsiAINLinkSetTable."
    ::= { rsiCommonMib 64 }

rsiAINLinkEntry OBJECT-TYPE
    SYNTAX          RsiAINLinkEntry
    ACCESS          not-accessible
    STATUS          mandatory
    DESCRIPTION     
            "Description of a AIN Link"
    INDEX           { rsiAINTrunkName, rsiAINLinkSetName, rsiAINLinkName }
    ::= { rsiAINLinkTable 1 }

RsiAINLinkEntry ::=
    SEQUENCE {
        rsiAINLinkName                  DisplayString,
        rsiAINLinkTimeSlot              INTEGER,
        rsiAINLinkPriority              INTEGER,
        rsiAINLinkStatus                INTEGER,
        rsiAINLinkConfigStatus          INTEGER,
        rsiAINLinkRowStatus             RowStatus
    }

rsiAINLinkName OBJECT-TYPE
    SYNTAX          DisplayString
    ACCESS          read-write
    STATUS          mandatory
    DESCRIPTION     
            "This identifies a unique name for a link"
    ::= { rsiAINLinkEntry 2 }

rsiAINLinkTimeSlot OBJECT-TYPE
    SYNTAX          INTEGER
    ACCESS          read-write
    STATUS          mandatory
    DESCRIPTION     
            "It specifies time slot"
    ::= { rsiAINLinkEntry 3 }

rsiAINLinkPriority OBJECT-TYPE
    SYNTAX          INTEGER
    ACCESS          read-write
    STATUS          mandatory
    DESCRIPTION     
            "It specifies priority"
    ::= { rsiAINLinkEntry 4 }

rsiAINLinkStatus OBJECT-TYPE
    SYNTAX          INTEGER { active(0), inactive(1) }
    ACCESS          read-write
    STATUS          mandatory
    DESCRIPTION     
            "It specifies status of link"
    ::= { rsiAINLinkEntry 5 }

rsiAINLinkConfigStatus OBJECT-TYPE
    SYNTAX          INTEGER { addinprogress(0), addok(1), adderror(2), 
                        addpartial(3), delinprogress(4), delok(5), 
                        delerror(6), delpartial(7), modinprogress(8), 
                        modok(9), moderror(10), modpartial(11) }
    ACCESS          read-only
    STATUS          mandatory
    DESCRIPTION     
            "It specifies configured status of link"
    ::= { rsiAINLinkEntry 6 }

rsiAINLinkRowStatus OBJECT-TYPE
    SYNTAX          RowStatus
    ACCESS          read-write
    STATUS          mandatory
    DESCRIPTION     
            "
             For creating a new AIN Link, only 'createAndGo' is
             supported. For deleting an existing row, 'delete'
             is supported"
    ::= { rsiAINLinkEntry 7 }

rsiAINRouteSetTable OBJECT-TYPE
    SYNTAX          SEQUENCE OF RsiAINRouteSetEntry
    ACCESS          not-accessible
    STATUS          mandatory
    DESCRIPTION     
            "This table contains information about AIN Route Sets."
    ::= { rsiCommonMib 65 }

rsiAINRouteSetEntry OBJECT-TYPE
    SYNTAX          RsiAINRouteSetEntry
    ACCESS          not-accessible
    STATUS          mandatory
    DESCRIPTION     
            "Description of a AIN Route Set"
    INDEX           { rsiAINRouteSetName }
    ::= { rsiAINRouteSetTable 1 }

RsiAINRouteSetEntry ::=
    SEQUENCE {
        rsiAINRouteSetName              DisplayString,
        rsiAINRouteSetDPC               DisplayString,
        rsiAINRouteSetRowStatus         RowStatus
    }

rsiAINRouteSetName OBJECT-TYPE
    SYNTAX          DisplayString
    ACCESS          read-write
    STATUS          mandatory
    DESCRIPTION     
            "This identifies a unique name for a route set"
    ::= { rsiAINRouteSetEntry 2 }

rsiAINRouteSetDPC OBJECT-TYPE
    SYNTAX          DisplayString
    ACCESS          read-write
    STATUS          mandatory
    DESCRIPTION     
            "It specifies DPC for this route set.It has sytax as x-x-x"
    ::= { rsiAINRouteSetEntry 3 }

rsiAINRouteSetRowStatus OBJECT-TYPE
    SYNTAX          RowStatus
    ACCESS          read-write
    STATUS          mandatory
    DESCRIPTION     
            "
             For creating a new AIN Route Set, only 'createAndGo' is
             supported. For deleting an existing row, 'delete'
             is supported"
    ::= { rsiAINRouteSetEntry 4 }

rsiAINRouteTable OBJECT-TYPE
    SYNTAX          SEQUENCE OF RsiAINRouteEntry
    ACCESS          not-accessible
    STATUS          mandatory
    DESCRIPTION     
            "This table contains information about AIN Route.
             It contains rsiCompId from rsiComponentTable table where component
             is a functional unit group.It contains rsiAINTrunkName from rsiAINTrunkTable
             table and rsiAINRouteSetName from rsiAINRouteSetTable."
    ::= { rsiCommonMib 66 }

rsiAINRouteEntry OBJECT-TYPE
    SYNTAX          RsiAINRouteEntry
    ACCESS          not-accessible
    STATUS          mandatory
    DESCRIPTION     
            "Description of a AIN Route"
    INDEX           { rsiCompId, rsiAINRouteName, rsiAINRouteSetName, 
                      rsiAINLinkSetName }
    ::= { rsiAINRouteTable 1 }

RsiAINRouteEntry ::=
    SEQUENCE {
        rsiAINRouteName                 DisplayString,
        rsiAINRoutePriority             INTEGER,
        rsiAINRouteSIO                  INTEGER,
        rsiAINRouteSSN                  INTEGER,
        rsiAINRoutehasSSN               INTEGER,
        rsiAINRouteDPC                  DisplayString,
        rsiAINRouteStatus               INTEGER,
        rsiAINRouteRowStatus            RowStatus
    }

rsiAINRouteName OBJECT-TYPE
    SYNTAX          DisplayString
    ACCESS          read-write
    STATUS          mandatory
    DESCRIPTION     
            "This identifies a unique name for a route"
    ::= { rsiAINRouteEntry 2 }

rsiAINRoutePriority OBJECT-TYPE
    SYNTAX          INTEGER
    ACCESS          read-write
    STATUS          mandatory
    DESCRIPTION     
            "It specifies priority"
    ::= { rsiAINRouteEntry 3 }

rsiAINRouteSIO OBJECT-TYPE
    SYNTAX          INTEGER
    ACCESS          read-write
    STATUS          mandatory
    DESCRIPTION     
            "It specifies SIO"
    ::= { rsiAINRouteEntry 4 }

rsiAINRouteSSN OBJECT-TYPE
    SYNTAX          INTEGER
    ACCESS          read-write
    STATUS          mandatory
    DESCRIPTION     
            "It specifies SSN"
    ::= { rsiAINRouteEntry 5 }

rsiAINRoutehasSSN OBJECT-TYPE
    SYNTAX          INTEGER
    ACCESS          read-write
    STATUS          mandatory
    DESCRIPTION     
            "It specifies whether route has SSN"
    ::= { rsiAINRouteEntry 6 }

rsiAINRouteDPC OBJECT-TYPE
    SYNTAX          DisplayString
    ACCESS          read-write
    STATUS          mandatory
    DESCRIPTION     
            "It specifies Distant point code.It has sytax as x-x-x"
    ::= { rsiAINRouteEntry 7 }

rsiAINRouteStatus OBJECT-TYPE
    SYNTAX          INTEGER { addinprogress(0), addok(1), adderror(2), 
                        addpartial(3), delinprogress(4), delok(5), 
                        delerror(6), delpartial(7), modinprogress(8), 
                        modok(9), moderror(10), modpartial(11) }
    ACCESS          read-only
    STATUS          mandatory
    DESCRIPTION     
            "It specifies status of route"
    ::= { rsiAINRouteEntry 8 }

rsiAINRouteRowStatus OBJECT-TYPE
    SYNTAX          RowStatus
    ACCESS          read-write
    STATUS          mandatory
    DESCRIPTION     
            "
             For creating a new AIN Route, only 'createAndGo' is
             supported. For deleting an existing row, 'delete'
             is supported"
    ::= { rsiAINRouteEntry 9 }

rsiAINRouteDetailTable OBJECT-TYPE
    SYNTAX          SEQUENCE OF RsiAINRouteDetailEntry
    ACCESS          not-accessible
    STATUS          mandatory
    DESCRIPTION     
            "This table contains detail information about AIN Route.
             It contains rsiCompId from rsiComponentTable table where component
             is a OMC.It contains rsiAINTrunkName from rsiAINTrunkTable
             table and rsiAINRouteSetName from rsiAINRouteSetTable."
    ::= { rsiCommonMib 67 }

rsiAINRouteDetailEntry OBJECT-TYPE
    SYNTAX          RsiAINRouteDetailEntry
    ACCESS          not-accessible
    STATUS          mandatory
    DESCRIPTION     
            "Description of a AIN Route"
    INDEX           { rsiAINRouteName, rsiCompId, rsiRouteOMCCompId }
    ::= { rsiAINRouteDetailTable 1 }

RsiAINRouteDetailEntry ::=
    SEQUENCE {
        rsiRouteOMCCompId               INTEGER,
        rsiAINRouteDetailStatus         INTEGER
    }

rsiRouteOMCCompId OBJECT-TYPE
    SYNTAX          INTEGER
    ACCESS          read-only
    STATUS          mandatory
    DESCRIPTION     
            "It specifies component id of OMC"
    ::= { rsiAINRouteDetailEntry 1 }

rsiAINRouteDetailStatus OBJECT-TYPE
    SYNTAX          INTEGER { addinprogress(0), addok(1), adderror(2), 
                        delinprogress(4), delok(5), delerror(6), 
                        modinprogress(8), modok(9), moderror(10) }
    ACCESS          read-only
    STATUS          mandatory
    DESCRIPTION     
            "It specifies status of route"
    ::= { rsiAINRouteDetailEntry 2 }

rsiSasGeneralPerfCounters OBJECT-TYPE
    SYNTAX          SEQUENCE OF RsiSasGeneralPerfCountersEntry
    ACCESS          not-accessible
    STATUS          mandatory
    DESCRIPTION     
            "This table contains the information of General Perf measurement
             counters on different subsystems.It contains rsiSubsystemID
             from rsiSubsystemTable."
    ::= { rsiCommonMib 68 }

rsiSasGeneralPerfCountersEntry OBJECT-TYPE
    SYNTAX          RsiSasGeneralPerfCountersEntry
    ACCESS          not-accessible
    STATUS          mandatory
    DESCRIPTION     
            "Description of a General measurement counter of a particular subsystem."
    INDEX           { rsisubsysid }
    ::= { rsiSasGeneralPerfCounters 1 }

RsiSasGeneralPerfCountersEntry ::=
    SEQUENCE {
        rsisubsysid                     INTEGER,
        rsiSasNumActAppSessions         INTEGER,
        rsiSasNumActSipSessions         INTEGER,
        rsiSasNumRejectReq              INTEGER,
        rsiSasNumCallsCurrReplicated    INTEGER,
        rsiSasNumReqFailedTrig          INTEGER,
        rsiSasNum1XXResIn               INTEGER,
        rsiSasNum1XXResOut              INTEGER,
        rsiSasNum2XXResIn               INTEGER,
        rsiSasNum2XXResOut              INTEGER,
        rsiSasNum3XXResIn               INTEGER,
        rsiSasNum3XXResOut              INTEGER,
        rsiSasNum4XXResIn               INTEGER,
        rsiSasNum4XXResOut              INTEGER,
        rsiSasNum5XXResIn               INTEGER,
        rsiSasNum5XXResOut              INTEGER,
        rsiSasNum6XXResIn               INTEGER,
        rsiSasNum6XXResOut              INTEGER,
        rsiSasNumACKTimeout             INTEGER,
        rsiSasNumACKsIn                 INTEGER,
        rsiSasNumACKsOut                INTEGER,
        rsiSasNumAppSessions            INTEGER,
        rsiSasNumBYEsIn                 INTEGER,
        rsiSasNuBYEsOut                 INTEGER,
        rsiSasNumCancelsIn              INTEGER,
        rsiSasNumCancelsOut             INTEGER,
        rsiSasNumDeserialFail           INTEGER,
        rsiSasNumInfosIn                INTEGER,
        rsiSasNumInforsOut              INTEGER,
        rsiSasNumInvitesIn              INTEGER,
        rsiSasNumInvitesOut             INTEGER,
        rsiSasNumMsgIn                  INTEGER,
        rsiSasNumMsgOut                 INTEGER,
        rsiSasNumNotifysIn              INTEGER,
        rsiSasNumNotifysOut             INTEGER,
        rsiSasNumOptionsIn              INTEGER,
        rsiSasNumOptionsOut             INTEGER,
        rsiSasNumPrackTimedout          INTEGER,
        rsiSasNumPracksIn               INTEGER,
        rsiSasNumPracksOut              INTEGER,
        rsiSasNumPublishsIn             INTEGER,
        rsiSasNumPublishsOut            INTEGER,
        rsiSasNumRefersIn               INTEGER,
        rsiSasNumRefersOut              INTEGER,
        rsiSasNumRegistersIn            INTEGER,
        rsiSasNumRegistersOut           INTEGER,
        rsiSasNumRequestsIn             INTEGER,
        rsiSasNumRequestsOut            INTEGER,
        rsiSasNumResponsesIn            INTEGER,
        rsiSasNumResponsesOut           INTEGER,
        rsiSasNumSIPSessions            INTEGER,
        rsiSasNumSubscribesIn           INTEGER,
        rsiSasNumSubscribesOut          INTEGER,
        rsiSasNumSerializationFailures  INTEGER,
        rsiSasNumTimedoutAppSessions    INTEGER,
        rsiSasNumUpdatesIn              INTEGER,
        rsiSasNumUpdatesOut             INTEGER,
        rsiSasNumcallsActivated         INTEGER,
        rsiSasNumcallsCleanedup         INTEGER,
        rsiSasNumcallsReplicated        INTEGER
    }

rsisubsysid OBJECT-TYPE
    SYNTAX          INTEGER
    ACCESS          read-only
    STATUS          mandatory
    DESCRIPTION     
            "Subsystem for which measurement counter is needed"
    ::= { rsiSasGeneralPerfCountersEntry 1 }

rsiSasNumActAppSessions OBJECT-TYPE
    SYNTAX          INTEGER
    ACCESS          read-only
    STATUS          mandatory
    DESCRIPTION     
            "Number of active application sessions"
    ::= { rsiSasGeneralPerfCountersEntry 2 }

rsiSasNumActSipSessions OBJECT-TYPE
    SYNTAX          INTEGER
    ACCESS          read-only
    STATUS          mandatory
    DESCRIPTION     
            "Number of active SIP sessions"
    ::= { rsiSasGeneralPerfCountersEntry 3 }

rsiSasNumRejectReq OBJECT-TYPE
    SYNTAX          INTEGER
    ACCESS          read-only
    STATUS          mandatory
    DESCRIPTION     
            "Number of Rejected Requests"
    ::= { rsiSasGeneralPerfCountersEntry 4 }

rsiSasNumCallsCurrReplicated OBJECT-TYPE
    SYNTAX          INTEGER
    ACCESS          read-only
    STATUS          mandatory
    DESCRIPTION     
            "Number of Calls Currently Replicated"
    ::= { rsiSasGeneralPerfCountersEntry 5 }

rsiSasNumReqFailedTrig OBJECT-TYPE
    SYNTAX          INTEGER
    ACCESS          read-only
    STATUS          mandatory
    DESCRIPTION     
            "Number of active Request Failed to Trigger"
    ::= { rsiSasGeneralPerfCountersEntry 6 }

rsiSasNum1XXResIn OBJECT-TYPE
    SYNTAX          INTEGER
    ACCESS          read-only
    STATUS          mandatory
    DESCRIPTION     
            "Number of 1XX Responses In"
    ::= { rsiSasGeneralPerfCountersEntry 7 }

rsiSasNum1XXResOut OBJECT-TYPE
    SYNTAX          INTEGER
    ACCESS          read-only
    STATUS          mandatory
    DESCRIPTION     
            "Number of 1XX Responses Out"
    ::= { rsiSasGeneralPerfCountersEntry 8 }

rsiSasNum2XXResIn OBJECT-TYPE
    SYNTAX          INTEGER
    ACCESS          read-only
    STATUS          mandatory
    DESCRIPTION     
            "Number of 2XX Responses In"
    ::= { rsiSasGeneralPerfCountersEntry 9 }

rsiSasNum2XXResOut OBJECT-TYPE
    SYNTAX          INTEGER
    ACCESS          read-only
    STATUS          mandatory
    DESCRIPTION     
            "Number of 2XX Responses Out"
    ::= { rsiSasGeneralPerfCountersEntry 10 }

rsiSasNum3XXResIn OBJECT-TYPE
    SYNTAX          INTEGER
    ACCESS          read-only
    STATUS          mandatory
    DESCRIPTION     
            "Number of  3XX Responses In"
    ::= { rsiSasGeneralPerfCountersEntry 11 }

rsiSasNum3XXResOut OBJECT-TYPE
    SYNTAX          INTEGER
    ACCESS          read-only
    STATUS          mandatory
    DESCRIPTION     
            "Number of 3XX Responses Out"
    ::= { rsiSasGeneralPerfCountersEntry 12 }

rsiSasNum4XXResIn OBJECT-TYPE
    SYNTAX          INTEGER
    ACCESS          read-only
    STATUS          mandatory
    DESCRIPTION     
            "Number of 4XX Responses In"
    ::= { rsiSasGeneralPerfCountersEntry 13 }

rsiSasNum4XXResOut OBJECT-TYPE
    SYNTAX          INTEGER
    ACCESS          read-only
    STATUS          mandatory
    DESCRIPTION     
            "Number of 4XX Responses Out"
    ::= { rsiSasGeneralPerfCountersEntry 14 }

rsiSasNum5XXResIn OBJECT-TYPE
    SYNTAX          INTEGER
    ACCESS          read-only
    STATUS          mandatory
    DESCRIPTION     
            "Number of 5XX Responses In"
    ::= { rsiSasGeneralPerfCountersEntry 15 }

rsiSasNum5XXResOut OBJECT-TYPE
    SYNTAX          INTEGER
    ACCESS          read-only
    STATUS          mandatory
    DESCRIPTION     
            "Number of 5XX Responses Out"
    ::= { rsiSasGeneralPerfCountersEntry 16 }

rsiSasNum6XXResIn OBJECT-TYPE
    SYNTAX          INTEGER
    ACCESS          read-only
    STATUS          mandatory
    DESCRIPTION     
            "Number of  6XX Responses In"
    ::= { rsiSasGeneralPerfCountersEntry 17 }

rsiSasNum6XXResOut OBJECT-TYPE
    SYNTAX          INTEGER
    ACCESS          read-only
    STATUS          mandatory
    DESCRIPTION     
            "Number of 6XX Responses Out"
    ::= { rsiSasGeneralPerfCountersEntry 18 }

rsiSasNumACKTimeout OBJECT-TYPE
    SYNTAX          INTEGER
    ACCESS          read-only
    STATUS          mandatory
    DESCRIPTION     
            "Number of ACK TImed Out"
    ::= { rsiSasGeneralPerfCountersEntry 19 }

rsiSasNumACKsIn OBJECT-TYPE
    SYNTAX          INTEGER
    ACCESS          read-only
    STATUS          mandatory
    DESCRIPTION     
            "Number of ACKs In"
    ::= { rsiSasGeneralPerfCountersEntry 20 }

rsiSasNumACKsOut OBJECT-TYPE
    SYNTAX          INTEGER
    ACCESS          read-only
    STATUS          mandatory
    DESCRIPTION     
            "Number of ACKs Out"
    ::= { rsiSasGeneralPerfCountersEntry 21 }

rsiSasNumAppSessions OBJECT-TYPE
    SYNTAX          INTEGER
    ACCESS          read-only
    STATUS          mandatory
    DESCRIPTION     
            "Number of application sessions"
    ::= { rsiSasGeneralPerfCountersEntry 22 }

rsiSasNumBYEsIn OBJECT-TYPE
    SYNTAX          INTEGER
    ACCESS          read-only
    STATUS          mandatory
    DESCRIPTION     
            "Number of BYEs In"
    ::= { rsiSasGeneralPerfCountersEntry 23 }

rsiSasNuBYEsOut OBJECT-TYPE
    SYNTAX          INTEGER
    ACCESS          read-only
    STATUS          mandatory
    DESCRIPTION     
            "Number of BYEs Out"
    ::= { rsiSasGeneralPerfCountersEntry 24 }

rsiSasNumCancelsIn OBJECT-TYPE
    SYNTAX          INTEGER
    ACCESS          read-only
    STATUS          mandatory
    DESCRIPTION     
            "Number of Cancels In"
    ::= { rsiSasGeneralPerfCountersEntry 25 }

rsiSasNumCancelsOut OBJECT-TYPE
    SYNTAX          INTEGER
    ACCESS          read-only
    STATUS          mandatory
    DESCRIPTION     
            "Number of Cancels Out"
    ::= { rsiSasGeneralPerfCountersEntry 26 }

rsiSasNumDeserialFail OBJECT-TYPE
    SYNTAX          INTEGER
    ACCESS          read-only
    STATUS          mandatory
    DESCRIPTION     
            "Number of Deserialization Failures"
    ::= { rsiSasGeneralPerfCountersEntry 27 }

rsiSasNumInfosIn OBJECT-TYPE
    SYNTAX          INTEGER
    ACCESS          read-only
    STATUS          mandatory
    DESCRIPTION     
            "Number of INFOs In"
    ::= { rsiSasGeneralPerfCountersEntry 28 }

rsiSasNumInforsOut OBJECT-TYPE
    SYNTAX          INTEGER
    ACCESS          read-only
    STATUS          mandatory
    DESCRIPTION     
            "Number of INFOs Out"
    ::= { rsiSasGeneralPerfCountersEntry 29 }

rsiSasNumInvitesIn OBJECT-TYPE
    SYNTAX          INTEGER
    ACCESS          read-only
    STATUS          mandatory
    DESCRIPTION     
            "Number of INVITEs In"
    ::= { rsiSasGeneralPerfCountersEntry 30 }

rsiSasNumInvitesOut OBJECT-TYPE
    SYNTAX          INTEGER
    ACCESS          read-only
    STATUS          mandatory
    DESCRIPTION     
            "Number of INVITEs Out"
    ::= { rsiSasGeneralPerfCountersEntry 31 }

rsiSasNumMsgIn OBJECT-TYPE
    SYNTAX          INTEGER
    ACCESS          read-only
    STATUS          mandatory
    DESCRIPTION     
            "Number of Message In"
    ::= { rsiSasGeneralPerfCountersEntry 32 }

rsiSasNumMsgOut OBJECT-TYPE
    SYNTAX          INTEGER
    ACCESS          read-only
    STATUS          mandatory
    DESCRIPTION     
            "Number of Message Out"
    ::= { rsiSasGeneralPerfCountersEntry 33 }

rsiSasNumNotifysIn OBJECT-TYPE
    SYNTAX          INTEGER
    ACCESS          read-only
    STATUS          mandatory
    DESCRIPTION     
            "Number of Notify In"
    ::= { rsiSasGeneralPerfCountersEntry 34 }

rsiSasNumNotifysOut OBJECT-TYPE
    SYNTAX          INTEGER
    ACCESS          read-only
    STATUS          mandatory
    DESCRIPTION     
            "Number of Notify Out"
    ::= { rsiSasGeneralPerfCountersEntry 35 }

rsiSasNumOptionsIn OBJECT-TYPE
    SYNTAX          INTEGER
    ACCESS          read-only
    STATUS          mandatory
    DESCRIPTION     
            "Number of active Option In"
    ::= { rsiSasGeneralPerfCountersEntry 36 }

rsiSasNumOptionsOut OBJECT-TYPE
    SYNTAX          INTEGER
    ACCESS          read-only
    STATUS          mandatory
    DESCRIPTION     
            "Number of Option Out"
    ::= { rsiSasGeneralPerfCountersEntry 37 }

rsiSasNumPrackTimedout OBJECT-TYPE
    SYNTAX          INTEGER
    ACCESS          read-only
    STATUS          mandatory
    DESCRIPTION     
            "Number of Pracks TimeOut"
    ::= { rsiSasGeneralPerfCountersEntry 38 }

rsiSasNumPracksIn OBJECT-TYPE
    SYNTAX          INTEGER
    ACCESS          read-only
    STATUS          mandatory
    DESCRIPTION     
            "Number of Pracks In"
    ::= { rsiSasGeneralPerfCountersEntry 39 }

rsiSasNumPracksOut OBJECT-TYPE
    SYNTAX          INTEGER
    ACCESS          read-only
    STATUS          mandatory
    DESCRIPTION     
            "Number of Pracks Out"
    ::= { rsiSasGeneralPerfCountersEntry 40 }

rsiSasNumPublishsIn OBJECT-TYPE
    SYNTAX          INTEGER
    ACCESS          read-only
    STATUS          mandatory
    DESCRIPTION     
            "Number of  Publishes In"
    ::= { rsiSasGeneralPerfCountersEntry 41 }

rsiSasNumPublishsOut OBJECT-TYPE
    SYNTAX          INTEGER
    ACCESS          read-only
    STATUS          mandatory
    DESCRIPTION     
            "Number of Publishes Out"
    ::= { rsiSasGeneralPerfCountersEntry 42 }

rsiSasNumRefersIn OBJECT-TYPE
    SYNTAX          INTEGER
    ACCESS          read-only
    STATUS          mandatory
    DESCRIPTION     
            "Number of 4XX Responses In"
    ::= { rsiSasGeneralPerfCountersEntry 43 }

rsiSasNumRefersOut OBJECT-TYPE
    SYNTAX          INTEGER
    ACCESS          read-only
    STATUS          mandatory
    DESCRIPTION     
            "Number of Refer Out"
    ::= { rsiSasGeneralPerfCountersEntry 44 }

rsiSasNumRegistersIn OBJECT-TYPE
    SYNTAX          INTEGER
    ACCESS          read-only
    STATUS          mandatory
    DESCRIPTION     
            "Number of Register In"
    ::= { rsiSasGeneralPerfCountersEntry 45 }

rsiSasNumRegistersOut OBJECT-TYPE
    SYNTAX          INTEGER
    ACCESS          read-only
    STATUS          mandatory
    DESCRIPTION     
            "Number of Register Out"
    ::= { rsiSasGeneralPerfCountersEntry 46 }

rsiSasNumRequestsIn OBJECT-TYPE
    SYNTAX          INTEGER
    ACCESS          read-only
    STATUS          mandatory
    DESCRIPTION     
            "Number of  Requests In"
    ::= { rsiSasGeneralPerfCountersEntry 47 }

rsiSasNumRequestsOut OBJECT-TYPE
    SYNTAX          INTEGER
    ACCESS          read-only
    STATUS          mandatory
    DESCRIPTION     
            "Number of Requested Out"
    ::= { rsiSasGeneralPerfCountersEntry 48 }

rsiSasNumResponsesIn OBJECT-TYPE
    SYNTAX          INTEGER
    ACCESS          read-only
    STATUS          mandatory
    DESCRIPTION     
            "Number of Responses In"
    ::= { rsiSasGeneralPerfCountersEntry 49 }

rsiSasNumResponsesOut OBJECT-TYPE
    SYNTAX          INTEGER
    ACCESS          read-only
    STATUS          mandatory
    DESCRIPTION     
            "Number of ACKs In"
    ::= { rsiSasGeneralPerfCountersEntry 50 }

rsiSasNumSIPSessions OBJECT-TYPE
    SYNTAX          INTEGER
    ACCESS          read-only
    STATUS          mandatory
    DESCRIPTION     
            "Number of SIP Session"
    ::= { rsiSasGeneralPerfCountersEntry 51 }

rsiSasNumSubscribesIn OBJECT-TYPE
    SYNTAX          INTEGER
    ACCESS          read-only
    STATUS          mandatory
    DESCRIPTION     
            "Number of Subscriber In"
    ::= { rsiSasGeneralPerfCountersEntry 52 }

rsiSasNumSubscribesOut OBJECT-TYPE
    SYNTAX          INTEGER
    ACCESS          read-only
    STATUS          mandatory
    DESCRIPTION     
            "Number of Subcribers Out"
    ::= { rsiSasGeneralPerfCountersEntry 53 }

rsiSasNumSerializationFailures OBJECT-TYPE
    SYNTAX          INTEGER
    ACCESS          read-only
    STATUS          mandatory
    DESCRIPTION     
            "Number of Serialization Failures"
    ::= { rsiSasGeneralPerfCountersEntry 54 }

rsiSasNumTimedoutAppSessions OBJECT-TYPE
    SYNTAX          INTEGER
    ACCESS          read-only
    STATUS          mandatory
    DESCRIPTION     
            "Number of Timed Out App Session"
    ::= { rsiSasGeneralPerfCountersEntry 55 }

rsiSasNumUpdatesIn OBJECT-TYPE
    SYNTAX          INTEGER
    ACCESS          read-only
    STATUS          mandatory
    DESCRIPTION     
            "Number of Updates In"
    ::= { rsiSasGeneralPerfCountersEntry 56 }

rsiSasNumUpdatesOut OBJECT-TYPE
    SYNTAX          INTEGER
    ACCESS          read-only
    STATUS          mandatory
    DESCRIPTION     
            "Number of Updates Out"
    ::= { rsiSasGeneralPerfCountersEntry 57 }

rsiSasNumcallsActivated OBJECT-TYPE
    SYNTAX          INTEGER
    ACCESS          read-only
    STATUS          mandatory
    DESCRIPTION     
            "Number of Calls Activated"
    ::= { rsiSasGeneralPerfCountersEntry 58 }

rsiSasNumcallsCleanedup OBJECT-TYPE
    SYNTAX          INTEGER
    ACCESS          read-only
    STATUS          mandatory
    DESCRIPTION     
            "Number of Calls Cleaned Up"
    ::= { rsiSasGeneralPerfCountersEntry 59 }

rsiSasNumcallsReplicated OBJECT-TYPE
    SYNTAX          INTEGER
    ACCESS          read-only
    STATUS          mandatory
    DESCRIPTION     
            "Number of Calls Replicated"
    ::= { rsiSasGeneralPerfCountersEntry 60 }

rsiSasPriorityCallPerfCounters OBJECT-TYPE
    SYNTAX          SEQUENCE OF RsiSasPriorityCallPerfCountersEntry
    ACCESS          not-accessible
    STATUS          mandatory
    DESCRIPTION     
            "This table contains the information of Priority Call Perf measurement
             counters on different subsystems.It contains rsiSubsystemID
             from rsiSubsystemTable."
    ::= { rsiCommonMib 69 }

rsiSasPriorityCallPerfCountersEntry OBJECT-TYPE
    SYNTAX          RsiSasPriorityCallPerfCountersEntry
    ACCESS          not-accessible
    STATUS          mandatory
    DESCRIPTION     
            "Description of a Priority Call measurement counter of a particular subsystem."
    INDEX           { rsiSubsystemId }
    ::= { rsiSasPriorityCallPerfCounters 1 }

RsiSasPriorityCallPerfCountersEntry ::=
    SEQUENCE {
        rsiMeasurementPriCallCounterValueId   DisplayString,
        rsiMeasurementPriCallCounterValue INTEGER
    }

rsiMeasurementPriCallCounterValueId OBJECT-TYPE
    SYNTAX          DisplayString
    ACCESS          read-only
    STATUS          mandatory
    DESCRIPTION     
            "Measurement Priority Call Counter Identifier"
    ::= { rsiSasPriorityCallPerfCountersEntry 1 }

rsiMeasurementPriCallCounterValue OBJECT-TYPE
    SYNTAX          INTEGER
    ACCESS          read-only
    STATUS          mandatory
    DESCRIPTION     
            "This is value of rsiMeasurementCounterID/rsiSystemID/rsiMeasurementCounterValueId"
    ::= { rsiSasPriorityCallPerfCountersEntry 2 }

rsiTraps OBJECT IDENTIFIER
    ::= { rsiMib 10 }

rsiCommunicationFailure TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms corresponding to communication 
             failure between two subsystems"
    ::= 1

rsiConfigurationError TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms raised because of configuration
             errors of a subsystem. For ex: a directory not found"
    ::= 2

rsiSystemFaults TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms rasied by subsystems. For ex:
             subsystem is up/down, etc"
    ::= 3

rsiSystemCapacity TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms corresponding to system capacity 
             overflow. For ex: buffer overflow, max. no of service
             instances exceeded."
    ::= 4

rsiResourceFailure TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms corresponding to Resource Failure. 
             For ex: database write failed, file open failed, etc"
    ::= 5

rsiApplicationError TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms corresponding to application errors. 
             For ex: wrong format of input CDR, incomplete input CDR, etc"
    ::= 6

rsiThresholdAlarm TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName }
--     STATUS          mandatory
    DESCRIPTION     
            "This defines the alarms corresponding to threshold errors. 
             For ex: CPU usage exceeded a given threshold"
    ::= 7

rsiSecurityAlarm TRAP-TYPE
    ENTERPRISE      rsiTraps
    VARIABLES       { rsiAlarmId, rsiRelatedAlarmId, rsiAlarmDateTime, 
                      rsiAlarmErrorCode, rsiAlarmContent, 
                      rsiOriginatingSubsystemId, 
                      rsiOriginatingSubsystemName, 
                      rsiTroublingSubsystemId, rsiTroublingSubsystemName, 
                      rsiAlarmSeverity, rsiOrigSystemId, 
                      rsiOrigSystemName, rsiOrigHostId, rsiOrigHostName, 
                      rsiUserId }
--     STATUS          mandatory
    DESCRIPTION     
            "This defines the security alarms. For ex: if a user tries
             to login in for 3 consecutive times, and enters a wrong
             password, then an alarm would be raised."
    ::= 8

END -- end of module BAY-PACKETS-EMS-MIB.
