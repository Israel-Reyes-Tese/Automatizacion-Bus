--
-- This SMIv1 module has been generated by smidump 0.2-cvs. Do not edit.
--

SONUS-METAVAR-MIB DEFINITIONS ::= BEGIN

IMPORTS
    OBJECT-TYPE
        FROM RFC-1212
    Counter, Gauge, IpAddress
        FROM RFC1155-SMI
    sonusCommonSoftwarePlatformServicesMIBs
        FROM SONUS-SMI;

sonusMetaVarMIB OBJECT IDENTIFIER
    ::= { sonusCommonSoftwarePlatformServicesMIBs 22 }

-- sonusMetaVarMIB MODULE-IDENTITY
--     LAST-UPDATED    "201604140000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB Module for Meta Variables."
--     REVISION        "201604140000Z"
--     DESCRIPTION     
--             "Auto generated MIB."
--     ::= { sonusCommonSoftwarePlatformServicesMIBs 22 }


String ::=
    OCTET STRING

-- String ::= TEXTUAL-CONVENTION
--     DISPLAY-HINT    "1t"
--     STATUS          mandatory
--     DESCRIPTION     
--             "xs:string"
--     SYNTAX          OCTET STRING

sonusMetaVariableTable OBJECT-TYPE
    SYNTAX          SEQUENCE OF SonusMetaVariableEntry
    ACCESS          not-accessible
    STATUS          mandatory
    DESCRIPTION     
            "
             Dynamic Meta variable name and value pair table in Cloud SBC configuration management.
             "
    ::= { sonusMetaVarMIB 1 }

sonusMetaVariableEntry OBJECT-TYPE
    SYNTAX          SonusMetaVariableEntry
    ACCESS          not-accessible
    STATUS          mandatory
    DESCRIPTION     
            ""
    INDEX           { sonusMetaVariableCeName, sonusMetaVariableName }
    ::= { sonusMetaVariableTable 1 }

SonusMetaVariableEntry ::=
    SEQUENCE {
        sonusMetaVariableName           String,
        sonusMetaVariableValue          String,
        sonusMetaVariableCeName         String
    }

sonusMetaVariableName OBJECT-TYPE
    SYNTAX          String (SIZE(0..255))
    ACCESS          not-accessible
    STATUS          mandatory
    DESCRIPTION     
            "
             The name of Meta Variable.
             "
    ::= { sonusMetaVariableEntry 1 }

sonusMetaVariableValue OBJECT-TYPE
    SYNTAX          String (SIZE(0..255))
    ACCESS          read-only
    STATUS          mandatory
    DESCRIPTION     
            "
             The value of Meta Variable - string of 255 bytes
             "
    ::= { sonusMetaVariableEntry 2 }

sonusMetaVariableCeName OBJECT-TYPE
    SYNTAX          String (SIZE(0..255))
    ACCESS          not-accessible
    STATUS          mandatory
    DESCRIPTION     
            "
             Identifies the instance.
             "
    ::= { sonusMetaVariableEntry 3 }

END -- end of module SONUS-METAVAR-MIB.
