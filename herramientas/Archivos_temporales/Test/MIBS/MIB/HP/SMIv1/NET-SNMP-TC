--
-- This SMIv1 module has been generated by smidump 0.2-cvs. Do not edit.
--

NET-SNMP-TC DEFINITIONS ::= BEGIN

IMPORTS
    netSnmpAgentOIDs, netSnmpDomains, netSnmpModuleIDs
        FROM NET-SNMP-MIB
    Opaque
        FROM RFC1155-SMI;

netSnmpTCs OBJECT IDENTIFIER
    ::= { netSnmpModuleIDs 1 }

-- netSnmpTCs MODULE-IDENTITY
--     LAST-UPDATED    "200510140000Z"
--     ORGANIZATION    
--             "www.net-snmp.org"
--     CONTACT-INFO    
--             "postal:   Wes Hardaker
--              P.O. Box 382
--              Davis CA  95617
--              
--              email:    net-snmp-coders@lists.sourceforge.net"
--     DESCRIPTION     
--             "Textual conventions and enumerations for the Net-SNMP project"
--     REVISION        "200202120000Z"
--     DESCRIPTION     
--             "First draft"
--     ::= { netSnmpModuleIDs 1 }


Float ::=
    Opaque (SIZE(7))

-- Float ::= TEXTUAL-CONVENTION
--     STATUS          mandatory
--     DESCRIPTION     
--             "A single precision floating-point number.  The semantics
--              and encoding are identical for type 'single' defined in
--              IEEE Standard for Binary Floating-Point,
--              ANSI/IEEE Std 754-1985.
--              The value is restricted to the BER serialization of
--              the following ASN.1 type:
--                  FLOATTYPE ::= [120] IMPLICIT FloatType
--              (note: the value 120 is the sum of '30'h and '48'h)
--              The BER serialization of the length for values of
--              this type must use the definite length, short
--              encoding form.
--              
--              For example, the BER serialization of value 123
--              of type FLOATTYPE is '9f780442f60000'h.  (The tag
--              is '9f78'h; the length is '04'h; and the value is
--              '42f60000'h.) The BER serialization of value
--              '9f780442f60000'h of data type Opaque is
--              '44079f780442f60000'h. (The tag is '44'h; the length
--              is '07'h; and the value is '9f780442f60000'h.)"
--     SYNTAX          Opaque (SIZE(7))

hpux9 OBJECT IDENTIFIER
    ::= { netSnmpAgentOIDs 1 }

sunos4 OBJECT IDENTIFIER
    ::= { netSnmpAgentOIDs 2 }

solaris OBJECT IDENTIFIER
    ::= { netSnmpAgentOIDs 3 }

osf OBJECT IDENTIFIER
    ::= { netSnmpAgentOIDs 4 }

ultrix OBJECT IDENTIFIER
    ::= { netSnmpAgentOIDs 5 }

hpux10 OBJECT IDENTIFIER
    ::= { netSnmpAgentOIDs 6 }

netbsd OBJECT IDENTIFIER
    ::= { netSnmpAgentOIDs 7 }

freebsd OBJECT IDENTIFIER
    ::= { netSnmpAgentOIDs 8 }

irix OBJECT IDENTIFIER
    ::= { netSnmpAgentOIDs 9 }

linux OBJECT IDENTIFIER
    ::= { netSnmpAgentOIDs 10 }

bsdi OBJECT IDENTIFIER
    ::= { netSnmpAgentOIDs 11 }

openbsd OBJECT IDENTIFIER
    ::= { netSnmpAgentOIDs 12 }

win32 OBJECT IDENTIFIER
    ::= { netSnmpAgentOIDs 13 }

hpux11 OBJECT IDENTIFIER
    ::= { netSnmpAgentOIDs 14 }

aix OBJECT IDENTIFIER
    ::= { netSnmpAgentOIDs 15 }

macosx OBJECT IDENTIFIER
    ::= { netSnmpAgentOIDs 16 }

unknown OBJECT IDENTIFIER
    ::= { netSnmpAgentOIDs 255 }

netSnmpTCPDomain OBJECT IDENTIFIER
    ::= { netSnmpDomains 1 }

netSnmpUnixDomain OBJECT IDENTIFIER
    ::= { netSnmpDomains 2 }

netSnmpAAL5PVCDomain OBJECT IDENTIFIER
    ::= { netSnmpDomains 3 }

netSnmpUDPIPv6Domain OBJECT IDENTIFIER
    ::= { netSnmpDomains 4 }

netSnmpTCPIPv6Domain OBJECT IDENTIFIER
    ::= { netSnmpDomains 5 }

netSnmpCallbackDomain OBJECT IDENTIFIER
    ::= { netSnmpDomains 6 }

netSnmpAliasDomain OBJECT IDENTIFIER
    ::= { netSnmpDomains 7 }

netSnmpDTLSUDPDomain OBJECT IDENTIFIER
    ::= { netSnmpDomains 8 }

netSnmpDTLSSCTPDomain OBJECT IDENTIFIER
    ::= { netSnmpDomains 9 }

END -- end of module NET-SNMP-TC.
