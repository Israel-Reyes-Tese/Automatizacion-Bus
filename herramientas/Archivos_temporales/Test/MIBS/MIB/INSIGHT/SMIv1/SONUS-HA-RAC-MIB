--
-- This SMIv1 module has been generated by smidump 0.2-cvs. Do not edit.
--

SONUS-HA-RAC-MIB DEFINITIONS ::= BEGIN

IMPORTS
    InetAddress
        FROM INET-ADDRESS-MIB
    OBJECT-TYPE
        FROM RFC-1212
    TRAP-TYPE
        FROM RFC-1215
    sysName
        FROM SNMPv2-MIB
    sonusEventClass, sonusEventDescription, sonusEventLevel, 
    sonusEventTime
        FROM SONUS-COMMON-MIB
    sonusHostID
        FROM SONUS-HOST-MIB
    sonusServicesMIBs
        FROM SONUS-SMI;

sonusHARACMIB OBJECT IDENTIFIER
    ::= { sonusServicesMIBs 3339 }

-- sonusHARACMIB MODULE-IDENTITY
--     LAST-UPDATED    "201308040000Z"
--     ORGANIZATION    
--             "Sonus Networks, Inc."
--     CONTACT-INFO    
--             "   Customer Support
--              Sonus Networks, Inc.
--              250 Apollo Drive
--              Chelmsford, MA 01824
--              USA
--              
--              Tel: 978-614-8100
--              Fax: 978-614-8609"
--     DESCRIPTION     
--             "The MIB Module for Sonus High Availability RAC Management."
--     ::= { sonusServicesMIBs 3339 }


SonusHARACState ::=
    INTEGER { offline(0), active(1), standby(2), standby-intent(3) }

-- SonusHARACState ::= TEXTUAL-CONVENTION
--     STATUS          mandatory
--     DESCRIPTION     
--             "The high availability designation of the host.  This is an operational state."
--     SYNTAX          INTEGER
--                       { offline(0), active(1), standby(2), 
--                         standby-intent(3) }

sonusHARACMIBObjects OBJECT IDENTIFIER
    ::= { sonusHARACMIB 1 }

sonusHARACMIBNotifications OBJECT IDENTIFIER
    ::= { sonusHARACMIB 2 }

sonusHARACMIBNotificationsPrefix OBJECT IDENTIFIER
    ::= { sonusHARACMIBNotifications 0 }

sonusHARACMIBNotificationsObjects OBJECT IDENTIFIER
    ::= { sonusHARACMIBNotifications 1 }

sonusRACProcess OBJECT IDENTIFIER
    ::= { sonusHARACMIBNotificationsObjects 11 }

sonusHARACPrevState OBJECT-TYPE
    SYNTAX          SonusHARACState
    ACCESS          read-only
    STATUS          mandatory
    DESCRIPTION     
            "The previous high availability state of this host."
    ::= { sonusHARACMIBNotificationsObjects 12 }

sonusHARACNewState OBJECT-TYPE
    SYNTAX          SonusHARACState
    ACCESS          read-only
    STATUS          mandatory
    DESCRIPTION     
            "The new high availability state of this host."
    ::= { sonusHARACMIBNotificationsObjects 13 }

sonusHARACClusterName OBJECT IDENTIFIER
    ::= { sonusHARACMIBNotificationsObjects 14 }

sonusHARACNodeName OBJECT IDENTIFIER
    ::= { sonusHARACMIBNotificationsObjects 15 }

sonusHARACFailoverReason OBJECT IDENTIFIER
    ::= { sonusHARACMIBNotificationsObjects 16 }

sonusHARACEvicted OBJECT IDENTIFIER
    ::= { sonusHARACMIBNotificationsObjects 26 }

sonusRACHostID OBJECT IDENTIFIER
    ::= { sonusHARACMIBNotificationsObjects 27 }

sonusRACResource OBJECT IDENTIFIER
    ::= { sonusHARACMIBNotificationsObjects 28 }

sonusHARACArbitratorIp OBJECT-TYPE
    SYNTAX          InetAddress
    ACCESS          read-only
    STATUS          mandatory
    DESCRIPTION     
            "The IP address of the Arbitrator instance for whom the trap is raised."
    ::= { sonusHARACMIBNotificationsObjects 29 }

sonusHARACProcessDownNotification TRAP-TYPE
    ENTERPRISE      sonusHARACMIBNotifications
    VARIABLES       { sonusHostID, sonusEventDescription, 
                      sonusEventClass, sonusEventLevel, sonusEventTime, 
                      sonusRACProcess, sonusRACHostID }
--     STATUS          mandatory
    DESCRIPTION     
            "Could not start clusterware process"
    ::= 1

sonusHARACProcessUpNotification TRAP-TYPE
    ENTERPRISE      sonusHARACMIBNotifications
    VARIABLES       { sonusHostID, sonusEventDescription, 
                      sonusEventClass, sonusEventLevel, sonusEventTime, 
                      sonusRACProcess, sonusRACHostID }
--     STATUS          mandatory
    DESCRIPTION     
            "Successfully started clusterware process"
    ::= 2

sonusHARACStateChangeNotification TRAP-TYPE
    ENTERPRISE      sonusHARACMIBNotifications
    VARIABLES       { sonusHARACPrevState, sonusHARACNewState, 
                      sonusHARACClusterName, sonusHARACNodeName }
--     STATUS          mandatory
    DESCRIPTION     
            "Insight State Change notification"
    ::= 3

sonusHARACFailoverInitiatedNotification TRAP-TYPE
    ENTERPRISE      sonusHARACMIBNotifications
    VARIABLES       { sonusHARACFailoverReason, sonusHARACClusterName }
--     STATUS          mandatory
    DESCRIPTION     
            "RAC relocate initiated notification"
    ::= 4

sonusHARACFailoverStandbyTimeoutNotification TRAP-TYPE
    ENTERPRISE      sonusHARACMIBNotifications
    VARIABLES       { sonusHARACClusterName, sonusHARACNodeName }
--     STATUS          mandatory
    DESCRIPTION     
            "RAC relocate timedout notification"
    ::= 5

sonusHARACResourceDownNotification TRAP-TYPE
    ENTERPRISE      sonusHARACMIBNotifications
    VARIABLES       { sonusHostID, sonusEventDescription, 
                      sonusEventClass, sonusEventLevel, sonusEventTime, 
                      sonusRACResource, sonusRACHostID }
--     STATUS          mandatory
    DESCRIPTION     
            "HA RAC Resource down"
    ::= 6

sonusHARACResourceUpNotification TRAP-TYPE
    ENTERPRISE      sonusHARACMIBNotifications
    VARIABLES       { sonusHostID, sonusEventDescription, 
                      sonusEventClass, sonusEventLevel, sonusEventTime, 
                      sonusRACResource, sonusRACHostID }
--     STATUS          mandatory
    DESCRIPTION     
            "HA RAC Resource up"
    ::= 7

sonusHARACNodeShutdownInitiated TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC Shutdown initiated"
    ::= 8

sonusHARACNodeShutdownSucceeded TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC Shutdown succeeded"
    ::= 9

sonusHARACNodeShutdownFailed TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC Shutdown Failed"
    ::= 10

sonusHARACNodeStartupInitiated TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC StartUp initiated"
    ::= 11

sonusHARACNodeStartupSucceeded TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC StartUp succeeded"
    ::= 12

sonusHARACNodeStartupFailed TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC StartUp failed"
    ::= 13

sonusHARACFailoverSuccessful TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC failover successful"
    ::= 14

sonusHARACFailoverFailed TRAP-TYPE
    ENTERPRISE      sonusHARACMIBNotifications
    VARIABLES       { sonusHostID, sonusEventDescription, 
                      sonusEventClass, sonusEventLevel, sonusEventTime, 
                      sonusRACHostID }
--     STATUS          mandatory
    DESCRIPTION     
            "HA RAC failover failed"
    ::= 15

sonusHARACArbitratorDownNotification TRAP-TYPE
    ENTERPRISE      sonusHARACMIBNotifications
    VARIABLES       { sysName, sonusEventTime, sonusEventDescription, 
                      sonusEventLevel, sonusHARACArbitratorIp }
--     STATUS          mandatory
    DESCRIPTION     
            "Arbitrator instance down"
    ::= 16

sonusHARACArbitratorUpNotification TRAP-TYPE
    ENTERPRISE      sonusHARACMIBNotifications
    VARIABLES       { sysName, sonusEventTime, sonusEventDescription, 
                      sonusEventLevel, sonusHARACArbitratorIp }
--     STATUS          mandatory
    DESCRIPTION     
            "Arbitrator instance up"
    ::= 17

END -- end of module SONUS-HA-RAC-MIB.
