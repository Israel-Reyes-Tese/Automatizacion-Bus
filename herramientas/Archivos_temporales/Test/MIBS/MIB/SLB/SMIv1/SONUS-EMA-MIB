--
-- This SMIv1 module has been generated by smidump 0.2-cvs. Do not edit.
--

SONUS-EMA-MIB DEFINITIONS ::= BEGIN

IMPORTS
    OBJECT-TYPE
        FROM RFC-1212
    Counter, Gauge, IpAddress
        FROM RFC1155-SMI
    sonusCommonSoftwarePlatformServicesMIBs
        FROM SONUS-SMI;

sonusEmaMIB OBJECT IDENTIFIER
    ::= { sonusCommonSoftwarePlatformServicesMIBs 20 }

-- sonusEmaMIB MODULE-IDENTITY
--     LAST-UPDATED    "202007050000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             ""
--     REVISION        "202007050000Z"
--     DESCRIPTION     
--             "Auto generated MIB."
--     ::= { sonusCommonSoftwarePlatformServicesMIBs 20 }


String ::=
    OCTET STRING

-- String ::= TEXTUAL-CONVENTION
--     DISPLAY-HINT    "1t"
--     STATUS          mandatory
--     DESCRIPTION     
--             "xs:string"
--     SYNTAX          OCTET STRING

EmaClientAuthMethodType ::=
    INTEGER { usernamePasswordOnly(0), pkiCertOnly(1), 
                        usernamePasswordOrPkiCert(2) }

-- EmaClientAuthMethodType ::= TEXTUAL-CONVENTION
--     STATUS          mandatory
--     DESCRIPTION     
--             ""
--     SYNTAX          INTEGER
--                       { usernamePasswordOnly(0), pkiCertOnly(1), 
--                         usernamePasswordOrPkiCert(2) }

sonusEma OBJECT IDENTIFIER
    ::= { sonusEmaMIB 1 }

sonusEmaClientAuthMethod OBJECT-TYPE
    SYNTAX          EmaClientAuthMethodType
    ACCESS          read-write
    STATUS          obsolete
    DESCRIPTION     
            "
             EMA client authentication method
             "
    ::= { sonusEma 1 }

END -- end of module SONUS-EMA-MIB.
