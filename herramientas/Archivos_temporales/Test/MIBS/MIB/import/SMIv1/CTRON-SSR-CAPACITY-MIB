--
-- This SMIv1 module has been generated by smidump 0.2-cvs. Do not edit.
--

CTRON-SSR-CAPACITY-MIB DEFINITIONS ::= BEGIN

IMPORTS
    ssrMibs
        FROM CTRON-SSR-SMI-MIB
    OBJECT-TYPE
        FROM RFC-1212
    Counter
        FROM RFC1155-SMI
    TruthValue
        FROM SNMPv2-TC;

capacityMIB OBJECT IDENTIFIER
    ::= { ssrMibs 270 }

-- capacityMIB MODULE-IDENTITY
--     LAST-UPDATED    "200006271600Z"
--     ORGANIZATION    
--             "Cabletron Systems, Inc."
--     CONTACT-INFO    
--             "Author:  Daniel M Hegglin
--              Riverstone Networks, Inc
--              5200 Great America Parkway 
--              Santa Clara, CA 95054 
--              408.878.6500 
--              nms-eng@riverstonenet.com
--              http://www.riverstonenet.com"
--     DESCRIPTION     
--             "This module defines a schema to access RS system resource 
--              capacity statistics."
--     REVISION        "200006271600Z"
--     DESCRIPTION     
--             "Update contact information, Change object name chassis
--              to chassisCap due to collsion with chassis in ctron-mib-names.txt.
--              SSR enterprise mibs apply to the Riverstone RS product line and
--              Enterasys SSR."
--     REVISION        "199811050000Z"
--     DESCRIPTION     
--             "Revision 1.0 Initial MIB revision."
--     ::= { ssrMibs 270 }


SSRMemoryType ::=
    INTEGER { cpu(1), intFlash(2), pcmcia(3), rmon(4), l2Hardware(5), 
                        l3Hardware(6) }

-- SSRMemoryType ::= TEXTUAL-CONVENTION
--     STATUS          mandatory
--     DESCRIPTION     
--             "A unique value, greater than zero, for each non-volatile memory
--              device supported by the SSR series of products."
--     SYNTAX          INTEGER
--                       { cpu(1), intFlash(2), pcmcia(3), rmon(4), 
--                         l2Hardware(5), l3Hardware(6) }

SSRCapabilityType ::=
    INTEGER { noSupport(1), available(2), enabled(3), disabled(4) }

-- SSRCapabilityType ::= TEXTUAL-CONVENTION
--     STATUS          mandatory
--     DESCRIPTION     
--             "A unique value, greater than zero, for the different 
--              capabilities of the SSR chassis."
--     SYNTAX          INTEGER
--                       { noSupport(1), available(2), enabled(3), 
--                         disabled(4) }

SSRStatusType ::=
    INTEGER { ready(0), suspPure(1), suspSleep(2), suspMbox(3), 
                        suspQue(4), suspPipe(5), suspSema4(6), 
                        suspEvent(7), suspPart(8), suspMem(9), 
                        suspDrvr(10), finished(11), terminated(12) }

-- SSRStatusType ::= TEXTUAL-CONVENTION
--     STATUS          mandatory
--     DESCRIPTION     
--             "A unique value, greater than zero, for each possible state
--              a task on the SSR can be in."
--     SYNTAX          INTEGER
--                       { ready(0), suspPure(1), suspSleep(2), 
--                         suspMbox(3), suspQue(4), suspPipe(5), 
--                         suspSema4(6), suspEvent(7), suspPart(8), 
--                         suspMem(9), suspDrvr(10), finished(11), 
--                         terminated(12) }

chassisCap OBJECT IDENTIFIER
    ::= { capacityMIB 1 }

capChassisSlotCount OBJECT-TYPE
    SYNTAX          INTEGER (2..32)
    ACCESS          read-only
    STATUS          mandatory
    DESCRIPTION     
            "The maximum number of slots in the chassis, including the
             slot for the CPU module."
    ::= { chassisCap 1 }

capChassisSlotsUsed OBJECT-TYPE
    SYNTAX          INTEGER (0..32)
    ACCESS          read-only
    STATUS          mandatory
    DESCRIPTION     
            "The number of slots used in the chassis.  This number 
             includes the slot used for the CPU module, if any."
    ::= { chassisCap 2 }

capChassisSlotsFree OBJECT-TYPE
    SYNTAX          INTEGER (0..32)
    ACCESS          read-only
    STATUS          mandatory
    DESCRIPTION     
            "The number of free slots in the chassis.  This includes
             all of the available slots not used by the CPU or redundant
             CPU card."
    ::= { chassisCap 3 }

capChassisCPURedundancy OBJECT-TYPE
    SYNTAX          SSRCapabilityType
    ACCESS          read-only
    STATUS          mandatory
    DESCRIPTION     
            "The chassis CPU redundancy capability of the SSR.  This
             will be one of the following values:
               noSupport(1)   -- feature not supported
               available(2)   -- feature not in use
               enabled(3)     -- feature in use and enabled
               disabled(4)    -- feature in use and disabled
             "
    ::= { chassisCap 4 }

capChassisPSRedundancy OBJECT-TYPE
    SYNTAX          SSRCapabilityType
    ACCESS          read-only
    STATUS          mandatory
    DESCRIPTION     
            "The chassis Power Supply redundancy capability of the SSR.  
             This will be one of the following values:
               noSupport(1)   -- feature not supported
               available(2)   -- feature not in use
               enabled(3)     -- feature in use and enabled
               disabled(4)    -- feature in use and disabled
             "
    ::= { chassisCap 5 }

capChassisSFRedundancy OBJECT-TYPE
    SYNTAX          SSRCapabilityType
    ACCESS          read-only
    STATUS          mandatory
    DESCRIPTION     
            "The chassis Switching Fabric redundancy capability of the SSR. 
             This will be one of the following values:
               noSupport(1)   -- feature not supported
               available(2)   -- feature not in use
               enabled(3)     -- feature in use and enabled
               disabled(4)    -- feature in use and disabled
             "
    ::= { chassisCap 6 }

cpu OBJECT IDENTIFIER
    ::= { capacityMIB 2 }

capCPUTable OBJECT-TYPE
    SYNTAX          SEQUENCE OF CapCPUEntry
    ACCESS          not-accessible
    STATUS          mandatory
    DESCRIPTION     
            "Summary of CPU statistics.  It is assumed that there is only 
             one CPU per line card."
    ::= { cpu 1 }

capCPUEntry OBJECT-TYPE
    SYNTAX          CapCPUEntry
    ACCESS          not-accessible
    STATUS          mandatory
    DESCRIPTION     
            "An entry containing CPU statistics information."
    INDEX           { capCPUModuleIndex }
    ::= { capCPUTable 1 }

CapCPUEntry ::=
    SEQUENCE {
        capCPUModuleIndex               INTEGER,
        capCPUCurrentUtilization        INTEGER,
        capCPUL3Learned                 Counter,
        capCPUL3Aged                    Counter,
        capCPUL2Learned                 Counter,
        capCPUL2Aged                    Counter,
        capCPUNIAReceived               Counter,
        capCPUNIATransmitted            Counter
    }

capCPUModuleIndex OBJECT-TYPE
    SYNTAX          INTEGER (0..4294967295)
    ACCESS          not-accessible
    STATUS          mandatory
    DESCRIPTION     
            "The Slot index in which the current CPU is residing."
    ::= { capCPUEntry 1 }

capCPUCurrentUtilization OBJECT-TYPE
    SYNTAX          INTEGER (0..100)
    ACCESS          read-only
    STATUS          mandatory
    DESCRIPTION     
            "The CPU utilization expressed as an integer percentage.
             This is calculated over the last 5 seconds at a 0.1 second
             interval as a simple average."
    ::= { capCPUEntry 2 }

capCPUL3Learned OBJECT-TYPE
    SYNTAX          Counter
    ACCESS          read-only
    STATUS          mandatory
    DESCRIPTION     
            "The total number of new layer 3 flows the CPU has processed and
             programmed into the Layer 3 hardware flow tables. 
             
             Layer 3 flows are packets for IP or IPX protocols that will
             be routed from one subnet to another. Bridged flows or IP and
             IPX flows that originate and terminate in the same subnet
             are accounted for by capCPUL2Learned object."
    ::= { capCPUEntry 3 }

capCPUL3Aged OBJECT-TYPE
    SYNTAX          Counter
    ACCESS          read-only
    STATUS          mandatory
    DESCRIPTION     
            "The total number of Layer 3flows that have been
             removed from the layer 3 hardware flow tables across 
             all modules by the Layer 3 aging task. This number may
             increase quickly if routing protocols are not stable. Removal
             or insertion of routes into the forwarding table will cause
             premature aging of flows. Flows are normally aged/removed 
             from the hardware when there are no more packets being sent
             for a defined time period.  
             This counter is cumulative from the time the system started."
    ::= { capCPUEntry 4 }

capCPUL2Learned OBJECT-TYPE
    SYNTAX          Counter
    ACCESS          read-only
    STATUS          mandatory
    DESCRIPTION     
            "The number of L2 flows or addresses learned. 
             The intended result here is to see how many stations 
             attempt to establish switched communication through the SSR."
    ::= { capCPUEntry 5 }

capCPUL2Aged OBJECT-TYPE
    SYNTAX          Counter
    ACCESS          read-only
    STATUS          mandatory
    DESCRIPTION     
            "The total number of L2 addresses or flows aged out.  Hosts
             that end switched communication through the SSR are aged out
             every 15 seconds."
    ::= { capCPUEntry 6 }

capCPUNIAReceived OBJECT-TYPE
    SYNTAX          Counter
    ACCESS          read-only
    STATUS          mandatory
    DESCRIPTION     
            "The total number of packets received by the NIA chip.
             This is useful in gauging how many packets are forwarded
             to the CPU for processing."
    ::= { capCPUEntry 7 }

capCPUNIATransmitted OBJECT-TYPE
    SYNTAX          Counter
    ACCESS          read-only
    STATUS          mandatory
    DESCRIPTION     
            "The total number of packets transmitted by the NIA chip. 
             This is useful in seeing how much the CPU is communicating
             directory with management stations and other routers."
    ::= { capCPUEntry 8 }

tasks OBJECT IDENTIFIER
    ::= { capacityMIB 3 }

capTaskTable OBJECT-TYPE
    SYNTAX          SEQUENCE OF CapTaskEntry
    ACCESS          not-accessible
    STATUS          mandatory
    DESCRIPTION     
            "A summary of the tasks running on a CPU enabled module in 
             the chassis."
    ::= { tasks 1 }

capTaskEntry OBJECT-TYPE
    SYNTAX          CapTaskEntry
    ACCESS          not-accessible
    STATUS          mandatory
    DESCRIPTION     
            "An entry containing information on a task running on a CPU enabled
             module in the chassis including the memory consumption and current
             status."
    INDEX           { capTaskModuleIndex, capTaskIndex }
    ::= { capTaskTable 1 }

CapTaskEntry ::=
    SEQUENCE {
        capTaskModuleIndex              INTEGER,
        capTaskIndex                    INTEGER,
        capTaskName                     OCTET STRING,
        capTaskShed                     Counter,
        capTaskStatus                   SSRStatusType,
        capTaskUsed                     INTEGER
    }

capTaskModuleIndex OBJECT-TYPE
    SYNTAX          INTEGER (1..4294967295)
    ACCESS          not-accessible
    STATUS          mandatory
    DESCRIPTION     
            "The module index on which the task is running."
    ::= { capTaskEntry 1 }

capTaskIndex OBJECT-TYPE
    SYNTAX          INTEGER (1..4294967295)
    ACCESS          not-accessible
    STATUS          mandatory
    DESCRIPTION     
            "A unique index assigned to a task instance.  This index is
             unique to the task for the time SSR is booted.  If the task
             is terminated, the index will not be reused for another task
             that might become active in the system."
    ::= { capTaskEntry 2 }

capTaskName OBJECT-TYPE
    SYNTAX          OCTET STRING (SIZE(0..8))
    ACCESS          read-only
    STATUS          mandatory
    DESCRIPTION     
            "The encrypted name assigned to this task.  This is unique 
             for each different type of task, but there may be multiple 
             instances of the same task running in the system."
    ::= { capTaskEntry 3 }

capTaskShed OBJECT-TYPE
    SYNTAX          Counter
    ACCESS          read-only
    STATUS          mandatory
    DESCRIPTION     
            "The number of times this task has been scheduled to run.  
             This is a cumulative count from the time the SSR was started."
    ::= { capTaskEntry 4 }

capTaskStatus OBJECT-TYPE
    SYNTAX          SSRStatusType
    ACCESS          read-only
    STATUS          mandatory
    DESCRIPTION     
            "The current status of this task."
    ::= { capTaskEntry 5 }

capTaskUsed OBJECT-TYPE
    SYNTAX          INTEGER (0..4294967295)
    ACCESS          read-only
    STATUS          mandatory
    DESCRIPTION     
            "The size of the memory consumed by this task.  This can be 
             used to monitor any excess memory use by a particular task 
             and is expressed in bytes."
    ::= { capTaskEntry 6 }

memory OBJECT IDENTIFIER
    ::= { capacityMIB 4 }

capMemoryTable OBJECT-TYPE
    SYNTAX          SEQUENCE OF CapMemoryEntry
    ACCESS          not-accessible
    STATUS          mandatory
    DESCRIPTION     
            "A summary of the non-volatile storage devices in the SSR."
    ::= { memory 1 }

capMemoryEntry OBJECT-TYPE
    SYNTAX          CapMemoryEntry
    ACCESS          not-accessible
    STATUS          mandatory
    DESCRIPTION     
            "An entry containing information on a non-volatile memory device
             in the SSR."
    INDEX           { capMemoryType, capMemoryIndex }
    ::= { capMemoryTable 1 }

CapMemoryEntry ::=
    SEQUENCE {
        capMemoryType                   SSRMemoryType,
        capMemoryIndex                  INTEGER,
        capMemoryDescr                  OCTET STRING,
        capMemorySize                   INTEGER,
        capMemoryFree                   INTEGER,
        capMemoryUsed                   INTEGER,
        capMemoryBlockSize              INTEGER,
        capMemoryFailures               Counter,
        capMemoryRemovable              TruthValue
    }

capMemoryType OBJECT-TYPE
    SYNTAX          SSRMemoryType
    ACCESS          not-accessible
    STATUS          mandatory
    DESCRIPTION     
            "A type of storage device from the enumerated memory types."
    ::= { capMemoryEntry 1 }

capMemoryIndex OBJECT-TYPE
    SYNTAX          INTEGER (1..4294967295)
    ACCESS          not-accessible
    STATUS          mandatory
    DESCRIPTION     
            "An index or enumeration for the entries of a particular 
             memory type.  This index corresponds to:
                -- Interface index for L2Hardware Type
                -- Module index for L3Hardware Type
                -- Enumeration for everything else."
    ::= { capMemoryEntry 2 }

capMemoryDescr OBJECT-TYPE
    SYNTAX          OCTET STRING (SIZE(0..256))
    ACCESS          read-only
    STATUS          mandatory
    DESCRIPTION     
            "The description of the memory device."
    ::= { capMemoryEntry 3 }

capMemorySize OBJECT-TYPE
    SYNTAX          INTEGER (1..4294967295)
    ACCESS          read-only
    STATUS          mandatory
    DESCRIPTION     
            "Memory device total memory capacity expressed in blocks."
    ::= { capMemoryEntry 4 }

capMemoryFree OBJECT-TYPE
    SYNTAX          INTEGER (1..4294967295)
    ACCESS          read-only
    STATUS          mandatory
    DESCRIPTION     
            "Memory device free memory in blocks.  This will include any
             unused memory between used memory blocks and is calculated by
             subtracting the memory used from the size of the memory device."
    ::= { capMemoryEntry 5 }

capMemoryUsed OBJECT-TYPE
    SYNTAX          INTEGER (1..4294967295)
    ACCESS          read-only
    STATUS          mandatory
    DESCRIPTION     
            "Size of used memory on the memory device.  This includes the blocks
             of memory that are only partially used and is expressed in blocks."
    ::= { capMemoryEntry 6 }

capMemoryBlockSize OBJECT-TYPE
    SYNTAX          INTEGER (1..4294967295)
    ACCESS          read-only
    STATUS          mandatory
    DESCRIPTION     
            "Size of the memory blocks on the memory device.  This is the 
             minimum block size of memory returned when memory is requested 
             and is expressed in bytes."
    ::= { capMemoryEntry 7 }

capMemoryFailures OBJECT-TYPE
    SYNTAX          Counter
    ACCESS          read-only
    STATUS          mandatory
    DESCRIPTION     
            "The number of times a memory allocation in this memory device has
             failed.  In the case of L2Hardware and L3Hardware types it expresses
             the number of times a Full Hash Bucket condition has been met."
    ::= { capMemoryEntry 8 }

capMemoryRemovable OBJECT-TYPE
    SYNTAX          TruthValue
    ACCESS          read-only
    STATUS          mandatory
    DESCRIPTION     
            "Indicates if the memory type is removable."
    ::= { capMemoryEntry 9 }

capConformance OBJECT IDENTIFIER
    ::= { capacityMIB 6 }

capCompliances OBJECT IDENTIFIER
    ::= { capConformance 1 }

capGroups OBJECT IDENTIFIER
    ::= { capConformance 2 }

capConfGroupV10 OBJECT IDENTIFIER
    ::= { capGroups 1 }

-- capConfGroupV10 OBJECT-GROUP
--     OBJECTS         { capChassisSlotCount, capChassisSlotsUsed, 
--                       capChassisSlotsFree, capChassisCPURedundancy, 
--                       capChassisPSRedundancy, capChassisSFRedundancy, 
--                       capCPUCurrentUtilization, capCPUL3Learned, 
--                       capCPUL3Aged, capCPUL2Learned, capCPUL2Aged, 
--                       capCPUNIAReceived, capCPUNIATransmitted, 
--                       capTaskName, capTaskShed, capTaskStatus, 
--                       capTaskUsed, capMemoryDescr, capMemorySize, 
--                       capMemoryFree, capMemoryUsed, 
--                       capMemoryBlockSize, capMemoryFailures, 
--                       capMemoryRemovable }
--     STATUS          mandatory
--     DESCRIPTION     
--             "A set of managed objects that make up version 3.0 of the SSR capacity mib."
--     ::= { capGroups 1 }

capComplianceV10 OBJECT IDENTIFIER
    ::= { capConfGroupV10 1 }

-- capComplianceV10 MODULE-COMPLIANCE
--     STATUS          mandatory
--     DESCRIPTION     
--             "The compliance statement for the SSR-CAPACITY-MIB."

--     MODULE          -- -- this module

--         MANDATORY-GROUPS    { capConfGroupV10 }

--     ::= { capConfGroupV10 1 }

END -- end of module CTRON-SSR-CAPACITY-MIB.
