--
-- This SMIv1 module has been generated by smidump 0.2-cvs. Do not edit.
--

SONUS-NETSCORE-MIB DEFINITIONS ::= BEGIN

IMPORTS
    OBJECT-TYPE
        FROM RFC-1212
    TRAP-TYPE
        FROM RFC-1215
    DisplayString
        FROM SNMPv2-TC
    sonusEventClass, sonusEventDescription, sonusEventLevel, 
    sonusEventTime
        FROM SONUS-COMMON-MIB
    sonusToolsMIBs
        FROM SONUS-SMI
    SonusSystemName
        FROM SONUS-TC;

sonusNetscoreMIB OBJECT IDENTIFIER
    ::= { sonusToolsMIBs 3 }

-- sonusNetscoreMIB MODULE-IDENTITY
--     LAST-UPDATED    "201003020000Z"
--     ORGANIZATION    
--             "Sonus Networks, Inc."
--     CONTACT-INFO    
--             "   Customer Support
--              Sonus Networks, Inc.
--              7 Technology Park Drive
--              Westford, MA 01886
--              USA
--              
--              Tel: 978-614-8100
--              Fax: 978-614-8609"
--     DESCRIPTION     
--             "The MIB Module for Netscore management."
--     ::= { sonusToolsMIBs 3 }


sonusNetscoreMIBObjects OBJECT IDENTIFIER
    ::= { sonusNetscoreMIB 1 }

sonusNetscoreMIBNotifications OBJECT IDENTIFIER
    ::= { sonusNetscoreMIB 2 }

sonusNetscoreMIBNotificationsPrefix OBJECT IDENTIFIER
    ::= { sonusNetscoreMIBNotifications 0 }

sonusNetscoreMIBNotificationsObjects OBJECT IDENTIFIER
    ::= { sonusNetscoreMIBNotifications 1 }

sonusNetscoreAlarmId OBJECT-TYPE
    SYNTAX          INTEGER
    ACCESS          read-only
    STATUS          mandatory
    DESCRIPTION     
            "This object defines the alarm id"
    ::= { sonusNetscoreMIBNotificationsObjects 1 }

sonusNetscoreNotificationSetClearStatus OBJECT-TYPE
    SYNTAX          INTEGER { notificationSet(1), notificationClear(2) }
    ACCESS          read-only
    STATUS          mandatory
    DESCRIPTION     
            "This object defines the status of the notification."
    ::= { sonusNetscoreMIBNotificationsObjects 2 }

sonusNetscoreServerName OBJECT-TYPE
    SYNTAX          SonusSystemName
    ACCESS          read-only
    STATUS          mandatory
    DESCRIPTION     
            "Name of the Netscore Server."
    ::= { sonusNetscoreMIBNotificationsObjects 3 }

sonusNetscoreTargetName OBJECT-TYPE
    SYNTAX          DisplayString (SIZE(0..8))
    ACCESS          read-only
    STATUS          mandatory
    DESCRIPTION     
            "This object defines the Netscore monitored value"
    ::= { sonusNetscoreMIBNotificationsObjects 4 }

sonusNetscoreThresholdName OBJECT-TYPE
    SYNTAX          DisplayString (SIZE(0..255))
    ACCESS          read-only
    STATUS          mandatory
    DESCRIPTION     
            "This object specifies the Netscore Threshold name"
    ::= { sonusNetscoreMIBNotificationsObjects 5 }

sonusNetscoreAlarmDetails OBJECT-TYPE
    SYNTAX          DisplayString (SIZE(0..255))
    ACCESS          read-only
    STATUS          mandatory
    DESCRIPTION     
            "This object specifies the Netscore Threshold name"
    ::= { sonusNetscoreMIBNotificationsObjects 6 }

-- sonusNetscoreDiskUsageThresholdValue OBJECT-TYPE
--     SYNTAX          Counter64
--     ACCESS          read-only
--     STATUS          mandatory
--     DESCRIPTION     
--             "Disk Usage Threshold trigger value."
--     ::= { sonusNetscoreMIBNotificationsObjects 7 }

-- sonusNetscoreDiskUsageActualValue OBJECT-TYPE
--     SYNTAX          Counter64
--     ACCESS          read-only
--     STATUS          mandatory
--     DESCRIPTION     
--             "Disk Usage actual value."
--     ::= { sonusNetscoreMIBNotificationsObjects 8 }

sonusNetscoreDiskName OBJECT-TYPE
    SYNTAX          DisplayString
    ACCESS          read-only
    STATUS          mandatory
    DESCRIPTION     
            "Disk name."
    ::= { sonusNetscoreMIBNotificationsObjects 9 }

sonusNetscoreThresholdNotification TRAP-TYPE
    ENTERPRISE      sonusNetscoreMIBNotifications
    VARIABLES       { sonusEventTime, sonusEventClass, sonusEventLevel, 
                      sonusEventDescription, sonusNetscoreServerName, 
                      sonusNetscoreAlarmId, 
                      sonusNetscoreNotificationSetClearStatus, 
                      sonusNetscoreThresholdName, 
                      sonusNetscoreTargetName, sonusNetscoreAlarmDetails }
--     STATUS          mandatory
    DESCRIPTION     
            "This trap is sent when a Netscore Theshold event occurs"
    ::= 1

sonusNetscoreOverloadNotification TRAP-TYPE
    ENTERPRISE      sonusNetscoreMIBNotifications
    VARIABLES       { sonusEventTime, sonusEventClass, sonusEventLevel, 
                      sonusEventDescription, sonusNetscoreServerName, 
                      sonusNetscoreAlarmId, 
                      sonusNetscoreNotificationSetClearStatus, 
                      sonusNetscoreAlarmDetails }
--     STATUS          mandatory
    DESCRIPTION     
            "This trap is sent when a Netscore Overload event occurs"
    ::= 2

sonusNetscoreDiskUsageNotification TRAP-TYPE
    ENTERPRISE      sonusNetscoreMIBNotifications
    VARIABLES       { sonusEventTime, sonusEventClass, sonusEventLevel, 
                      sonusEventDescription, sonusNetscoreServerName, 
                      sonusNetscoreAlarmId, 
                      sonusNetscoreNotificationSetClearStatus, 
                      sonusNetscoreDiskName, 
                      sonusNetscoreDiskUsageThresholdValue, 
                      sonusNetscoreDiskUsageActualValue, 
                      sonusNetscoreAlarmDetails }
--     STATUS          mandatory
    DESCRIPTION     
            "This trap is sent when disk usage goes over a predefined threshold value."
    ::= 3

END -- end of module SONUS-NETSCORE-MIB.
