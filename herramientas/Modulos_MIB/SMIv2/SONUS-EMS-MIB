--
-- This SMIv2 module has been generated by smidump 0.2-cvs. Do not edit.
--

SONUS-EMS-MIB DEFINITIONS ::= BEGIN

IMPORTS
    InetAddress, InetAddressType
        FROM INET-ADDRESS-MIB
    sysName, sysObjectID
        FROM SNMPv2-MIB
    Integer32, IpAddress, MODULE-IDENTITY, NOTIFICATION-TYPE, 
    OBJECT-TYPE, Unsigned32
        FROM SNMPv2-SMI
    DisplayString
        FROM SNMPv2-TC
    sonusEventClass, sonusEventDescription, sonusEventLevel, 
    sonusEventTime, sonusSequenceId
        FROM SONUS-COMMON-MIB
    sonusHostID
        FROM SONUS-HOST-MIB
    sonusSystemMIBs
        FROM SONUS-SMI;

sonusEmsMIB MODULE-IDENTITY
    LAST-UPDATED    "201604220000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for EMS related objects."
    ::= { sonusSystemMIBs 7 }


sonusEmsMIBObjects OBJECT IDENTIFIER
    ::= { sonusEmsMIB 1 }

sonusEmsNotifications OBJECT IDENTIFIER
    ::= { sonusEmsMIB 2 }

sonusEmsNotificationsNewPrefix OBJECT IDENTIFIER
    ::= { sonusEmsNotifications 0 }

sonusEmsNotificationsPrefix OBJECT IDENTIFIER
    ::= { sonusEmsNotifications 1 }

sonusEmsNotificationsObjects OBJECT IDENTIFIER
    ::= { sonusEmsNotifications 2 }

sonusEmsThresholdObjects OBJECT IDENTIFIER
    ::= { sonusEmsNotificationsObjects 1 }

sonusEmsThresholdObjectId OBJECT-TYPE
    SYNTAX          OBJECT IDENTIFIER
    MAX-ACCESS      read-only
    STATUS          current
    DESCRIPTION     
            "The OID of the performance measure that was crossed."
    ::= { sonusEmsThresholdObjects 1 }

sonusEmsThresholdTriggerValue OBJECT-TYPE
    SYNTAX          Integer32
    MAX-ACCESS      read-only
    STATUS          current
    DESCRIPTION     
            "The threshold value that was crossed (the rising or
             falling value set for the threshold)."
    ::= { sonusEmsThresholdObjects 2 }

sonusEmsThresholdSampleValue OBJECT-TYPE
    SYNTAX          Integer32
    MAX-ACCESS      read-only
    STATUS          current
    DESCRIPTION     
            "The actual value measured that denotes that the
             threshold was crossed (should be greater than or
             equal to the rising trigger value or less than
             or equal to the falling trigger value)."
    ::= { sonusEmsThresholdObjects 3 }

sonusEmsThresholdIpAddress OBJECT-TYPE
    SYNTAX          IpAddress
    MAX-ACCESS      read-only
    STATUS          deprecated
    DESCRIPTION     
            "The IP address of the device on which the threshold was
             crossed."
    ::= { sonusEmsThresholdObjects 4 }

sonusEmsThresholdLocationIndexes OBJECT-TYPE
    SYNTAX          DisplayString
    MAX-ACCESS      read-only
    STATUS          current
    DESCRIPTION     
            "The indexes of the location within the device at which
             the threshold was crossed; may be shelf, slot number,
              interface number, trunk group number, etc, depending on
              where the threshold event occurred."
    ::= { sonusEmsThresholdObjects 5 }

sonusEmsThresholdIdentifier OBJECT-TYPE
    SYNTAX          DisplayString
    MAX-ACCESS      read-only
    STATUS          current
    DESCRIPTION     
            "A key that uniquely indentifies this threshold for
             managing duplicate alarms and clearing (matching
             the falling notification with the rising)."
    ::= { sonusEmsThresholdObjects 6 }

sonusEmsV2ThresholdIpAddressType OBJECT-TYPE
    SYNTAX          InetAddressType
    MAX-ACCESS      read-only
    STATUS          current
    DESCRIPTION     
            "The address type of sonusEmsV2ThresholdIpAddress."
    ::= { sonusEmsThresholdObjects 7 }

sonusEmsV2ThresholdIpAddress OBJECT-TYPE
    SYNTAX          InetAddress
    MAX-ACCESS      read-only
    STATUS          current
    DESCRIPTION     
            "The IP address of the device on which the threshold was
             crossed. The type of this address is determined by the 
             value of sonusEmsV2ThresholdIpAddressType."
    ::= { sonusEmsThresholdObjects 8 }

sonusEmsReachabilityObjects OBJECT IDENTIFIER
    ::= { sonusEmsNotificationsObjects 2 }

sonusEmsNodeIpAddress OBJECT-TYPE
    SYNTAX          IpAddress
    MAX-ACCESS      read-only
    STATUS          deprecated
    DESCRIPTION     
            "The IP address of the node that was polled."
    ::= { sonusEmsReachabilityObjects 1 }

sonusEmsNodeId OBJECT-TYPE
    SYNTAX          DisplayString
    MAX-ACCESS      read-only
    STATUS          current
    DESCRIPTION     
            "The internal ID of the node that was polled."
    ::= { sonusEmsReachabilityObjects 2 }

sonusEmsV2NodeIpAddressType OBJECT-TYPE
    SYNTAX          InetAddressType
    MAX-ACCESS      read-only
    STATUS          current
    DESCRIPTION     
            "The address type of sonusEmsV2NodeIpAddress."
    ::= { sonusEmsReachabilityObjects 3 }

sonusEmsV2NodeIpAddress OBJECT-TYPE
    SYNTAX          InetAddress
    MAX-ACCESS      read-only
    STATUS          current
    DESCRIPTION     
            "The IP address of the node that was polled. The type
             of this address is determined by the value of
              sonusEmsV2NodeIpAddressType."
    ::= { sonusEmsReachabilityObjects 4 }

sonusEmsProfileName OBJECT-TYPE
    SYNTAX          DisplayString
    MAX-ACCESS      read-only
    STATUS          current
    DESCRIPTION     
            "Profile Name for Performance Collection"
    ::= { sonusEmsReachabilityObjects 5 }

sonusEmsForwardingObjects OBJECT IDENTIFIER
    ::= { sonusEmsNotificationsObjects 4 }

sonusEmsTrapOriginator OBJECT-TYPE
    SYNTAX          IpAddress
    MAX-ACCESS      read-only
    STATUS          deprecated
    DESCRIPTION     
            "The IP address of the node that originated the trap."
    ::= { sonusEmsForwardingObjects 1 }

sonusEmsTrapForwardCounter64 OBJECT-TYPE
    SYNTAX          OCTET STRING (SIZE(1..128))
    MAX-ACCESS      read-only
    STATUS          current
    DESCRIPTION     
            "Internal use only. Specifies a 64 bit counter oid and value in the format oid:value ."
    ::= { sonusEmsForwardingObjects 2 }

sonusEmsV2TrapOriginatorType OBJECT-TYPE
    SYNTAX          InetAddressType
    MAX-ACCESS      read-only
    STATUS          current
    DESCRIPTION     
            "The address type of sonusEmsV2TrapOriginator."
    ::= { sonusEmsForwardingObjects 3 }

sonusEmsV2TrapOriginator OBJECT-TYPE
    SYNTAX          InetAddress
    MAX-ACCESS      read-only
    STATUS          current
    DESCRIPTION     
            "The IP address of the node that originated the trap.
             The type of this address is determined by the value of
              sonusEmsV2TrapOriginatorType."
    ::= { sonusEmsForwardingObjects 4 }

sonusDeviceHostName OBJECT-TYPE
    SYNTAX          DisplayString
    MAX-ACCESS      read-only
    STATUS          current
    DESCRIPTION     
            "Hostname/device Id of the device."
    ::= { sonusEmsForwardingObjects 5 }

sonusEmsFmObjects OBJECT IDENTIFIER
    ::= { sonusEmsNotificationsObjects 5 }

sonusEmsFmSequenceId OBJECT-TYPE
    SYNTAX          Unsigned32
    MAX-ACCESS      read-only
    STATUS          current
    DESCRIPTION     
            "The sequence number expected as the next in the series."
    ::= { sonusEmsFmObjects 1 }

sonusEmsFmSequenceEndGapId OBJECT-TYPE
    SYNTAX          Unsigned32
    MAX-ACCESS      read-only
    STATUS          current
    DESCRIPTION     
            "The last sequence number in a sequence gap."
    ::= { sonusEmsFmObjects 2 }

sonusEmsFmSequenceResetId OBJECT-TYPE
    SYNTAX          Unsigned32
    MAX-ACCESS      read-only
    STATUS          current
    DESCRIPTION     
            "The value to which the expected sequence number was reset."
    ::= { sonusEmsFmObjects 3 }

sonusEmsFmTrapFwdProfileName OBJECT-TYPE
    SYNTAX          DisplayString
    MAX-ACCESS      read-only
    STATUS          current
    DESCRIPTION     
            "Name of the FM Trap Forwarder Profile for which queue overflowed."
    ::= { sonusEmsFmObjects 4 }

sonusEmsFmTrapReSyncDelimiter OBJECT-TYPE
    SYNTAX          INTEGER { start(1), stop(2) }
    MAX-ACCESS      read-only
    STATUS          current
    DESCRIPTION     
            "Represents delimiter used while OSS trap re-sync."
    ::= { sonusEmsFmObjects 5 }

sonusEmsFmEnableOSSTrapReSync OBJECT-TYPE
    SYNTAX          INTEGER { enable(1) }
    MAX-ACCESS      read-write
    STATUS          current
    DESCRIPTION     
            "Enables Trap re-sync for OSS."
    ::= { sonusEmsFmObjects 6 }

sonusEmsPMObjects OBJECT IDENTIFIER
    ::= { sonusEmsNotificationsObjects 6 }

sonusEmsPMStatsNames OBJECT-TYPE
    SYNTAX          DisplayString
    MAX-ACCESS      read-only
    STATUS          current
    DESCRIPTION     
            "Comma-separated names of relevant PM stats (e.g. SystemStats,CallCountStats)"
    ::= { sonusEmsPMObjects 1 }

sonusEmsPMExportCsvFile OBJECT-TYPE
    SYNTAX          DisplayString
    MAX-ACCESS      read-only
    STATUS          current
    DESCRIPTION     
            "Directory name and file name of the PM export CSV file which did not have any data."
    ::= { sonusEmsPMObjects 2 }

sonusRemoteServer OBJECT-TYPE
    SYNTAX          DisplayString
    MAX-ACCESS      read-only
    STATUS          current
    DESCRIPTION     
            "Remote server where SFTP of stats needs to be performed."
    ::= { sonusEmsPMObjects 3 }

sonusEmsFileRepObjects OBJECT IDENTIFIER
    ::= { sonusEmsNotificationsObjects 7 }

sonusFileRepNotifyPID OBJECT-TYPE
    SYNTAX          Integer32
    MAX-ACCESS      read-only
    STATUS          current
    DESCRIPTION     
            "The process id of the process to be notified."
    ::= { sonusEmsFileRepObjects 1 }

sonusFileRepFilename OBJECT-TYPE
    SYNTAX          DisplayString
    MAX-ACCESS      read-only
    STATUS          current
    DESCRIPTION     
            "The name of the file which failed replication."
    ::= { sonusEmsFileRepObjects 2 }

sonusEmsLoginObjects OBJECT IDENTIFIER
    ::= { sonusEmsNotificationsObjects 8 }

sonusEmsLoginIPAddress OBJECT-TYPE
    SYNTAX          IpAddress
    MAX-ACCESS      read-only
    STATUS          deprecated
    DESCRIPTION     
            "The IP address of the node from which a login attempt was made."
    ::= { sonusEmsLoginObjects 1 }

sonusEmsLoginUserName OBJECT-TYPE
    SYNTAX          OCTET STRING (SIZE(1..20))
    MAX-ACCESS      read-only
    STATUS          current
    DESCRIPTION     
            "The user name provided during a login attempt."
    ::= { sonusEmsLoginObjects 2 }

sonusEmsV2LoginIPAddressType OBJECT-TYPE
    SYNTAX          InetAddressType
    MAX-ACCESS      read-only
    STATUS          current
    DESCRIPTION     
            "The address type of sonusEmsV2LoginIPAddress."
    ::= { sonusEmsLoginObjects 3 }

sonusEmsV2LoginIPAddress OBJECT-TYPE
    SYNTAX          InetAddress
    MAX-ACCESS      read-only
    STATUS          current
    DESCRIPTION     
            "The IP address of the node from which a login attempt was 
             made. The type of this address is determined by the value of
              sonusEmsV2LoginIPAddressType."
    ::= { sonusEmsLoginObjects 4 }

sonusEmsASXColdStandByAutomationObjects OBJECT IDENTIFIER
    ::= { sonusEmsNotificationsObjects 9 }

sonusEmsASXColdStandByAutomationASXRedundancyMode OBJECT-TYPE
    SYNTAX          INTEGER { primary(1), backup(2) }
    MAX-ACCESS      read-only
    STATUS          current
    DESCRIPTION     
            "ASX redundancy mode."
    ::= { sonusEmsASXColdStandByAutomationObjects 1 }

sonusEmsASXColdStandByAutomationConfigGRStateFailedInfo OBJECT-TYPE
    SYNTAX          DisplayString (SIZE(0..128))
    MAX-ACCESS      read-only
    STATUS          current
    DESCRIPTION     
            "Configuring GR operational status fail reason."
    ::= { sonusEmsASXColdStandByAutomationObjects 2 }

sonusEmsNPServicesObjects OBJECT IDENTIFIER
    ::= { sonusEmsNotificationsObjects 10 }

sonusEmsNPServicesMCHName OBJECT-TYPE
    SYNTAX          DisplayString (SIZE(0..128))
    MAX-ACCESS      read-only
    STATUS          current
    DESCRIPTION     
            "Name of the clearing house hosting Number Portability data."
    ::= { sonusEmsNPServicesObjects 1 }

sonusEmsNPServicesBulkRequestTransactionId OBJECT-TYPE
    SYNTAX          DisplayString (SIZE(0..256))
    MAX-ACCESS      read-only
    STATUS          current
    DESCRIPTION     
            "Transaction Id of bulk data file request."
    ::= { sonusEmsNPServicesObjects 2 }

sonusEmsSBCMgmtNotificationObjects OBJECT IDENTIFIER
    ::= { sonusEmsNotificationsObjects 11 }

scheduleId OBJECT-TYPE
    SYNTAX          DisplayString
    MAX-ACCESS      read-only
    STATUS          current
    DESCRIPTION     
            "The name of the file which failed replication."
    ::= { sonusEmsSBCMgmtNotificationObjects 1 }

scheduleName OBJECT-TYPE
    SYNTAX          DisplayString
    MAX-ACCESS      read-only
    STATUS          current
    DESCRIPTION     
            "The name of the file which failed replication."
    ::= { sonusEmsSBCMgmtNotificationObjects 2 }

failedNodes OBJECT-TYPE
    SYNTAX          DisplayString
    MAX-ACCESS      read-only
    STATUS          current
    DESCRIPTION     
            "The name of the file which failed replication."
    ::= { sonusEmsSBCMgmtNotificationObjects 3 }

sonusEmsClusterMgmtNotificationObjects OBJECT IDENTIFIER
    ::= { sonusEmsNotificationsObjects 12 }

nodename OBJECT-TYPE
    SYNTAX          DisplayString
    MAX-ACCESS      read-only
    STATUS          current
    DESCRIPTION     
            "The name of the Node."
    ::= { sonusEmsClusterMgmtNotificationObjects 1 }

nodeip OBJECT-TYPE
    SYNTAX          DisplayString
    MAX-ACCESS      read-only
    STATUS          current
    DESCRIPTION     
            "It represents Node IP value."
    ::= { sonusEmsClusterMgmtNotificationObjects 2 }

clustername OBJECT-TYPE
    SYNTAX          DisplayString
    MAX-ACCESS      read-only
    STATUS          current
    DESCRIPTION     
            "The name of the cluster."
    ::= { sonusEmsClusterMgmtNotificationObjects 3 }

reason OBJECT-TYPE
    SYNTAX          DisplayString
    MAX-ACCESS      read-only
    STATUS          current
    DESCRIPTION     
            "Describes notification reason "
    ::= { sonusEmsClusterMgmtNotificationObjects 4 }

clusterid OBJECT-TYPE
    SYNTAX          DisplayString
    MAX-ACCESS      read-only
    STATUS          current
    DESCRIPTION     
            "The id of the cluster"
    ::= { sonusEmsClusterMgmtNotificationObjects 5 }

sonusEmsLINotificationObjects OBJECT IDENTIFIER
    ::= { sonusEmsNotificationsObjects 13 }

mediationServerIP OBJECT-TYPE
    SYNTAX          DisplayString
    MAX-ACCESS      read-only
    STATUS          current
    DESCRIPTION     
            "IP Address of the mediation server"
    ::= { sonusEmsLINotificationObjects 1 }

sonusEmsVnfrMgmtNotificationObjects OBJECT IDENTIFIER
    ::= { sonusEmsNotificationsObjects 14 }

vnfmIp OBJECT-TYPE
    SYNTAX          DisplayString
    MAX-ACCESS      read-only
    STATUS          current
    DESCRIPTION     
            "It represents VNFM IP value."
    ::= { sonusEmsVnfrMgmtNotificationObjects 1 }

restResponseCode OBJECT-TYPE
    SYNTAX          DisplayString
    MAX-ACCESS      read-only
    STATUS          current
    DESCRIPTION     
            "It represents response code return from VNFM when tried to register."
    ::= { sonusEmsVnfrMgmtNotificationObjects 2 }

lastHeartbeatTime OBJECT-TYPE
    SYNTAX          DisplayString
    MAX-ACCESS      read-only
    STATUS          current
    DESCRIPTION     
            "It represents last Heartbeat received from VNFM"
    ::= { sonusEmsVnfrMgmtNotificationObjects 3 }

sonusEmsFileRepNotifyFailNotification NOTIFICATION-TYPE
    OBJECTS         { sonusEventTime, sonusEventDescription, 
                      sonusEventClass, sonusEventLevel, sonusHostID, 
                      sonusFileRepNotifyPID }
    STATUS          current
    DESCRIPTION     
            "The EMS file replication service has failed to notify the fault manager process. The process id to which notification was attempted is specified by sonusFileRepNotifyPID."
    ::= { sonusEmsNotificationsNewPrefix 31 }

sonusEmsFileRepSourceCopyFailNotification NOTIFICATION-TYPE
    OBJECTS         { sonusEventTime, sonusEventDescription, 
                      sonusEventClass, sonusEventLevel, sonusHostID, 
                      sonusFileRepFilename }
    STATUS          current
    DESCRIPTION     
            "The EMS file replication service has failed to copy the file specified by sonusFileRepFileName from the source to the target."
    ::= { sonusEmsNotificationsNewPrefix 32 }

sonusEmsFileRepTargetCopyFailNotification NOTIFICATION-TYPE
    OBJECTS         { sonusEventTime, sonusEventDescription, 
                      sonusEventClass, sonusEventLevel, sonusHostID, 
                      sonusFileRepFilename }
    STATUS          current
    DESCRIPTION     
            "The EMS file replication service has failed to copy a replicated file specified by sonusRepFileName from a temporary directory to a permanent directory."
    ::= { sonusEmsNotificationsNewPrefix 33 }

sonusEmsLoginFailureNotification NOTIFICATION-TYPE
    OBJECTS         { sonusEventTime, sonusEventDescription, 
                      sonusEventClass, sonusEventLevel, 
                      sonusEmsLoginIPAddress, sonusEmsLoginUserName }
    STATUS          deprecated
    DESCRIPTION     
            "Specifies that a login attempt failed for the user specified by sonusEmsLoginUserName from host specified by sonusEmsLoginIPAddress."
    ::= { sonusEmsNotificationsNewPrefix 34 }

sonusEmsFMTrapFwdProfileReadErrorNotification NOTIFICATION-TYPE
    OBJECTS         { sysName, sysObjectID, sonusEventTime, 
                      sonusEventDescription, sonusEventClass, 
                      sonusEventLevel }
    STATUS          current
    DESCRIPTION     
            "There was an error reading FM Trap Forwarder profiles. Possible causes include problem connecting to database, incorrect database password etc."
    ::= { sonusEmsNotificationsNewPrefix 35 }

sonusEmsFMTrapFwdWOQueueOverflowNotification NOTIFICATION-TYPE
    OBJECTS         { sysName, sysObjectID, sonusEventTime, 
                      sonusEventDescription, sonusEventClass, 
                      sonusEventLevel, sonusEmsFmTrapFwdProfileName }
    STATUS          current
    DESCRIPTION     
            "FM Trap Forwarder incoming work order trap queue has overflown for the specified profile, based on the configured tolerance."
    ::= { sonusEmsNotificationsNewPrefix 36 }

sonusEmsFMTrapFwdBrassAgtQueueOverflowNotification NOTIFICATION-TYPE
    OBJECTS         { sysName, sysObjectID, sonusEventTime, 
                      sonusEventDescription, sonusEventClass, 
                      sonusEventLevel }
    STATUS          current
    DESCRIPTION     
            "Brass Agent queue overflow warnings in emsSNMP.log."
    ::= { sonusEmsNotificationsNewPrefix 37 }

sonusEmsFMTrapFwdLogOutOfMemoryNotification NOTIFICATION-TYPE
    OBJECTS         { sysName, sysObjectID, sonusEventTime, 
                      sonusEventDescription, sonusEventClass, 
                      sonusEventLevel }
    STATUS          current
    DESCRIPTION     
            "Java out of memory warnings in emsFM.log."
    ::= { sonusEmsNotificationsNewPrefix 38 }

sonusEmsPrimRadiusAuthServerUnreachableNotification NOTIFICATION-TYPE
    OBJECTS         { sysName, sysObjectID, sonusEventTime, 
                      sonusEventDescription, sonusEventClass, 
                      sonusEventLevel }
    STATUS          current
    DESCRIPTION     
            "Specifies that the primary radius authentication server was unreachable when attempting to authenticate using the user specified by sonusEmsLoginUserName from the host specified by sonusEmsLoginIPAddress."
    ::= { sonusEmsNotificationsNewPrefix 41 }

sonusEmsPrimRadiusAuthServerReachableNotification NOTIFICATION-TYPE
    OBJECTS         { sysName, sysObjectID, sonusEventTime, 
                      sonusEventDescription, sonusEventClass, 
                      sonusEventLevel }
    STATUS          current
    DESCRIPTION     
            "Specifies that the primary radius authentication server was reachable when attempting to authenticate using the user specified by sonusEmsLoginUserName from the host specified by sonusEmsLoginIPAddress."
    ::= { sonusEmsNotificationsNewPrefix 42 }

sonusEmsPrimAndSecRadiusAuthServerUnreachableNotification NOTIFICATION-TYPE
    OBJECTS         { sysName, sysObjectID, sonusEventTime, 
                      sonusEventDescription, sonusEventClass, 
                      sonusEventLevel }
    STATUS          current
    DESCRIPTION     
            "Specifies that the primary and secondary radius authentication servers were unreachable when attempting to authenticate using the user specified by sonusEmsLoginUserName from the host specified by sonusEmsLoginIPAddress."
    ::= { sonusEmsNotificationsNewPrefix 43 }

sonusEmsPrimAndSecRadiusAuthServerReachableNotification NOTIFICATION-TYPE
    OBJECTS         { sysName, sysObjectID, sonusEventTime, 
                      sonusEventDescription, sonusEventClass, 
                      sonusEventLevel }
    STATUS          current
    DESCRIPTION     
            "Specifies that the primary and secondary radius authentication servers were reachable when attempting to authenticate using the user specified by sonusEmsLoginUserName from the host specified by sonusEmsLoginIPAddress."
    ::= { sonusEmsNotificationsNewPrefix 44 }

sonusEmsPrimRadiusAccServerUnreachableNotification NOTIFICATION-TYPE
    OBJECTS         { sysName, sysObjectID, sonusEventTime, 
                      sonusEventDescription, sonusEventClass, 
                      sonusEventLevel }
    STATUS          current
    DESCRIPTION     
            "Specifies that the primary radius accounting server was unreachable when attempting to authenticate using the user specified by sonusEmsLoginUserName from the host specified by sonusEmsLoginIPAddress."
    ::= { sonusEmsNotificationsNewPrefix 45 }

sonusEmsPrimRadiusAccServerReachableNotification NOTIFICATION-TYPE
    OBJECTS         { sysName, sysObjectID, sonusEventTime, 
                      sonusEventDescription, sonusEventClass, 
                      sonusEventLevel }
    STATUS          current
    DESCRIPTION     
            "Specifies that the primary radius accounting server was reachable when attempting to authenticate using the user specified by sonusEmsLoginUserName from the host specified by sonusEmsLoginIPAddress."
    ::= { sonusEmsNotificationsNewPrefix 46 }

sonusEmsPrimAndSecRadiusAccServerUnreachableNotification NOTIFICATION-TYPE
    OBJECTS         { sysName, sysObjectID, sonusEventTime, 
                      sonusEventDescription, sonusEventClass, 
                      sonusEventLevel }
    STATUS          current
    DESCRIPTION     
            "Specifies that the primary and secondary radius accounting servers were unreachable when attempting to authenticate using the user specified by sonusEmsLoginUserName from the host specified by sonusEmsLoginIPAddress."
    ::= { sonusEmsNotificationsNewPrefix 47 }

sonusEmsPrimAndSecRadiusAccServerReachableNotification NOTIFICATION-TYPE
    OBJECTS         { sysName, sysObjectID, sonusEventTime, 
                      sonusEventDescription, sonusEventClass, 
                      sonusEventLevel }
    STATUS          current
    DESCRIPTION     
            "Specifies that the primary and secondary radius accounting servers were reachable when attempting to authenticate using the user specified by sonusEmsLoginUserName from the host specified by sonusEmsLoginIPAddress."
    ::= { sonusEmsNotificationsNewPrefix 48 }

sonusEmsASXGROperationalStateChangeFailureNotification NOTIFICATION-TYPE
    OBJECTS         { sonusEventTime, sonusEventDescription, 
                      sonusEventClass, sonusEventLevel, sonusHostID, 
                      sonusEmsNodeId, 
                      sonusEmsASXColdStandByAutomationASXRedundancyMode, 
                      sonusEmsASXColdStandByAutomationConfigGRStateFailedInfo }
    STATUS          current
    DESCRIPTION     
            "EMS fails to set GR operational state against a Home ASX."
    ::= { sonusEmsNotificationsNewPrefix 49 }

sonusEmsASXGROperationalStateChangeSuccessNotification NOTIFICATION-TYPE
    OBJECTS         { sonusEventTime, sonusEventDescription, 
                      sonusEventClass, sonusEventLevel, sonusHostID, 
                      sonusEmsNodeId, 
                      sonusEmsASXColdStandByAutomationASXRedundancyMode }
    STATUS          current
    DESCRIPTION     
            "EMS succeeds to set GR operational status against a Home ASX."
    ::= { sonusEmsNotificationsNewPrefix 50 }

sonusEmsV2RisingEventNotification NOTIFICATION-TYPE
    OBJECTS         { sysName, sysObjectID, sonusEventTime, 
                      sonusEventDescription, sonusEventClass, 
                      sonusEventLevel, sonusEmsV2ThresholdIpAddressType, 
                      sonusEmsV2ThresholdIpAddress, 
                      sonusEmsThresholdObjectId, 
                      sonusEmsThresholdTriggerValue, 
                      sonusEmsThresholdSampleValue, 
                      sonusEmsThresholdLocationIndexes, 
                      sonusEmsThresholdIdentifier }
    STATUS          current
    DESCRIPTION     
            "A rising event notification informs that a given
             performance measure has crossed a given threshold
             - it has risen above a defined rising threshold
             value."
    ::= { sonusEmsNotificationsNewPrefix 51 }

sonusEmsV2FallingEventNotification NOTIFICATION-TYPE
    OBJECTS         { sysName, sysObjectID, sonusEventTime, 
                      sonusEventDescription, sonusEventClass, 
                      sonusEventLevel, sonusEmsV2ThresholdIpAddressType, 
                      sonusEmsV2ThresholdIpAddress, 
                      sonusEmsThresholdObjectId, 
                      sonusEmsThresholdTriggerValue, 
                      sonusEmsThresholdSampleValue, 
                      sonusEmsThresholdLocationIndexes, 
                      sonusEmsThresholdIdentifier }
    STATUS          current
    DESCRIPTION     
            "A falling event notification informs that a given
             performance measure for which a previous rising event
             notification was generated has returned below a defined
             falling value for that threshold and should be cleared."
    ::= { sonusEmsNotificationsNewPrefix 52 }

sonusEmsV2NodeUnreachableNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified node is not reachable by the EMS."
    ::= { sonusEmsNotificationsNewPrefix 53 }

sonusEmsV2NodeReachableNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified node is now reachable by the EMS."
    ::= { sonusEmsNotificationsNewPrefix 54 }

sonusEmsV2NodeRestartedNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified node has been restarted since last polled by the EMS."
    ::= { sonusEmsNotificationsNewPrefix 55 }

sonusEmsV2NodeCfgFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "EMS failed to configure the specified node."
    ::= { sonusEmsNotificationsNewPrefix 56 }

sonusEmsV2NodeCfgDoneNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Successfully configured the specified node."
    ::= { sonusEmsNotificationsNewPrefix 57 }

sonusEmsV2FmSequenceGapNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusEmsFmSequenceId, sonusEmsFmSequenceEndGapId }
    STATUS          current
    DESCRIPTION     
            "The fm manager has observed a sequence gap in INFORM traps from the device."
    ::= { sonusEmsNotificationsNewPrefix 58 }

sonusEmsV2FmSequenceResetNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusEmsFmSequenceId, sonusEmsFmSequenceResetId }
    STATUS          current
    DESCRIPTION     
            "The fm manager has observed a situation which caused it to rest the expected sequence number.  This can be due to a agent reset or reboot."
    ::= { sonusEmsNotificationsNewPrefix 59 }

sonusEmsV2FmSequenceQOverflowNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusEmsFmSequenceId }
    STATUS          current
    DESCRIPTION     
            "The queue used by sequence handling code has overflowed. This may cause traps to be handled out of order."
    ::= { sonusEmsNotificationsNewPrefix 60 }

sonusEmsV2NodeCfgPartialNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Partially configured the specified node.  One of the hosts of a redundant configuration was not successfully configured."
    ::= { sonusEmsNotificationsNewPrefix 61 }

sonusEmsV2HostCfgSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The host identified by sonusHostID was configured successfully."
    ::= { sonusEmsNotificationsNewPrefix 62 }

sonusEmsV2HostCfgFailureNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The host identified by sonusHostID was not configured successfully."
    ::= { sonusEmsNotificationsNewPrefix 63 }

sonusV2VfyMgrNodeTypeFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID does not contain the instrumentation component needed to manage the registered node."
    ::= { sonusEmsNotificationsNewPrefix 64 }

sonusV2VfyMgrNodeTypeSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID contains the instrumentation component needed to manage the registered node."
    ::= { sonusEmsNotificationsNewPrefix 65 }

sonusV2VfyMgrApplVersionFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID reports a different application version than that contained in the EMS node model. The application version is that of the instrumented device. For example PSX or SGX."
    ::= { sonusEmsNotificationsNewPrefix 66 }

sonusV2VfyMgrApplVersionSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID reports the same application version as that contained in the EMS node model. The application version is that of the instrumented device. For example PSX or SGX."
    ::= { sonusEmsNotificationsNewPrefix 67 }

sonusV2VfyMgrMgmtClientFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID does not contain a fault subscription entry for the EMS."
    ::= { sonusEmsNotificationsNewPrefix 68 }

sonusV2VfyMgrMgmtClientSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID contains a fault subscription entry for the EMS."
    ::= { sonusEmsNotificationsNewPrefix 69 }

sonusV2VfyMgrSnmpAccessFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID does not allow SNMP Read access priviledge for Insight."
    ::= { sonusEmsNotificationsNewPrefix 70 }

sonusV2VfyMgrSnmpAccessSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID allows SNMP Read access priviledge for Insight."
    ::= { sonusEmsNotificationsNewPrefix 71 }

sonusV2VfyMgrAgentVersionFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID reports a different version than that stored in the EMS."
    ::= { sonusEmsNotificationsNewPrefix 72 }

sonusV2VfyMgrAgentVersionSuccessNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusHostID }
    STATUS          current
    DESCRIPTION     
            "The agent on the host identified by sonusHostID reports the same version as that stored in the EMS."
    ::= { sonusEmsNotificationsNewPrefix 73 }

sonusEmsV2HostUnreachableNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified host is not reachable by the EMS."
    ::= { sonusEmsNotificationsNewPrefix 74 }

sonusEmsV2HostReachableNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified host is now reachable by the EMS."
    ::= { sonusEmsNotificationsNewPrefix 75 }

sonusEmsV2HostRestartedNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "The specified host has been restarted since last polled by the EMS."
    ::= { sonusEmsNotificationsNewPrefix 76 }

sonusEmsV2PifCollectFailNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "EMS failed to complete PIF collection for the specified node."
    ::= { sonusEmsNotificationsNewPrefix 77 }

sonusEmsV2PifCollectDoneNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Successfully complete PIF collection for the specified node."
    ::= { sonusEmsNotificationsNewPrefix 78 }

sonusEmsV2PMCollectionTaskStopped NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "PM Collection task has stopped and PMWatchdog is restarting the task."
    ::= { sonusEmsNotificationsNewPrefix 79 }

sonusEmsV2PMExportWithNoData NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId, 
                      sonusEmsPMStatsNames, sonusEmsPMExportCsvFile }
    STATUS          current
    DESCRIPTION     
            "PM Exporter wrote the CSV file without any data (i.e with only header information)."
    ::= { sonusEmsNotificationsNewPrefix 80 }

sonusEmsV2LoginFailureNotification NOTIFICATION-TYPE
    OBJECTS         { sonusEventTime, sonusEventDescription, 
                      sonusEventClass, sonusEventLevel, 
                      sonusEmsV2LoginIPAddressType, 
                      sonusEmsV2LoginIPAddress, sonusEmsLoginUserName }
    STATUS          current
    DESCRIPTION     
            "Specifies that a login attempt failed for the user specified by sonusEmsLoginUserName from host specified by sonusEmsV2LoginIPAddress."
    ::= { sonusEmsNotificationsNewPrefix 81 }

sonusEmsLnpBddFileDownloadErrorNotification NOTIFICATION-TYPE
    OBJECTS         { sysName, sysObjectID, sonusEventTime, 
                      sonusEventDescription, sonusEventClass, 
                      sonusEventLevel, sonusEmsNodeId, sonusHostID }
    STATUS          current
    DESCRIPTION     
            "EMS was not able to download Bulk Data Download File."
    ::= { sonusEmsNotificationsNewPrefix 82 }

sonusEmsLnpBddFileDownloadCompletedNotification NOTIFICATION-TYPE
    OBJECTS         { sysName, sysObjectID, sonusEventTime, 
                      sonusEventDescription, sonusEventClass, 
                      sonusEventLevel, sonusEmsNodeId, sonusHostID }
    STATUS          current
    DESCRIPTION     
            "EMS downloaded Bulk Data Download File correctly and was able to obtain last transaction id."
    ::= { sonusEmsNotificationsNewPrefix 83 }

sonusEmsLnpDataSyncErrorNotification NOTIFICATION-TYPE
    OBJECTS         { sysName, sysObjectID, sonusEventTime, 
                      sonusEventDescription, sonusEventClass, 
                      sonusEventLevel, sonusEmsNodeId, sonusHostID }
    STATUS          current
    DESCRIPTION     
            "EMS/IAS was not able to sync LNP/MNP data between MCH server and PSX."
    ::= { sonusEmsNotificationsNewPrefix 84 }

sonusEmsNPBulkFileReadyNotification NOTIFICATION-TYPE
    OBJECTS         { sysName, sysObjectID, sonusEventTime, 
                      sonusEventDescription, sonusEventClass, 
                      sonusEventLevel, sonusEmsNodeId, sonusHostID, 
                      sonusEmsNPServicesMCHName, 
                      sonusEmsNPServicesBulkRequestTransactionId }
    STATUS          current
    DESCRIPTION     
            "MCH has generated the bulk file corresponding to request sent by EMS and is ready for download."
    ::= { sonusEmsNotificationsNewPrefix 85 }

sonusEmsNPBulkFileRequestRejectedNotification NOTIFICATION-TYPE
    OBJECTS         { sysName, sysObjectID, sonusEventTime, 
                      sonusEventDescription, sonusEventClass, 
                      sonusEventLevel, sonusEmsNodeId, sonusHostID, 
                      sonusEmsNPServicesMCHName, 
                      sonusEmsNPServicesBulkRequestTransactionId }
    STATUS          current
    DESCRIPTION     
            "MCH has rejected the bulk file generation request, check the request and resubmit. 
             Possible reasons include wrong time range, incorrect user credentials"
    ::= { sonusEmsNotificationsNewPrefix 86 }

sonusEmsNPBulkProvisioningCompletedNotification NOTIFICATION-TYPE
    OBJECTS         { sysName, sysObjectID, sonusEventTime, 
                      sonusEventDescription, sonusEventClass, 
                      sonusEventLevel, sonusEmsNodeId, sonusHostID, 
                      sonusEmsNPServicesMCHName, 
                      sonusEmsNPServicesBulkRequestTransactionId }
    STATUS          current
    DESCRIPTION     
            "Provisioning of Partial Bulk File is completed successfully."
    ::= { sonusEmsNotificationsNewPrefix 87 }

sonusEmsNPBulkProvisioningFailedNotification NOTIFICATION-TYPE
    OBJECTS         { sysName, sysObjectID, sonusEventTime, 
                      sonusEventDescription, sonusEventClass, 
                      sonusEventLevel, sonusEmsNodeId, sonusHostID, 
                      sonusEmsNPServicesMCHName, 
                      sonusEmsNPServicesBulkRequestTransactionId }
    STATUS          current
    DESCRIPTION     
            "Provisioning of Partial Bulk File failed."
    ::= { sonusEmsNotificationsNewPrefix 88 }

sonusEmsUpgradeJobFailedErrorNotification NOTIFICATION-TYPE
    OBJECTS         { sysName, sysObjectID, sonusEventTime, 
                      sonusEventDescription, sonusEventClass, 
                      sonusEventLevel, scheduleId, scheduleName, 
                      failedNodes }
    STATUS          current
    DESCRIPTION     
            "SBC management Upgrade schedule error notification"
    ::= { sonusEmsNotificationsNewPrefix 89 }

sonusEmsBackupJobFailedErrorNotification NOTIFICATION-TYPE
    OBJECTS         { sysName, sysObjectID, sonusEventTime, 
                      sonusEventDescription, sonusEventClass, 
                      sonusEventLevel, scheduleId, scheduleName, 
                      failedNodes }
    STATUS          current
    DESCRIPTION     
            "SBC management Backup schedule error notification"
    ::= { sonusEmsNotificationsNewPrefix 90 }

sonusEmsConfigurationJobFailedErrorNotification NOTIFICATION-TYPE
    OBJECTS         { sysName, sysObjectID, sonusEventTime, 
                      sonusEventDescription, sonusEventClass, 
                      sonusEventLevel, scheduleId, scheduleName, 
                      failedNodes }
    STATUS          current
    DESCRIPTION     
            "SBC management Configuration schedule error notification"
    ::= { sonusEmsNotificationsNewPrefix 91 }

sonusEmsRestoreFailedErrorNotification NOTIFICATION-TYPE
    OBJECTS         { sysName, sysObjectID, sonusEventTime, 
                      sonusEventDescription, sonusEventClass, 
                      failedNodes }
    STATUS          current
    DESCRIPTION     
            "SBC management Restore Operation error notification"
    ::= { sonusEmsNotificationsNewPrefix 92 }

sonusEmsV2PMStatsFileCollectionFailed NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Downloading of statistics file from device failed."
    ::= { sonusEmsNotificationsNewPrefix 93 }

sonusEmsPartialConfigurationJobFailedErrorNotification NOTIFICATION-TYPE
    OBJECTS         { sysName, sysObjectID, sonusEventTime, 
                      sonusEventDescription, sonusEventClass, 
                      sonusEventLevel, scheduleId, scheduleName, 
                      failedNodes }
    STATUS          current
    DESCRIPTION     
            "SBC management Partial Configuration schedule error notification"
    ::= { sonusEmsNotificationsNewPrefix 94 }

sonusEmsClusterNodeRegistrationRejectedNotification NOTIFICATION-TYPE
    OBJECTS         { sysName, sysObjectID, sonusEventTime, 
                      sonusEventDescription, sonusEventClass, nodename, 
                      nodeip, clustername }
    STATUS          current
    DESCRIPTION     
            "Cluster dynamic node registration rejected"
    ::= { sonusEmsNotificationsNewPrefix 95 }

sonusEmsClusterInstanceUpNotReceivedNotification NOTIFICATION-TYPE
    OBJECTS         { sysName, sysObjectID, sonusEventTime, 
                      sonusEventDescription, sonusEventClass, nodename, 
                      nodeip, clustername }
    STATUS          current
    DESCRIPTION     
            "Instanceup request never received for the node"
    ::= { sonusEmsNotificationsNewPrefix 96 }

sonusEmsClusterNodeIPIsInUseNotification NOTIFICATION-TYPE
    OBJECTS         { sysName, sysObjectID, sonusEventTime, 
                      sonusEventDescription, sonusEventClass, nodename, 
                      nodeip, clustername }
    STATUS          current
    DESCRIPTION     
            "EMS detecting another node is already registered with same IP"
    ::= { sonusEmsNotificationsNewPrefix 97 }

sonusEmsClusterConfigUpdateFailedNotification NOTIFICATION-TYPE
    OBJECTS         { sysName, sysObjectID, sonusEventTime, 
                      sonusEventDescription, sonusEventClass, nodename, 
                      nodeip, clustername }
    STATUS          current
    DESCRIPTION     
            "Configuration update failed for node"
    ::= { sonusEmsNotificationsNewPrefix 98 }

sonusEMSClusterNodeDeRegistrationNotification NOTIFICATION-TYPE
    OBJECTS         { sysName, sysObjectID, sonusEventTime, 
                      sonusEventDescription, sonusEventClass, nodename, 
                      nodeip, clustername, reason }
    STATUS          current
    DESCRIPTION     
            "Cluster dynamic node deregistration rejected"
    ::= { sonusEmsNotificationsNewPrefix 99 }

sonusEMSClusterNodePurgeNotification NOTIFICATION-TYPE
    OBJECTS         { sysName, sysObjectID, sonusEventTime, 
                      sonusEventDescription, sonusEventClass, nodename, 
                      nodeip, clustername, reason }
    STATUS          current
    DESCRIPTION     
            "Cluster dynamic node purge rejected"
    ::= { sonusEmsNotificationsNewPrefix 100 }

sonusEMSClusterNodeDiscoveryFailedNotification NOTIFICATION-TYPE
    OBJECTS         { sysName, sysObjectID, sonusEventTime, 
                      sonusEventDescription, sonusEventClass, nodename, 
                      nodeip, clustername, reason }
    STATUS          current
    DESCRIPTION     
            "Cluster dynamic node purge rejected"
    ::= { sonusEmsNotificationsNewPrefix 101 }

sonusEmsClusterNodeIPIsInUseUnRegisterNotification NOTIFICATION-TYPE
    OBJECTS         { sysName, sysObjectID, sonusEventTime, 
                      sonusEventDescription, sonusEventClass, nodename, 
                      nodeip, clustername, reason }
    STATUS          current
    DESCRIPTION     
            "Cluster node ip is in use got UnRegister"
    ::= { sonusEmsNotificationsNewPrefix 102 }

sonusEmsClusterBelowConfiguredNodeCountNotification NOTIFICATION-TYPE
    OBJECTS         { sysName, sysObjectID, sonusEventTime, 
                      sonusEventDescription, sonusEventClass, nodename, 
                      nodeip, clustername, clusterid }
    STATUS          current
    DESCRIPTION     
            "Number of nodes in the cluster is below the configured limit"
    ::= { sonusEmsNotificationsNewPrefix 103 }

sonusEmsClusterReachedConfiguredNodeCountNotification NOTIFICATION-TYPE
    OBJECTS         { sysName, sysObjectID, sonusEventTime, 
                      sonusEventDescription, sonusEventClass, nodename, 
                      nodeip, clustername, clusterid }
    STATUS          current
    DESCRIPTION     
            "Number of nodes in the cluster reached the minimum configured limit"
    ::= { sonusEmsNotificationsNewPrefix 104 }

sonusEmsPMProfileAssignmentFailedNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Warning indicating that PM Profile assignment onto device failed."
    ::= { sonusEmsNotificationsNewPrefix 105 }

sonusEmsPMPollSkipNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "It describes the event when a PM skips a poll for node"
    ::= { sonusEmsNotificationsNewPrefix 106 }

sonusEMSLIX1InterfaceDownNotification NOTIFICATION-TYPE
    OBJECTS         { sysName, sysObjectID, sonusEventTime, 
                      sonusEventDescription, sonusEventClass, 
                      mediationServerIP }
    STATUS          current
    DESCRIPTION     
            "X1 Interface Connection Terminated."
    ::= { sonusEmsNotificationsNewPrefix 107 }

sonusEMSLIX1InterfaceUpNotification NOTIFICATION-TYPE
    OBJECTS         { sysName, sysObjectID, sonusEventTime, 
                      sonusEventDescription, sonusEventClass, 
                      mediationServerIP }
    STATUS          current
    DESCRIPTION     
            "X1 Interface Connection Established."
    ::= { sonusEmsNotificationsNewPrefix 108 }

sonusEmsSANEServerUnreachableNotification NOTIFICATION-TYPE
    OBJECTS         { sysName, sysObjectID, sonusEventTime, 
                      sonusEventDescription, sonusEventClass, 
                      sonusEventLevel }
    STATUS          current
    DESCRIPTION     
            "The SANE server was unreachable when attempting to authenticate SANE user."
    ::= { sonusEmsNotificationsNewPrefix 109 }

sonusEmsPMBacklogExportNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "It describes the event when a PM backlog export  happens for  a  node."
    ::= { sonusEmsNotificationsNewPrefix 110 }

sonusEmsSANECertificateExpiryNotification NOTIFICATION-TYPE
    OBJECTS         { sysName, sysObjectID, sonusEventTime, 
                      sonusEventDescription, sonusEventClass, 
                      sonusEventLevel }
    STATUS          current
    DESCRIPTION     
            "It describes the SANE certificate expiry event."
    ::= { sonusEmsNotificationsNewPrefix 111 }

sonusEMSVnfrRegistrationFailedNotification NOTIFICATION-TYPE
    OBJECTS         { sysName, sonusEventTime, sonusEventDescription, 
                      sonusEventClass, sonusEventLevel, vnfmIp, 
                      restResponseCode }
    STATUS          current
    DESCRIPTION     
            "VNFR registration with VNFM failed"
    ::= { sonusEmsNotificationsNewPrefix 112 }

sonusEMSVnfrRegistrationSuccessNotification NOTIFICATION-TYPE
    OBJECTS         { sysName, sonusEventTime, sonusEventDescription, 
                      sonusEventClass, sonusEventLevel, vnfmIp, 
                      restResponseCode }
    STATUS          current
    DESCRIPTION     
            "VNFR successfully registered with VNFM after initial failure"
    ::= { sonusEmsNotificationsNewPrefix 113 }

sonusEMSVnfrHeartbeatDownNotification NOTIFICATION-TYPE
    OBJECTS         { sysName, sonusEventTime, sonusEventDescription, 
                      sonusEventClass, sonusEventLevel, vnfmIp, 
                      lastHeartbeatTime }
    STATUS          current
    DESCRIPTION     
            "VNFR has stopped receiving heartbeat messages from the VNFM"
    ::= { sonusEmsNotificationsNewPrefix 114 }

sonusEMSVnfrHeartbeatUpNotification NOTIFICATION-TYPE
    OBJECTS         { sysName, sonusEventTime, sonusEventDescription, 
                      sonusEventClass, sonusEventLevel, vnfmIp, 
                      lastHeartbeatTime }
    STATUS          current
    DESCRIPTION     
            "VNFR has started receiving heartbeat messages from the VNFM again"
    ::= { sonusEmsNotificationsNewPrefix 115 }

sonusEmsClusterConfigHeadendOutofsyncNotification NOTIFICATION-TYPE
    OBJECTS         { sysName, sysObjectID, sonusEventTime, 
                      sonusEventDescription, sonusEventClass, nodename, 
                      nodeip, clustername, clusterid }
    STATUS          current
    DESCRIPTION     
            "An SBC head end has been updating the cluster configuration for a longer than expected duration and not yet activated it"
    ::= { sonusEmsNotificationsNewPrefix 116 }

sonusEmsClusterConfigHeadendActivatedNotification NOTIFICATION-TYPE
    OBJECTS         { sysName, sysObjectID, sonusEventTime, 
                      sonusEventDescription, sonusEventClass, nodename, 
                      nodeip, clustername, clusterid }
    STATUS          current
    DESCRIPTION     
            "An SBC head end has updated and activated a cluster configuration"
    ::= { sonusEmsNotificationsNewPrefix 117 }

sonusEmsClusterInvalidNodeRegistrationNotification NOTIFICATION-TYPE
    OBJECTS         { sysName, sysObjectID, sonusEventTime, 
                      sonusEventDescription, sonusEventClass, nodename, 
                      nodeip, clustername, clusterid, reason }
    STATUS          current
    DESCRIPTION     
            "Invalid cluster node registration received"
    ::= { sonusEmsNotificationsNewPrefix 118 }

sonusEmsInsightDBConnectionPoolExhaustedNotification NOTIFICATION-TYPE
    OBJECTS         { sysName, sysObjectID, sonusEventTime, 
                      sonusEventDescription, sonusEventClass, 
                      sonusEventLevel }
    STATUS          current
    DESCRIPTION     
            "The Insight DB Connection pool is empty."
    ::= { sonusEmsNotificationsNewPrefix 119 }

sonusEmsPMProfileProfileAssignmentSuccessNotification NOTIFICATION-TYPE
    OBJECTS         { sysName, sysObjectID, sonusEventTime, 
                      sonusEventDescription, sonusEventClass, 
                      sonusEventLevel, sonusEmsProfileName }
    STATUS          current
    DESCRIPTION     
            "Indicating that PM Profile assignment succeeded."
    ::= { sonusEmsNotificationsNewPrefix 120 }

sonusEmsPMProfileProfileAssignmentFailedNotification NOTIFICATION-TYPE
    OBJECTS         { sysName, sysObjectID, sonusEventTime, 
                      sonusEventDescription, sonusEventClass, 
                      sonusEventLevel, sonusEmsProfileName }
    STATUS          current
    DESCRIPTION     
            "Warning indicating that PM Profile assignment failed."
    ::= { sonusEmsNotificationsNewPrefix 121 }

sonusEmsFingerprintChangeNotification NOTIFICATION-TYPE
    OBJECTS         { sysName, sysObjectID, sonusEventTime, 
                      sonusEventDescription, sonusEventClass, 
                      sonusEventLevel }
    STATUS          current
    DESCRIPTION     
            "Indicating that Fingerprint is changed on device side."
    ::= { sonusEmsNotificationsNewPrefix 122 }

sonusEmsFingerprintMismatchNotification NOTIFICATION-TYPE
    OBJECTS         { sysName, sysObjectID, sonusEventTime, 
                      sonusEventDescription, sonusEventClass, 
                      sonusEventLevel }
    STATUS          current
    DESCRIPTION     
            "Indicating that Fingerprint verification failed on the device."
    ::= { sonusEmsNotificationsNewPrefix 123 }

sonusEmsNodeSnmpV3SetFailedNotification NOTIFICATION-TYPE
    OBJECTS         { sysName, sysObjectID, sonusEventTime, 
                      sonusEventDescription, sonusEventClass, 
                      sonusEventLevel, sonusEmsV2NodeIpAddressType, 
                      sonusEmsV2NodeIpAddress, sonusEmsNodeId }
    STATUS          current
    DESCRIPTION     
            "Node SNMP trap setting is out sync with the config. Reset the config."
    ::= { sonusEmsNotificationsNewPrefix 124 }

sonusDBaasFileSystemUtilizationNotification NOTIFICATION-TYPE
    OBJECTS         { sonusHostID, sonusEventDescription, 
                      sonusEventClass, sonusEventLevel, sonusEventTime }
    STATUS          current
    DESCRIPTION     
            "Database file system utilization "
    ::= { sonusEmsNotificationsNewPrefix 125 }

sonusDBaasDownNotification NOTIFICATION-TYPE
    OBJECTS         { sonusHostID, sonusEventDescription, 
                      sonusEventClass, sonusEventLevel, sonusEventTime }
    STATUS          current
    DESCRIPTION     
            "Database is down "
    ::= { sonusEmsNotificationsNewPrefix 126 }

sonusDBaasStandbyLagNotification NOTIFICATION-TYPE
    OBJECTS         { sonusHostID, sonusEventDescription, 
                      sonusEventClass, sonusEventLevel, sonusEventTime }
    STATUS          current
    DESCRIPTION     
            "Standby node Lag "
    ::= { sonusEmsNotificationsNewPrefix 127 }

sonusDBaasStandbyInactiveNotification NOTIFICATION-TYPE
    OBJECTS         { sonusHostID, sonusEventDescription, 
                      sonusEventClass, sonusEventLevel, sonusEventTime }
    STATUS          current
    DESCRIPTION     
            "Standby node is inactive "
    ::= { sonusEmsNotificationsNewPrefix 128 }

sonusDBaasClearNotification NOTIFICATION-TYPE
    OBJECTS         { sonusHostID, sonusEventDescription, 
                      sonusEventClass, sonusEventLevel, sonusEventTime }
    STATUS          current
    DESCRIPTION     
            "Clear trap for DBaas notification "
    ::= { sonusEmsNotificationsNewPrefix 129 }

sonusEmsTrapReSyncDelimiterNotification NOTIFICATION-TYPE
    OBJECTS         { sonusEventDescription, sonusEventLevel, 
                      sonusEmsFmTrapReSyncDelimiter }
    STATUS          current
    DESCRIPTION     
            "Trap Re-sync delimiter notification."
    ::= { sonusEmsNotificationsNewPrefix 130 }

sonusEmsLDAPServerErrorNotification NOTIFICATION-TYPE
    OBJECTS         { sonusHostID, sonusEventDescription, 
                      sonusEventClass, sonusEventLevel, sonusEventTime }
    STATUS          current
    DESCRIPTION     
            "LDAP Server Error Notification"
    ::= { sonusEmsNotificationsNewPrefix 131 }

sonusEmsRisingEventNotification NOTIFICATION-TYPE
    OBJECTS         { sysName, sysObjectID, sonusEventTime, 
                      sonusEventDescription, sonusEventClass, 
                      sonusEventLevel, sonusEmsThresholdIpAddress, 
                      sonusEmsThresholdObjectId, 
                      sonusEmsThresholdTriggerValue, 
                      sonusEmsThresholdSampleValue, 
                      sonusEmsThresholdLocationIndexes, 
                      sonusEmsThresholdIdentifier }
    STATUS          deprecated
    DESCRIPTION     
            "A rising event notification informs that a given
             performance measure has crossed a given threshold
             - it has risen above a defined rising threshold
             value."
    ::= { sonusEmsNotificationsPrefix 1 }

sonusEmsFallingEventNotification NOTIFICATION-TYPE
    OBJECTS         { sysName, sysObjectID, sonusEventTime, 
                      sonusEventDescription, sonusEventClass, 
                      sonusEventLevel, sonusEmsThresholdIpAddress, 
                      sonusEmsThresholdObjectId, 
                      sonusEmsThresholdTriggerValue, 
                      sonusEmsThresholdSampleValue, 
                      sonusEmsThresholdLocationIndexes, 
                      sonusEmsThresholdIdentifier }
    STATUS          deprecated
    DESCRIPTION     
            "A falling event notification informs that a given
             performance measure for which a previous rising event
             notification was generated has returned below a defined
             falling value for that threshold and should be cleared."
    ::= { sonusEmsNotificationsPrefix 2 }

sonusEmsNodeUnreachableNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified node is not reachable by the EMS."
    ::= { sonusEmsNotificationsPrefix 3 }

sonusEmsNodeReachableNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified node is now reachable by the EMS."
    ::= { sonusEmsNotificationsPrefix 4 }

sonusEmsNodeRestartedNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified node has been restarted since last polled by the EMS."
    ::= { sonusEmsNotificationsPrefix 5 }

sonusEmsNodeCfgFailNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "EMS failed to configure the specified node."
    ::= { sonusEmsNotificationsPrefix 6 }

sonusEmsNodeCfgDoneNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "Successfully configured the specified node."
    ::= { sonusEmsNotificationsPrefix 7 }

sonusEmsFmSequenceGapNotification NOTIFICATION-TYPE
    OBJECTS         { sysName, sysObjectID, sonusEventTime, 
                      sonusEventDescription, sonusEventClass, 
                      sonusEventLevel, sonusEmsNodeIpAddress, 
                      sonusEmsNodeId, sonusEmsFmSequenceId, 
                      sonusEmsFmSequenceEndGapId }
    STATUS          deprecated
    DESCRIPTION     
            "The fm manager has observed a sequence gap in INFORM traps from the device."
    ::= { sonusEmsNotificationsPrefix 8 }

sonusEmsFmSequenceResetNotification NOTIFICATION-TYPE
    OBJECTS         { sysName, sysObjectID, sonusEventTime, 
                      sonusEventDescription, sonusEventClass, 
                      sonusEventLevel, sonusEmsNodeIpAddress, 
                      sonusEmsNodeId, sonusEmsFmSequenceId, 
                      sonusEmsFmSequenceResetId }
    STATUS          deprecated
    DESCRIPTION     
            "The fm manager has observed a situation which caused it to rest the expected sequence number.  This can be due to a agent reset or reboot."
    ::= { sonusEmsNotificationsPrefix 9 }

sonusEmsFmSequenceQOverflowNotification NOTIFICATION-TYPE
    OBJECTS         { sysName, sysObjectID, sonusEventTime, 
                      sonusEventDescription, sonusEventClass, 
                      sonusEventLevel, sonusEmsNodeIpAddress, 
                      sonusEmsNodeId, sonusEmsFmSequenceId }
    STATUS          deprecated
    DESCRIPTION     
            "The queue used by sequence handling code has overflowed. This may cause traps to be handled out of order."
    ::= { sonusEmsNotificationsPrefix 10 }

sonusEmsNodeCfgPartialNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "Partially configured the specified node.  One of the hosts of a redundant configuration was not successfully configured."
    ::= { sonusEmsNotificationsPrefix 11 }

sonusEmsHostCfgSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The host identified by sonusHostID was configured successfully."
    ::= { sonusEmsNotificationsPrefix 12 }

sonusEmsHostCfgFailureNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The host identified by sonusHostID was not configured successfully."
    ::= { sonusEmsNotificationsPrefix 13 }

sonusVfyMgrNodeTypeFailNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID does not contain the instrumentation component needed to manage the registered node."
    ::= { sonusEmsNotificationsPrefix 14 }

sonusVfyMgrNodeTypeSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID contains the instrumentation component needed to manage the registered node."
    ::= { sonusEmsNotificationsPrefix 15 }

sonusVfyMgrApplVersionFailNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID reports a different application version than that contained in the EMS node model. The application version is that of the instrumented device. For example PSX or SGX."
    ::= { sonusEmsNotificationsPrefix 16 }

sonusVfyMgrApplVersionSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID reports the same application version as that contained in the EMS node model. The application version is that of the instrumented device. For example PSX or SGX."
    ::= { sonusEmsNotificationsPrefix 17 }

sonusVfyMgrMgmtClientFailNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID does not contain a fault subscription entry for the EMS."
    ::= { sonusEmsNotificationsPrefix 18 }

sonusVfyMgrMgmtClientSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID contains a fault subscription entry for the EMS."
    ::= { sonusEmsNotificationsPrefix 19 }

sonusVfyMgrSnmpAccessFailNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID does not allow SNMP Read access priviledge for Insight."
    ::= { sonusEmsNotificationsPrefix 20 }

sonusVfyMgrSnmpAccessSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID allows SNMP Read access priviledge for Insight."
    ::= { sonusEmsNotificationsPrefix 21 }

sonusVfyMgrAgentVersionFailNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID reports a different version than that stored in the EMS."
    ::= { sonusEmsNotificationsPrefix 22 }

sonusVfyMgrAgentVersionSuccessNotification NOTIFICATION-TYPE
    OBJECTS         { sysName, sysObjectID, sonusEventTime, 
                      sonusEventDescription, sonusEventClass, 
                      sonusEventLevel, sonusEmsNodeIpAddress, 
                      sonusEmsNodeId, sonusHostID }
    STATUS          deprecated
    DESCRIPTION     
            "The agent on the host identified by sonusHostID reports the same version as that stored in the EMS."
    ::= { sonusEmsNotificationsPrefix 23 }

sonusEmsHostUnreachableNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified host is not reachable by the EMS."
    ::= { sonusEmsNotificationsPrefix 24 }

sonusEmsHostReachableNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified host is now reachable by the EMS."
    ::= { sonusEmsNotificationsPrefix 25 }

sonusEmsHostRestartedNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "The specified host has been restarted since last polled by the EMS."
    ::= { sonusEmsNotificationsPrefix 26 }

sonusEmsPifCollectFailNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "EMS failed to complete PIF collection for the specified node."
    ::= { sonusEmsNotificationsPrefix 27 }

sonusEmsPifCollectDoneNotification NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "Successfully complete PIF collection for the specified node."
    ::= { sonusEmsNotificationsPrefix 28 }

sonusEmsPMCollectionTaskStopped NOTIFICATION-TYPE
    OBJECTS         { sysName, sysObjectID, sonusEventTime, 
                      sonusEventDescription, sonusEventClass, 
                      sonusEventLevel, sonusEmsNodeIpAddress, 
                      sonusEmsNodeId }
    STATUS          deprecated
    DESCRIPTION     
            "PM Collection task has stopped and PMWatchdog is restarting the task."
    ::= { sonusEmsNotificationsPrefix 29 }

sonusEmsPMExportWithNoData NOTIFICATION-TYPE
    OBJECTS         { sysName, sysObjectID, sonusEventTime, 
                      sonusEventDescription, sonusEventClass, 
                      sonusEventLevel, sonusEmsNodeIpAddress, 
                      sonusEmsNodeId, sonusEmsPMStatsNames, 
                      sonusEmsPMExportCsvFile }
    STATUS          deprecated
    DESCRIPTION     
            "PM Exporter wrote the CSV file without any data (i.e with only header information)."
    ::= { sonusEmsNotificationsPrefix 30 }

sonusEmsPMExportSFTPFailNotification NOTIFICATION-TYPE
    OBJECTS         { sysName, sysObjectID, sonusEventTime, 
                      sonusEventDescription, sonusEventClass, 
                      sonusEventLevel, sonusRemoteServer }
    STATUS          current
    DESCRIPTION     
            "PM Exporter: Problem SCP'ing files to host."
    ::= { sonusEmsNotificationsPrefix 31 }

sonusEmsPMExportSFTPFailClearNotification NOTIFICATION-TYPE
    OBJECTS         { sysName, sysObjectID, sonusEventTime, 
                      sonusEventDescription, sonusEventClass, 
                      sonusEventLevel, sonusRemoteServer }
    STATUS          current
    DESCRIPTION     
            "PM Exporter: Rectified SCP'ing files to host."
    ::= { sonusEmsNotificationsPrefix 32 }

END -- end of module SONUS-EMS-MIB.
