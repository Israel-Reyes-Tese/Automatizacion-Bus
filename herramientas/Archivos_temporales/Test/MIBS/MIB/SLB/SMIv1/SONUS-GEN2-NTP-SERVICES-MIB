--
-- This SMIv1 module has been generated by smidump 0.2-cvs. Do not edit.
--

SONUS-GEN2-NTP-SERVICES-MIB DEFINITIONS ::= BEGIN

IMPORTS
    OBJECT-TYPE
        FROM RFC-1212
    Counter, Gauge, IpAddress
        FROM RFC1155-SMI
    RowStatus
        FROM SNMPv2-TC
    sonusCommonSoftwarePlatformServicesMIBs
        FROM SONUS-SMI;

sonusGen2NtpMIB OBJECT IDENTIFIER
    ::= { sonusCommonSoftwarePlatformServicesMIBs 7 }

-- sonusGen2NtpMIB MODULE-IDENTITY
--     LAST-UPDATED    "201212310000Z"
--     ORGANIZATION    
--             "Ribbon Communications, Inc."
--     CONTACT-INFO    
--             "Customer Support        
--              Ribbon Communications, Inc. 
--              4 Technology Park Drive 
--              Westford, MA 01886      
--              USA                     
--                                      
--              Tel: 978-614-8100       
--              Fax: 978-614-8609"
--     DESCRIPTION     
--             "The MIB Module for NTP Services Management."
--     REVISION        "201212310000Z"
--     DESCRIPTION     
--             "Auto generated MIB."
--     ::= { sonusCommonSoftwarePlatformServicesMIBs 7 }


InetAddressIP ::=
    OCTET STRING (SIZE(4 | 16))

-- InetAddressIP ::= TEXTUAL-CONVENTION
--     STATUS          mandatory
--     DESCRIPTION     
--             "confd:inetAddressIP"
--     SYNTAX          OCTET STRING (SIZE(4 | 16))

String ::=
    OCTET STRING

-- String ::= TEXTUAL-CONVENTION
--     DISPLAY-HINT    "1t"
--     STATUS          mandatory
--     DESCRIPTION     
--             "xs:string"
--     SYNTAX          OCTET STRING

SonusCpNtpDownReasonType ::=
    INTEGER { noNtpServerConfigured(1), allNtpServersOutOfSync(2) }

-- SonusCpNtpDownReasonType ::= TEXTUAL-CONVENTION
--     STATUS          mandatory
--     DESCRIPTION     
--             ""
--     SYNTAX          INTEGER
--                       { noNtpServerConfigured(1), 
--                         allNtpServersOutOfSync(2) }

SonusNtpServerVersionType ::=
    INTEGER { version3(3), version4(4) }

-- SonusNtpServerVersionType ::= TEXTUAL-CONVENTION
--     STATUS          mandatory
--     DESCRIPTION     
--             ""
--     SYNTAX          INTEGER
--                       { version3(3), version4(4) }

SonusNtpSysClockType ::=
    OCTET STRING (SIZE(0..255))

-- SonusNtpSysClockType ::= TEXTUAL-CONVENTION
--     DISPLAY-HINT    "1t"
--     STATUS          mandatory
--     DESCRIPTION     
--             ""
--     SYNTAX          OCTET STRING (SIZE(0..255))

SonusNtpKeysValueType ::=
    OCTET STRING (SIZE(0..255))

-- SonusNtpKeysValueType ::= TEXTUAL-CONVENTION
--     DISPLAY-HINT    "1t"
--     STATUS          mandatory
--     DESCRIPTION     
--             ""
--     SYNTAX          OCTET STRING (SIZE(0..255))

SonusNtpPeerMaxPollType ::=
    Gauge (10..17)

-- SonusNtpPeerMaxPollType ::= TEXTUAL-CONVENTION
--     STATUS          mandatory
--     DESCRIPTION     
--             ""
--     SYNTAX          Gauge (10..17)

SonusNtpPeerMinPollType ::=
    Gauge (4..17)

-- SonusNtpPeerMinPollType ::= TEXTUAL-CONVENTION
--     STATUS          mandatory
--     DESCRIPTION     
--             ""
--     SYNTAX          Gauge (4..17)

SonusNtpKeyType ::=
    INTEGER { md5(1), sha1(2) }

-- SonusNtpKeyType ::= TEXTUAL-CONVENTION
--     STATUS          mandatory
--     DESCRIPTION     
--             ""
--     SYNTAX          INTEGER
--                       { md5(1), sha1(2) }

SonusNtpKeyIdType ::=
    Gauge (1..65534)

-- SonusNtpKeyIdType ::= TEXTUAL-CONVENTION
--     STATUS          mandatory
--     DESCRIPTION     
--             ""
--     SYNTAX          Gauge (1..65534)

SonusNtpPeerVersionType ::=
    INTEGER { version3(3), version4(4) }

-- SonusNtpPeerVersionType ::= TEXTUAL-CONVENTION
--     STATUS          mandatory
--     DESCRIPTION     
--             ""
--     SYNTAX          INTEGER
--                       { version3(3), version4(4) }

SonusNtpPeerRefTimeType ::=
    OCTET STRING (SIZE(0..255))

-- SonusNtpPeerRefTimeType ::= TEXTUAL-CONVENTION
--     DISPLAY-HINT    "1t"
--     STATUS          mandatory
--     DESCRIPTION     
--             ""
--     SYNTAX          OCTET STRING (SIZE(0..255))

SonusTimeZoneType ::=
    INTEGER { gmtPlus12-Kwajalein(1), gmtMinus11-MidwayIsland(2), 
                        gmtMinus10-Hawaii(3), gmtMinus09-Alaska(4), 
                        gmtMinus08-Pacific-US(5), gmtMinus07-Arizona(6), 
                        gmtMinus07-Mountain(7), gmtMinus06-Central-US(8), 
                        gmtMinus06-Mexico(9), 
                        gmtMinus06-Saskatchewan(10), 
                        gmtMinus05-Bogota(11), gmtMinus05-Eastern-US(12), 
                        gmtMinus05-Indiana(13), 
                        gmtMinus04-Atlantic-Canada(14), 
                        gmtMinus0430-Caracas(15), 
                        gmtMinus03-BuenosAires(16), 
                        gmtMinus02-MidAtlantic(17), 
                        gmtMinus01-Azores(18), gmt(19), 
                        gmtPlus01-Berlin(20), gmtPlus02-Athens(21), 
                        gmtPlus03-Moscow(22), gmtPlus0330-Tehran(23), 
                        gmtPlus04-AbuDhabi(24), gmtPlus0430-Kabul(25), 
                        gmtPlus05-Islamabad(26), 
                        gmtPlus0530-Calcutta(27), gmtPlus06-Dhaka(28), 
                        gmtPlus07-Bangkok(29), gmtPlus08-HongKong(30), 
                        gmtPlus09-Tokyo(31), gmtPlus0930-Adelaide(32), 
                        gmtPlus10-Guam(33), gmtPlus11-Magadan(34), 
                        gmtPlus12-Fiji(35), gmt-London(36), 
                        arctic-Longyearbyen(37), us-Pacific-New(38), 
                        us-Indiana-Starke(39), us-Aleutian(40), 
                        us-Michigan(41), us-Samoa(42), 
                        america-Danmarkshavn(43), america-Montevideo(44), 
                        america-Chicago(45), america-Goose-Bay(46), 
                        america-Montserrat(47), america-Grenada(48), 
                        america-Mexico-City(49), america-Aruba(50), 
                        america-St-Barthelemy(51), america-Araguaina(52), 
                        america-Swift-Current(53), america-Recife(54), 
                        america-St-Vincent(55), america-Phoenix(56), 
                        america-Creston(57), america-Fortaleza(58), 
                        america-Rio-Branco(59), 
                        america-Cambridge-Bay(60), america-St-Johns(61), 
                        america-Cuiaba(62), america-Rosario(63), 
                        america-Juneau(64), america-Sao-Paulo(65), 
                        america-Dominica(66), america-Thule(67), 
                        america-Coral-Harbour(68), america-Anchorage(69), 
                        america-Noronha(70), america-St-Kitts(71), 
                        america-Cayenne(72), america-Martinique(73), 
                        america-Winnipeg(74), america-Ojinaga(75), 
                        america-Belem(76), america-Scoresbysund(77), 
                        america-Pangnirtung(78), america-Ensenada(79), 
                        america-Belize(80), america-Santa-Isabel(81), 
                        america-Louisville(82), america-Rankin-Inlet(83), 
                        america-Managua(84), america-Santarem(85), 
                        america-Santo-Domingo(86), america-Barbados(87), 
                        america-Manaus(88), america-Virgin(89), 
                        america-Lower-Princes(90), america-Nome(91), 
                        america-Catamarca(92), america-Montreal(93), 
                        america-Fort-Wayne(94), america-New-York(95), 
                        america-Asuncion(96), america-Porto-Acre(97), 
                        america-Toronto(98), 
                        america-Indiana-Vincennes(99), 
                        america-Indiana-Tell-City(100), 
                        america-Indiana-Marengo(101), 
                        america-Indiana-Knox(102), 
                        america-Indiana-Petersburg(103), 
                        america-Indiana-Winamac(104), 
                        america-Indiana-Vevay(105), 
                        america-Indiana-Indianapolis(106), 
                        america-Detroit(107), america-Nassau(108), 
                        america-Lima(109), america-Denver(110), 
                        america-Cancun(111), america-Anguilla(112), 
                        america-Tortola(113), america-Whitehorse(114), 
                        america-Guyana(115), america-Bahia-Banderas(116), 
                        america-Rainy-River(117), america-St-Thomas(118), 
                        america-Jamaica(119), america-Edmonton(120), 
                        america-Adak(121), america-Godthab(122), 
                        america-St-Lucia(123), america-Cayman(124), 
                        america-Santiago(125), america-Thunder-Bay(126), 
                        america-Resolute(127), 
                        america-North-Dakota-Center(128), 
                        america-North-Dakota-New-Salem(129), 
                        america-North-Dakota-Beulah(130), 
                        america-Boa-Vista(131), america-Merida(132), 
                        america-Monterrey(133), america-Eirunepe(134), 
                        america-Vancouver(135), america-Mazatlan(136), 
                        america-Atka(137), america-Sitka(138), 
                        america-Shiprock(139), america-Yakutat(140), 
                        america-Costa-Rica(141), america-Antigua(142), 
                        america-Guatemala(143), 
                        america-Campo-Grande(144), 
                        america-Kentucky-Louisville(145), 
                        america-Kentucky-Monticello(146), 
                        america-Glace-Bay(147), america-Maceio(148), 
                        america-Grand-Turk(149), america-Cordoba(150), 
                        america-Halifax(151), america-Yellowknife(152), 
                        america-Port-of-Spain(153), 
                        america-Menominee(154), america-Bahia(155), 
                        america-Tijuana(156), america-Metlakatla(157), 
                        america-Curacao(158), america-Mendoza(159), 
                        america-Porto-Velho(160), america-Marigot(161), 
                        america-La-Paz(162), america-Dawson(163), 
                        america-Guadeloupe(164), 
                        america-Argentina-ComodRivadavia(165), 
                        america-Argentina-San-Juan(166), 
                        america-Argentina-Tucuman(167), 
                        america-Argentina-Catamarca(168), 
                        america-Argentina-Ushuaia(169), 
                        america-Argentina-Rio-Gallegos(170), 
                        america-Argentina-La-Rioja(171), 
                        america-Argentina-Cordoba(172), 
                        america-Argentina-San-Luis(173), 
                        america-Argentina-Salta(174), 
                        america-Argentina-Mendoza(175), 
                        america-Argentina-Jujuy(176), 
                        america-Argentina-Buenos-Aires(177), 
                        america-Hermosillo(178), america-Atikokan(179), 
                        america-Los-Angeles(180), 
                        america-Dawson-Creek(181), america-Panama(182), 
                        america-Boise(183), america-Jujuy(184), 
                        america-Paramaribo(185), america-Inuvik(186), 
                        america-Guayaquil(187), america-Regina(188), 
                        america-Tegucigalpa(189), america-Havana(190), 
                        america-Port-au-Prince(191), 
                        america-Nipigon(192), america-El-Salvador(193), 
                        america-Chihuahua(194), america-Miquelon(195), 
                        america-Kralendijk(196), 
                        america-Puerto-Rico(197), america-Iqaluit(198), 
                        america-Indianapolis(199), 
                        america-Blanc-Sablon(200), 
                        america-Matamoros(201), america-Moncton(202), 
                        america-Knox-IN(203), canada-Central(204), 
                        canada-Eastern(205), canada-Mountain(206), 
                        canada-Yukon(207), canada-East-Saskatchewan(208), 
                        canada-Pacific(209), canada-Newfoundland(210), 
                        brazil-DeNoronha(211), brazil-Acre(212), 
                        brazil-East(213), brazil-West(214), eet(215), 
                        est5EDT(216), mexico-BajaSur(217), 
                        mexico-BajaNorte(218), hst(219), kwajalein(220), 
                        mst7MDT(221), nz(222), australia-Victoria(223), 
                        australia-LHI(224), australia-Brisbane(225), 
                        australia-NSW(226), australia-Lindeman(227), 
                        australia-Darwin(228), australia-Tasmania(229), 
                        australia-North(230), australia-West(231), 
                        australia-ACT(232), australia-Lord-Howe(233), 
                        australia-Melbourne(234), australia-Eucla(235), 
                        australia-Broken-Hill(236), 
                        australia-Currie(237), australia-Sydney(238), 
                        australia-Yancowinna(239), australia-Perth(240), 
                        australia-South(241), australia-Canberra(242), 
                        australia-Queensland(243), australia-Hobart(244), 
                        libya(245), iran(246), iceland(247), 
                        chile-Continental(248), chile-EasterIsland(249), 
                        egypt(250), greenwich(251), israel(252), 
                        navajo(253), indian-Christmas(254), 
                        indian-Antananarivo(255), indian-Chagos(256), 
                        indian-Comoro(257), indian-Reunion(258), 
                        indian-Mahe(259), indian-Maldives(260), 
                        indian-Kerguelen(261), indian-Mauritius(262), 
                        indian-Mayotte(263), indian-Cocos(264), mst(265), 
                        met(266), gmtplus0(267), cuba(268), 
                        antarctica-Macquarie(269), 
                        antarctica-McMurdo(270), 
                        antarctica-DumontDUrville(271), 
                        antarctica-Casey(272), antarctica-Davis(273), 
                        antarctica-South-Pole(274), 
                        antarctica-Mawson(275), antarctica-Syowa(276), 
                        antarctica-Vostok(277), antarctica-Palmer(278), 
                        antarctica-Rothera(279), utc(280), 
                        systemV-EST5EDT(281), systemV-AST4ADT(282), 
                        systemV-MST7MDT(283), systemV-HST10(284), 
                        systemV-YST9(285), systemV-PST8(286), 
                        systemV-YST9YDT(287), systemV-EST5(288), 
                        systemV-CST6(289), systemV-AST4(290), 
                        systemV-PST8PDT(291), systemV-CST6CDT(292), 
                        systemV-MST7(293), universal(294), jamaica(295), 
                        gmt0(296), japan(297), wet(298), hongkong(299), 
                        prc(300), asia-Riyadh(301), 
                        asia-Ulaanbaatar(302), asia-Irkutsk(303), 
                        asia-Vladivostok(304), asia-Ulan-Bator(305), 
                        asia-Oral(306), asia-Yekaterinburg(307), 
                        asia-Ashkhabad(308), asia-Baghdad(309), 
                        asia-Saigon(310), asia-Aqtau(311), 
                        asia-Nicosia(313), asia-Krasnoyarsk(314), 
                        asia-Sakhalin(315), asia-Dushanbe(316), 
                        asia-Novokuznetsk(317), asia-Novosibirsk(318), 
                        asia-Tbilisi(319), asia-Dili(320), 
                        asia-Jayapura(321), asia-Colombo(322), 
                        asia-Ashgabat(323), asia-Bahrain(324), 
                        asia-Aden(325), asia-Muscat(326), 
                        asia-Ho-Chi-Minh(327), asia-Baku(328), 
                        asia-Macau(329), asia-Makassar(330), 
                        asia-Aqtobe(331), asia-Kathmandu(332), 
                        asia-Macao(333), asia-Samarkand(334), 
                        asia-Yerevan(335), asia-Thimbu(336), 
                        asia-Seoul(337), asia-Yakutsk(338), 
                        asia-Kuwait(339), asia-Amman(340), 
                        asia-Tel-Aviv(341), asia-Shanghai(342), 
                        asia-Kashgar(343), asia-Almaty(344), 
                        asia-Vientiane(345), asia-Qyzylorda(346), 
                        asia-Pyongyang(347), asia-Rangoon(348), 
                        asia-Thimphu(349), asia-Harbin(350), 
                        asia-Damascus(351), asia-Bishkek(352), 
                        asia-Chungking(353), asia-Choibalsan(354), 
                        asia-Omsk(355), asia-Kamchatka(356), 
                        asia-Istanbul(357), asia-Jakarta(358), 
                        asia-Hovd(359), asia-Anadyr(360), 
                        asia-Chongqing(361), asia-Kuching(362), 
                        asia-Tashkent(363), asia-Phnom-Penh(365), 
                        asia-Manila(366), asia-Urumqi(367), 
                        asia-Dacca(368), asia-Pontianak(369), 
                        asia-Kolkata(370), asia-Katmandu(371), 
                        asia-Hebron(372), asia-Ujung-Pandang(373), 
                        asia-Taipei(374), asia-Beirut(376), 
                        asia-Gaza(377), asia-Kuala-Lumpur(378), 
                        asia-Singapore(379), asia-Qatar(380), 
                        asia-Brunei(381), asia-Karachi(382), 
                        asia-Jerusalem(383), nz-CHAT(384), portugal(385), 
                        gb(386), pacific-Nauru(387), pacific-Tarawa(388), 
                        pacific-Easter(389), pacific-Truk(390), 
                        pacific-Wallis(391), pacific-Efate(392), 
                        pacific-Saipan(393), pacific-Tongatapu(394), 
                        pacific-Johnston(395), pacific-Pitcairn(396), 
                        pacific-Auckland(397), pacific-Honolulu(398), 
                        pacific-Yap(399), pacific-Funafuti(400), 
                        pacific-Chuuk(401), pacific-Norfolk(402), 
                        pacific-Niue(403), pacific-Tahiti(404), 
                        pacific-Galapagos(405), pacific-Gambier(406), 
                        pacific-Kiritimati(407), pacific-Palau(408), 
                        pacific-Enderbury(409), pacific-Ponape(410), 
                        pacific-Apia(411), pacific-Noumea(412), 
                        pacific-Port-Moresby(413), pacific-Pohnpei(414), 
                        pacific-Rarotonga(415), pacific-Majuro(416), 
                        pacific-Fakaofo(417), pacific-Wake(418), 
                        pacific-Kosrae(419), pacific-Pago-Pago(420), 
                        pacific-Marquesas(421), pacific-Samoa(422), 
                        pacific-Guadalcanal(423), pacific-Chatham(424), 
                        est(425), zulu(426), w-SU(427), factory(428), 
                        roc(429), pst8PDT(430), cst6CDT(431), eire(432), 
                        etc-GMT-10(433), etc-GMT-4(434), etc-GMT-9(435), 
                        etc-GMTplus3(436), etc-GMTplus7(437), 
                        etc-GMT-13(438), etc-GMT-11(439), 
                        etc-Greenwich(440), etc-GMTplus6(441), 
                        etc-GMTplus12(442), etc-GMTplus0(443), 
                        etc-GMT-2(444), etc-UTC(445), etc-GMTplus4(446), 
                        etc-Universal(447), etc-GMTplus5(448), 
                        etc-GMT0(449), etc-GMT-12(450), etc-GMT-6(451), 
                        etc-GMTplus9(452), etc-GMT(453), etc-GMT-7(454), 
                        etc-GMTplus10(455), etc-GMTplus8(456), 
                        etc-GMT-3(457), etc-Zulu(458), etc-GMTplus1(459), 
                        etc-GMT-14(460), etc-UCT(461), etc-GMT-1(462), 
                        etc-GMT-0(463), etc-GMTplus11(464), 
                        etc-GMT-8(465), mideast-Riyadh87(466), 
                        mideast-Riyadh89(467), mideast-Riyadh88(468), 
                        africa-Timbuktu(469), africa-Bujumbura(470), 
                        africa-Lusaka(471), africa-Khartoum(472), 
                        africa-Libreville(473), africa-Bissau(474), 
                        africa-Dar-es-Salaam(475), africa-Luanda(476), 
                        africa-Windhoek(477), africa-Lome(478), 
                        africa-Tripoli(479), africa-El-Aaiun(480), 
                        africa-Monrovia(481), africa-Lagos(482), 
                        africa-Niamey(483), africa-Ndjamena(484), 
                        africa-Asmara(485), africa-Juba(486), 
                        africa-Malabo(487), africa-Maputo(488), 
                        africa-Ceuta(489), africa-Nouakchott(490), 
                        africa-Brazzaville(491), africa-Douala(492), 
                        africa-Bamako(493), africa-Maseru(494), 
                        africa-Dakar(495), africa-Ouagadougou(496), 
                        africa-Mogadishu(497), africa-Casablanca(498), 
                        africa-Kigali(499), africa-Conakry(500), 
                        africa-Blantyre(501), africa-Nairobi(502), 
                        africa-Kampala(503), africa-Freetown(504), 
                        africa-Mbabane(505), africa-Tunis(506), 
                        africa-Gaborone(507), africa-Accra(508), 
                        africa-Kinshasa(509), africa-Harare(510), 
                        africa-Banjul(511), africa-Johannesburg(512), 
                        africa-Asmera(513), africa-Cairo(514), 
                        africa-Addis-Ababa(515), africa-Lubumbashi(516), 
                        africa-Algiers(517), africa-Sao-Tome(518), 
                        africa-Porto-Novo(519), africa-Abidjan(520), 
                        africa-Djibouti(521), africa-Bangui(522), 
                        rok(523), poland(524), uct(525), 
                        europe-Monaco(526), europe-Sarajevo(527), 
                        europe-Volgograd(528), europe-Ljubljana(529), 
                        europe-Samara(530), europe-Mariehamn(531), 
                        europe-Brussels(532), europe-Helsinki(533), 
                        europe-Copenhagen(534), europe-Tallinn(535), 
                        europe-Kiev(536), europe-Nicosia(537), 
                        europe-Tirane(538), europe-Skopje(539), 
                        europe-Dublin(540), europe-Warsaw(541), 
                        europe-Zurich(542), europe-Bratislava(543), 
                        europe-Vienna(544), europe-Chisinau(545), 
                        europe-Simferopol(546), europe-Guernsey(547), 
                        europe-Luxembourg(548), europe-Vaduz(549), 
                        europe-Belfast(550), europe-Isle-of-Man(551), 
                        europe-Budapest(552), europe-Minsk(553), 
                        europe-Riga(554), europe-Vilnius(555), 
                        europe-Zagreb(556), europe-Madrid(557), 
                        europe-Amsterdam(558), europe-Istanbul(559), 
                        europe-Zaporozhye(560), europe-Oslo(561), 
                        europe-Paris(562), europe-Stockholm(563), 
                        europe-Vatican(564), europe-San-Marino(565), 
                        europe-Jersey(566), europe-Bucharest(567), 
                        europe-Rome(568), europe-Malta(569), 
                        europe-Tiraspol(570), europe-Gibraltar(571), 
                        europe-Podgorica(572), europe-Uzhgorod(573), 
                        europe-Sofia(574), europe-Kaliningrad(575), 
                        europe-Andorra(576), europe-Lisbon(577), 
                        europe-Prague(578), europe-Belgrade(579), 
                        gb-Eire(580), gmt-0(581), cet(582), 
                        singapore(583), turkey(584), 
                        atlantic-Reykjavik(585), atlantic-Faroe(586), 
                        atlantic-Stanley(587), atlantic-Jan-Mayen(588), 
                        atlantic-St-Helena(589), atlantic-Faeroe(590), 
                        atlantic-Madeira(591), atlantic-Cape-Verde(592), 
                        atlantic-Bermuda(593), atlantic-Canary(594), 
                        atlantic-South-Georgia(595) }

-- SonusTimeZoneType ::= TEXTUAL-CONVENTION
--     STATUS          mandatory
--     DESCRIPTION     
--             ""
--     SYNTAX          INTEGER
--                       { gmtPlus12-Kwajalein(1), 
--                         gmtMinus11-MidwayIsland(2), 
--                         gmtMinus10-Hawaii(3), gmtMinus09-Alaska(4), 
--                         gmtMinus08-Pacific-US(5), 
--                         gmtMinus07-Arizona(6), gmtMinus07-Mountain(7), 
--                         gmtMinus06-Central-US(8), 
--                         gmtMinus06-Mexico(9), 
--                         gmtMinus06-Saskatchewan(10), 
--                         gmtMinus05-Bogota(11), 
--                         gmtMinus05-Eastern-US(12), 
--                         gmtMinus05-Indiana(13), 
--                         gmtMinus04-Atlantic-Canada(14), 
--                         gmtMinus0430-Caracas(15), 
--                         gmtMinus03-BuenosAires(16), 
--                         gmtMinus02-MidAtlantic(17), 
--                         gmtMinus01-Azores(18), gmt(19), 
--                         gmtPlus01-Berlin(20), gmtPlus02-Athens(21), 
--                         gmtPlus03-Moscow(22), gmtPlus0330-Tehran(23), 
--                         gmtPlus04-AbuDhabi(24), gmtPlus0430-Kabul(25), 
--                         gmtPlus05-Islamabad(26), 
--                         gmtPlus0530-Calcutta(27), gmtPlus06-Dhaka(28), 
--                         gmtPlus07-Bangkok(29), gmtPlus08-HongKong(30), 
--                         gmtPlus09-Tokyo(31), gmtPlus0930-Adelaide(32), 
--                         gmtPlus10-Guam(33), gmtPlus11-Magadan(34), 
--                         gmtPlus12-Fiji(35), gmt-London(36), 
--                         arctic-Longyearbyen(37), us-Pacific-New(38), 
--                         us-Indiana-Starke(39), us-Aleutian(40), 
--                         us-Michigan(41), us-Samoa(42), 
--                         america-Danmarkshavn(43), 
--                         america-Montevideo(44), america-Chicago(45), 
--                         america-Goose-Bay(46), america-Montserrat(47), 
--                         america-Grenada(48), america-Mexico-City(49), 
--                         america-Aruba(50), america-St-Barthelemy(51), 
--                         america-Araguaina(52), 
--                         america-Swift-Current(53), america-Recife(54), 
--                         america-St-Vincent(55), america-Phoenix(56), 
--                         america-Creston(57), america-Fortaleza(58), 
--                         america-Rio-Branco(59), 
--                         america-Cambridge-Bay(60), 
--                         america-St-Johns(61), america-Cuiaba(62), 
--                         america-Rosario(63), america-Juneau(64), 
--                         america-Sao-Paulo(65), america-Dominica(66), 
--                         america-Thule(67), america-Coral-Harbour(68), 
--                         america-Anchorage(69), america-Noronha(70), 
--                         america-St-Kitts(71), america-Cayenne(72), 
--                         america-Martinique(73), america-Winnipeg(74), 
--                         america-Ojinaga(75), america-Belem(76), 
--                         america-Scoresbysund(77), 
--                         america-Pangnirtung(78), america-Ensenada(79), 
--                         america-Belize(80), america-Santa-Isabel(81), 
--                         america-Louisville(82), 
--                         america-Rankin-Inlet(83), america-Managua(84), 
--                         america-Santarem(85), 
--                         america-Santo-Domingo(86), 
--                         america-Barbados(87), america-Manaus(88), 
--                         america-Virgin(89), america-Lower-Princes(90), 
--                         america-Nome(91), america-Catamarca(92), 
--                         america-Montreal(93), america-Fort-Wayne(94), 
--                         america-New-York(95), america-Asuncion(96), 
--                         america-Porto-Acre(97), america-Toronto(98), 
--                         america-Indiana-Vincennes(99), 
--                         america-Indiana-Tell-City(100), 
--                         america-Indiana-Marengo(101), 
--                         america-Indiana-Knox(102), 
--                         america-Indiana-Petersburg(103), 
--                         america-Indiana-Winamac(104), 
--                         america-Indiana-Vevay(105), 
--                         america-Indiana-Indianapolis(106), 
--                         america-Detroit(107), america-Nassau(108), 
--                         america-Lima(109), america-Denver(110), 
--                         america-Cancun(111), america-Anguilla(112), 
--                         america-Tortola(113), america-Whitehorse(114), 
--                         america-Guyana(115), 
--                         america-Bahia-Banderas(116), 
--                         america-Rainy-River(117), 
--                         america-St-Thomas(118), america-Jamaica(119), 
--                         america-Edmonton(120), america-Adak(121), 
--                         america-Godthab(122), america-St-Lucia(123), 
--                         america-Cayman(124), america-Santiago(125), 
--                         america-Thunder-Bay(126), 
--                         america-Resolute(127), 
--                         america-North-Dakota-Center(128), 
--                         america-North-Dakota-New-Salem(129), 
--                         america-North-Dakota-Beulah(130), 
--                         america-Boa-Vista(131), america-Merida(132), 
--                         america-Monterrey(133), america-Eirunepe(134), 
--                         america-Vancouver(135), america-Mazatlan(136), 
--                         america-Atka(137), america-Sitka(138), 
--                         america-Shiprock(139), america-Yakutat(140), 
--                         america-Costa-Rica(141), america-Antigua(142), 
--                         america-Guatemala(143), 
--                         america-Campo-Grande(144), 
--                         america-Kentucky-Louisville(145), 
--                         america-Kentucky-Monticello(146), 
--                         america-Glace-Bay(147), america-Maceio(148), 
--                         america-Grand-Turk(149), america-Cordoba(150), 
--                         america-Halifax(151), 
--                         america-Yellowknife(152), 
--                         america-Port-of-Spain(153), 
--                         america-Menominee(154), america-Bahia(155), 
--                         america-Tijuana(156), america-Metlakatla(157), 
--                         america-Curacao(158), america-Mendoza(159), 
--                         america-Porto-Velho(160), 
--                         america-Marigot(161), america-La-Paz(162), 
--                         america-Dawson(163), america-Guadeloupe(164), 
--                         america-Argentina-ComodRivadavia(165), 
--                         america-Argentina-San-Juan(166), 
--                         america-Argentina-Tucuman(167), 
--                         america-Argentina-Catamarca(168), 
--                         america-Argentina-Ushuaia(169), 
--                         america-Argentina-Rio-Gallegos(170), 
--                         america-Argentina-La-Rioja(171), 
--                         america-Argentina-Cordoba(172), 
--                         america-Argentina-San-Luis(173), 
--                         america-Argentina-Salta(174), 
--                         america-Argentina-Mendoza(175), 
--                         america-Argentina-Jujuy(176), 
--                         america-Argentina-Buenos-Aires(177), 
--                         america-Hermosillo(178), 
--                         america-Atikokan(179), 
--                         america-Los-Angeles(180), 
--                         america-Dawson-Creek(181), 
--                         america-Panama(182), america-Boise(183), 
--                         america-Jujuy(184), america-Paramaribo(185), 
--                         america-Inuvik(186), america-Guayaquil(187), 
--                         america-Regina(188), america-Tegucigalpa(189), 
--                         america-Havana(190), 
--                         america-Port-au-Prince(191), 
--                         america-Nipigon(192), 
--                         america-El-Salvador(193), 
--                         america-Chihuahua(194), america-Miquelon(195), 
--                         america-Kralendijk(196), 
--                         america-Puerto-Rico(197), 
--                         america-Iqaluit(198), 
--                         america-Indianapolis(199), 
--                         america-Blanc-Sablon(200), 
--                         america-Matamoros(201), america-Moncton(202), 
--                         america-Knox-IN(203), canada-Central(204), 
--                         canada-Eastern(205), canada-Mountain(206), 
--                         canada-Yukon(207), 
--                         canada-East-Saskatchewan(208), 
--                         canada-Pacific(209), canada-Newfoundland(210), 
--                         brazil-DeNoronha(211), brazil-Acre(212), 
--                         brazil-East(213), brazil-West(214), eet(215), 
--                         est5EDT(216), mexico-BajaSur(217), 
--                         mexico-BajaNorte(218), hst(219), 
--                         kwajalein(220), mst7MDT(221), nz(222), 
--                         australia-Victoria(223), australia-LHI(224), 
--                         australia-Brisbane(225), australia-NSW(226), 
--                         australia-Lindeman(227), 
--                         australia-Darwin(228), 
--                         australia-Tasmania(229), australia-North(230), 
--                         australia-West(231), australia-ACT(232), 
--                         australia-Lord-Howe(233), 
--                         australia-Melbourne(234), 
--                         australia-Eucla(235), 
--                         australia-Broken-Hill(236), 
--                         australia-Currie(237), australia-Sydney(238), 
--                         australia-Yancowinna(239), 
--                         australia-Perth(240), australia-South(241), 
--                         australia-Canberra(242), 
--                         australia-Queensland(243), 
--                         australia-Hobart(244), libya(245), iran(246), 
--                         iceland(247), chile-Continental(248), 
--                         chile-EasterIsland(249), egypt(250), 
--                         greenwich(251), israel(252), navajo(253), 
--                         indian-Christmas(254), 
--                         indian-Antananarivo(255), indian-Chagos(256), 
--                         indian-Comoro(257), indian-Reunion(258), 
--                         indian-Mahe(259), indian-Maldives(260), 
--                         indian-Kerguelen(261), indian-Mauritius(262), 
--                         indian-Mayotte(263), indian-Cocos(264), 
--                         mst(265), met(266), gmtplus0(267), cuba(268), 
--                         antarctica-Macquarie(269), 
--                         antarctica-McMurdo(270), 
--                         antarctica-DumontDUrville(271), 
--                         antarctica-Casey(272), antarctica-Davis(273), 
--                         antarctica-South-Pole(274), 
--                         antarctica-Mawson(275), antarctica-Syowa(276), 
--                         antarctica-Vostok(277), 
--                         antarctica-Palmer(278), 
--                         antarctica-Rothera(279), utc(280), 
--                         systemV-EST5EDT(281), systemV-AST4ADT(282), 
--                         systemV-MST7MDT(283), systemV-HST10(284), 
--                         systemV-YST9(285), systemV-PST8(286), 
--                         systemV-YST9YDT(287), systemV-EST5(288), 
--                         systemV-CST6(289), systemV-AST4(290), 
--                         systemV-PST8PDT(291), systemV-CST6CDT(292), 
--                         systemV-MST7(293), universal(294), 
--                         jamaica(295), gmt0(296), japan(297), wet(298), 
--                         hongkong(299), prc(300), asia-Riyadh(301), 
--                         asia-Ulaanbaatar(302), asia-Irkutsk(303), 
--                         asia-Vladivostok(304), asia-Ulan-Bator(305), 
--                         asia-Oral(306), asia-Yekaterinburg(307), 
--                         asia-Ashkhabad(308), asia-Baghdad(309), 
--                         asia-Saigon(310), asia-Aqtau(311), 
--                         asia-Nicosia(313), asia-Krasnoyarsk(314), 
--                         asia-Sakhalin(315), asia-Dushanbe(316), 
--                         asia-Novokuznetsk(317), asia-Novosibirsk(318), 
--                         asia-Tbilisi(319), asia-Dili(320), 
--                         asia-Jayapura(321), asia-Colombo(322), 
--                         asia-Ashgabat(323), asia-Bahrain(324), 
--                         asia-Aden(325), asia-Muscat(326), 
--                         asia-Ho-Chi-Minh(327), asia-Baku(328), 
--                         asia-Macau(329), asia-Makassar(330), 
--                         asia-Aqtobe(331), asia-Kathmandu(332), 
--                         asia-Macao(333), asia-Samarkand(334), 
--                         asia-Yerevan(335), asia-Thimbu(336), 
--                         asia-Seoul(337), asia-Yakutsk(338), 
--                         asia-Kuwait(339), asia-Amman(340), 
--                         asia-Tel-Aviv(341), asia-Shanghai(342), 
--                         asia-Kashgar(343), asia-Almaty(344), 
--                         asia-Vientiane(345), asia-Qyzylorda(346), 
--                         asia-Pyongyang(347), asia-Rangoon(348), 
--                         asia-Thimphu(349), asia-Harbin(350), 
--                         asia-Damascus(351), asia-Bishkek(352), 
--                         asia-Chungking(353), asia-Choibalsan(354), 
--                         asia-Omsk(355), asia-Kamchatka(356), 
--                         asia-Istanbul(357), asia-Jakarta(358), 
--                         asia-Hovd(359), asia-Anadyr(360), 
--                         asia-Chongqing(361), asia-Kuching(362), 
--                         asia-Tashkent(363), asia-Phnom-Penh(365), 
--                         asia-Manila(366), asia-Urumqi(367), 
--                         asia-Dacca(368), asia-Pontianak(369), 
--                         asia-Kolkata(370), asia-Katmandu(371), 
--                         asia-Hebron(372), asia-Ujung-Pandang(373), 
--                         asia-Taipei(374), asia-Beirut(376), 
--                         asia-Gaza(377), asia-Kuala-Lumpur(378), 
--                         asia-Singapore(379), asia-Qatar(380), 
--                         asia-Brunei(381), asia-Karachi(382), 
--                         asia-Jerusalem(383), nz-CHAT(384), 
--                         portugal(385), gb(386), pacific-Nauru(387), 
--                         pacific-Tarawa(388), pacific-Easter(389), 
--                         pacific-Truk(390), pacific-Wallis(391), 
--                         pacific-Efate(392), pacific-Saipan(393), 
--                         pacific-Tongatapu(394), pacific-Johnston(395), 
--                         pacific-Pitcairn(396), pacific-Auckland(397), 
--                         pacific-Honolulu(398), pacific-Yap(399), 
--                         pacific-Funafuti(400), pacific-Chuuk(401), 
--                         pacific-Norfolk(402), pacific-Niue(403), 
--                         pacific-Tahiti(404), pacific-Galapagos(405), 
--                         pacific-Gambier(406), pacific-Kiritimati(407), 
--                         pacific-Palau(408), pacific-Enderbury(409), 
--                         pacific-Ponape(410), pacific-Apia(411), 
--                         pacific-Noumea(412), 
--                         pacific-Port-Moresby(413), 
--                         pacific-Pohnpei(414), pacific-Rarotonga(415), 
--                         pacific-Majuro(416), pacific-Fakaofo(417), 
--                         pacific-Wake(418), pacific-Kosrae(419), 
--                         pacific-Pago-Pago(420), 
--                         pacific-Marquesas(421), pacific-Samoa(422), 
--                         pacific-Guadalcanal(423), 
--                         pacific-Chatham(424), est(425), zulu(426), 
--                         w-SU(427), factory(428), roc(429), 
--                         pst8PDT(430), cst6CDT(431), eire(432), 
--                         etc-GMT-10(433), etc-GMT-4(434), 
--                         etc-GMT-9(435), etc-GMTplus3(436), 
--                         etc-GMTplus7(437), etc-GMT-13(438), 
--                         etc-GMT-11(439), etc-Greenwich(440), 
--                         etc-GMTplus6(441), etc-GMTplus12(442), 
--                         etc-GMTplus0(443), etc-GMT-2(444), 
--                         etc-UTC(445), etc-GMTplus4(446), 
--                         etc-Universal(447), etc-GMTplus5(448), 
--                         etc-GMT0(449), etc-GMT-12(450), 
--                         etc-GMT-6(451), etc-GMTplus9(452), 
--                         etc-GMT(453), etc-GMT-7(454), 
--                         etc-GMTplus10(455), etc-GMTplus8(456), 
--                         etc-GMT-3(457), etc-Zulu(458), 
--                         etc-GMTplus1(459), etc-GMT-14(460), 
--                         etc-UCT(461), etc-GMT-1(462), etc-GMT-0(463), 
--                         etc-GMTplus11(464), etc-GMT-8(465), 
--                         mideast-Riyadh87(466), mideast-Riyadh89(467), 
--                         mideast-Riyadh88(468), africa-Timbuktu(469), 
--                         africa-Bujumbura(470), africa-Lusaka(471), 
--                         africa-Khartoum(472), africa-Libreville(473), 
--                         africa-Bissau(474), africa-Dar-es-Salaam(475), 
--                         africa-Luanda(476), africa-Windhoek(477), 
--                         africa-Lome(478), africa-Tripoli(479), 
--                         africa-El-Aaiun(480), africa-Monrovia(481), 
--                         africa-Lagos(482), africa-Niamey(483), 
--                         africa-Ndjamena(484), africa-Asmara(485), 
--                         africa-Juba(486), africa-Malabo(487), 
--                         africa-Maputo(488), africa-Ceuta(489), 
--                         africa-Nouakchott(490), 
--                         africa-Brazzaville(491), africa-Douala(492), 
--                         africa-Bamako(493), africa-Maseru(494), 
--                         africa-Dakar(495), africa-Ouagadougou(496), 
--                         africa-Mogadishu(497), africa-Casablanca(498), 
--                         africa-Kigali(499), africa-Conakry(500), 
--                         africa-Blantyre(501), africa-Nairobi(502), 
--                         africa-Kampala(503), africa-Freetown(504), 
--                         africa-Mbabane(505), africa-Tunis(506), 
--                         africa-Gaborone(507), africa-Accra(508), 
--                         africa-Kinshasa(509), africa-Harare(510), 
--                         africa-Banjul(511), africa-Johannesburg(512), 
--                         africa-Asmera(513), africa-Cairo(514), 
--                         africa-Addis-Ababa(515), 
--                         africa-Lubumbashi(516), africa-Algiers(517), 
--                         africa-Sao-Tome(518), africa-Porto-Novo(519), 
--                         africa-Abidjan(520), africa-Djibouti(521), 
--                         africa-Bangui(522), rok(523), poland(524), 
--                         uct(525), europe-Monaco(526), 
--                         europe-Sarajevo(527), europe-Volgograd(528), 
--                         europe-Ljubljana(529), europe-Samara(530), 
--                         europe-Mariehamn(531), europe-Brussels(532), 
--                         europe-Helsinki(533), europe-Copenhagen(534), 
--                         europe-Tallinn(535), europe-Kiev(536), 
--                         europe-Nicosia(537), europe-Tirane(538), 
--                         europe-Skopje(539), europe-Dublin(540), 
--                         europe-Warsaw(541), europe-Zurich(542), 
--                         europe-Bratislava(543), europe-Vienna(544), 
--                         europe-Chisinau(545), europe-Simferopol(546), 
--                         europe-Guernsey(547), europe-Luxembourg(548), 
--                         europe-Vaduz(549), europe-Belfast(550), 
--                         europe-Isle-of-Man(551), europe-Budapest(552), 
--                         europe-Minsk(553), europe-Riga(554), 
--                         europe-Vilnius(555), europe-Zagreb(556), 
--                         europe-Madrid(557), europe-Amsterdam(558), 
--                         europe-Istanbul(559), europe-Zaporozhye(560), 
--                         europe-Oslo(561), europe-Paris(562), 
--                         europe-Stockholm(563), europe-Vatican(564), 
--                         europe-San-Marino(565), europe-Jersey(566), 
--                         europe-Bucharest(567), europe-Rome(568), 
--                         europe-Malta(569), europe-Tiraspol(570), 
--                         europe-Gibraltar(571), europe-Podgorica(572), 
--                         europe-Uzhgorod(573), europe-Sofia(574), 
--                         europe-Kaliningrad(575), europe-Andorra(576), 
--                         europe-Lisbon(577), europe-Prague(578), 
--                         europe-Belgrade(579), gb-Eire(580), 
--                         gmt-0(581), cet(582), singapore(583), 
--                         turkey(584), atlantic-Reykjavik(585), 
--                         atlantic-Faroe(586), atlantic-Stanley(587), 
--                         atlantic-Jan-Mayen(588), 
--                         atlantic-St-Helena(589), atlantic-Faeroe(590), 
--                         atlantic-Madeira(591), 
--                         atlantic-Cape-Verde(592), 
--                         atlantic-Bermuda(593), atlantic-Canary(594), 
--                         atlantic-South-Georgia(595) }

SonusNtpSysRefTimeType ::=
    OCTET STRING (SIZE(0..255))

-- SonusNtpSysRefTimeType ::= TEXTUAL-CONVENTION
--     DISPLAY-HINT    "1t"
--     STATUS          mandatory
--     DESCRIPTION     
--             ""
--     SYNTAX          OCTET STRING (SIZE(0..255))

SonusCpNtpServerOutOfServiceReasonType ::=
    INTEGER { ntpServerDisabled(1), ntpServerOutOfSync(2) }

-- SonusCpNtpServerOutOfServiceReasonType ::= TEXTUAL-CONVENTION
--     STATUS          mandatory
--     DESCRIPTION     
--             ""
--     SYNTAX          INTEGER
--                       { ntpServerDisabled(1), ntpServerOutOfSync(2) }

SonusNtpPeerStateType ::=
    INTEGER { outofsync(1), insync(2), reachable(3) }

-- SonusNtpPeerStateType ::= TEXTUAL-CONVENTION
--     STATUS          mandatory
--     DESCRIPTION     
--             ""
--     SYNTAX          INTEGER
--                       { outofsync(1), insync(2), reachable(3) }

SonusNtpServerMaxPollType ::=
    Gauge (10..17)

-- SonusNtpServerMaxPollType ::= TEXTUAL-CONVENTION
--     STATUS          mandatory
--     DESCRIPTION     
--             ""
--     SYNTAX          Gauge (10..17)

SonusNtpServerMinPollType ::=
    Gauge (4..17)

-- SonusNtpServerMinPollType ::= TEXTUAL-CONVENTION
--     STATUS          mandatory
--     DESCRIPTION     
--             ""
--     SYNTAX          Gauge (4..17)

sonusNtp OBJECT IDENTIFIER
    ::= { sonusGen2NtpMIB 1 }

sonusNtpTimeZoneTable OBJECT-TYPE
    SYNTAX          SEQUENCE OF SonusNtpTimeZoneEntry
    ACCESS          not-accessible
    STATUS          obsolete
    DESCRIPTION     
            "
             This table contains Time Zone configuration.
             "
    ::= { sonusNtp 1 }

sonusNtpTimeZoneEntry OBJECT-TYPE
    SYNTAX          SonusNtpTimeZoneEntry
    ACCESS          not-accessible
    STATUS          obsolete
    DESCRIPTION     
            ""
    INDEX           { sonusNtpTimeZoneName }
    ::= { sonusNtpTimeZoneTable 1 }

SonusNtpTimeZoneEntry ::=
    SEQUENCE {
        sonusNtpTimeZoneName            String,
        sonusNtpTimeZoneZone            SonusTimeZoneType,
        sonusNtpTimeZoneRowstatus       RowStatus
    }

sonusNtpTimeZoneName OBJECT-TYPE
    SYNTAX          String (SIZE(0..255))
    ACCESS          not-accessible
    STATUS          obsolete
    DESCRIPTION     
            "
             Name of the system.
             "
    ::= { sonusNtpTimeZoneEntry 1 }

sonusNtpTimeZoneZone OBJECT-TYPE
    SYNTAX          SonusTimeZoneType
    ACCESS          read-write
    STATUS          obsolete
    DESCRIPTION     
            "
             This is the Time Zone that this Node is in.
             "
    DEFVAL          { gmt }
    ::= { sonusNtpTimeZoneEntry 2 }

sonusNtpTimeZoneRowstatus OBJECT-TYPE
    SYNTAX          RowStatus
    ACCESS          read-write
    STATUS          obsolete
    DESCRIPTION     
            ""
    ::= { sonusNtpTimeZoneEntry 3 }

sonusNtpPeerAdminTable OBJECT-TYPE
    SYNTAX          SEQUENCE OF SonusNtpPeerAdminEntry
    ACCESS          not-accessible
    STATUS          obsolete
    DESCRIPTION     
            "
             This table contains information about each NTP Server
             configured to provide network time.
             "
    ::= { sonusNtp 2 }

sonusNtpPeerAdminEntry OBJECT-TYPE
    SYNTAX          SonusNtpPeerAdminEntry
    ACCESS          not-accessible
    STATUS          obsolete
    DESCRIPTION     
            ""
    INDEX           { sonusNtpPeerAdminCeName, 
                      sonusNtpPeerAdminIpAddress }
    ::= { sonusNtpPeerAdminTable 1 }

SonusNtpPeerAdminEntry ::=
    SEQUENCE {
        sonusNtpPeerAdminCeName         String,
        sonusNtpPeerAdminIpAddress      InetAddressIP,
        sonusNtpPeerAdminVersion        SonusNtpPeerVersionType,
        sonusNtpPeerAdminMinPoll        SonusNtpPeerMinPollType,
        sonusNtpPeerAdminMaxPoll        SonusNtpPeerMaxPollType,
        sonusNtpPeerAdminState          INTEGER,
        sonusNtpPeerAdminRowstatus      RowStatus
    }

sonusNtpPeerAdminCeName OBJECT-TYPE
    SYNTAX          String (SIZE(0..255))
    ACCESS          not-accessible
    STATUS          obsolete
    DESCRIPTION     
            "
             The name of this server.
             "
    ::= { sonusNtpPeerAdminEntry 1 }

sonusNtpPeerAdminIpAddress OBJECT-TYPE
    SYNTAX          InetAddressIP
    ACCESS          not-accessible
    STATUS          obsolete
    DESCRIPTION     
            "
             The IP address of this NTP Peer.
             "
    ::= { sonusNtpPeerAdminEntry 2 }

sonusNtpPeerAdminVersion OBJECT-TYPE
    SYNTAX          SonusNtpPeerVersionType
    ACCESS          read-write
    STATUS          obsolete
    DESCRIPTION     
            "
             The NTP version of this NTP Server
             "
    DEFVAL          { version3 }
    ::= { sonusNtpPeerAdminEntry 3 }

sonusNtpPeerAdminMinPoll OBJECT-TYPE
    SYNTAX          SonusNtpPeerMinPollType
    ACCESS          read-write
    STATUS          obsolete
    DESCRIPTION     
            "
             The minimum poll interval to this NTP Server.
             Intervals are set in powers of 2.
             "
    DEFVAL          { 4 }
    ::= { sonusNtpPeerAdminEntry 4 }

sonusNtpPeerAdminMaxPoll OBJECT-TYPE
    SYNTAX          SonusNtpPeerMaxPollType
    ACCESS          read-write
    STATUS          obsolete
    DESCRIPTION     
            "
             The maxiimum poll interval to this NTP Server.
             Intervals are set in powers of 2.
             "
    DEFVAL          { 10 }
    ::= { sonusNtpPeerAdminEntry 5 }

sonusNtpPeerAdminState OBJECT-TYPE
    SYNTAX          INTEGER { disabled(1), enabled(2) }
    ACCESS          read-write
    STATUS          obsolete
    DESCRIPTION     
            "
             The configured state of the NTP peer entry.
             "
    ::= { sonusNtpPeerAdminEntry 6 }

sonusNtpPeerAdminRowstatus OBJECT-TYPE
    SYNTAX          RowStatus
    ACCESS          read-write
    STATUS          obsolete
    DESCRIPTION     
            ""
    ::= { sonusNtpPeerAdminEntry 7 }

sonusNtpPeerStatusTable OBJECT-TYPE
    SYNTAX          SEQUENCE OF SonusNtpPeerStatusEntry
    ACCESS          not-accessible
    STATUS          mandatory
    DESCRIPTION     
            "
             This table contains status information about each NTP peer.
             "
    ::= { sonusNtp 3 }

sonusNtpPeerStatusEntry OBJECT-TYPE
    SYNTAX          SonusNtpPeerStatusEntry
    ACCESS          not-accessible
    STATUS          mandatory
    DESCRIPTION     
            ""
    INDEX           { sonusNtpPeerStatusCeName, 
                      sonusNtpPeerStatusIpaddress }
    ::= { sonusNtpPeerStatusTable 1 }

SonusNtpPeerStatusEntry ::=
    SEQUENCE {
        sonusNtpPeerStatusCeName        String,
        sonusNtpPeerStatusIpaddress     InetAddressIP,
        sonusNtpPeerStatusState         SonusNtpPeerStateType,
        sonusNtpPeerStatusStratum       INTEGER,
        sonusNtpPeerStatusRefTime       SonusNtpPeerRefTimeType
    }

sonusNtpPeerStatusCeName OBJECT-TYPE
    SYNTAX          String (SIZE(0..255))
    ACCESS          not-accessible
    STATUS          mandatory
    DESCRIPTION     
            "
             The name of this server.
             "
    ::= { sonusNtpPeerStatusEntry 1 }

sonusNtpPeerStatusIpaddress OBJECT-TYPE
    SYNTAX          InetAddressIP
    ACCESS          not-accessible
    STATUS          mandatory
    DESCRIPTION     
            "
             The IP address of this NTP Peer.
             "
    ::= { sonusNtpPeerStatusEntry 2 }

sonusNtpPeerStatusState OBJECT-TYPE
    SYNTAX          SonusNtpPeerStateType
    ACCESS          read-only
    STATUS          mandatory
    DESCRIPTION     
            "
             Identifies the state of the NTP peer.
             "
    ::= { sonusNtpPeerStatusEntry 3 }

sonusNtpPeerStatusStratum OBJECT-TYPE
    SYNTAX          INTEGER
    ACCESS          read-only
    STATUS          mandatory
    DESCRIPTION     
            "
             Identifies the NTP peer's stratum level, 16 = invalid.
             "
    ::= { sonusNtpPeerStatusEntry 4 }

sonusNtpPeerStatusRefTime OBJECT-TYPE
    SYNTAX          SonusNtpPeerRefTimeType
    ACCESS          read-only
    STATUS          mandatory
    DESCRIPTION     
            "
             The time this NTP peer was last updated.
             "
    ::= { sonusNtpPeerStatusEntry 5 }

sonusNtpSystemStatusTable OBJECT-TYPE
    SYNTAX          SEQUENCE OF SonusNtpSystemStatusEntry
    ACCESS          not-accessible
    STATUS          mandatory
    DESCRIPTION     
            "
             This table contains system status information about NTP.
             "
    ::= { sonusNtp 4 }

sonusNtpSystemStatusEntry OBJECT-TYPE
    SYNTAX          SonusNtpSystemStatusEntry
    ACCESS          not-accessible
    STATUS          mandatory
    DESCRIPTION     
            ""
    INDEX           { sonusNtpSystemStatusCeName }
    ::= { sonusNtpSystemStatusTable 1 }

SonusNtpSystemStatusEntry ::=
    SEQUENCE {
        sonusNtpSystemStatusCeName      String,
        sonusNtpSystemStatusClock       SonusNtpSysClockType,
        sonusNtpSystemStatusRefTime     SonusNtpSysRefTimeType
    }

sonusNtpSystemStatusCeName OBJECT-TYPE
    SYNTAX          String (SIZE(0..255))
    ACCESS          not-accessible
    STATUS          mandatory
    DESCRIPTION     
            "
             The name of this server.
             "
    ::= { sonusNtpSystemStatusEntry 1 }

sonusNtpSystemStatusClock OBJECT-TYPE
    SYNTAX          SonusNtpSysClockType
    ACCESS          read-only
    STATUS          mandatory
    DESCRIPTION     
            "
             The ntp server time of last successful ntpq poll.
             "
    ::= { sonusNtpSystemStatusEntry 2 }

sonusNtpSystemStatusRefTime OBJECT-TYPE
    SYNTAX          SonusNtpSysRefTimeType
    ACCESS          read-only
    STATUS          mandatory
    DESCRIPTION     
            "
             The time this system was last updated.
             "
    ::= { sonusNtpSystemStatusEntry 3 }

sonusNtpServerAdminTable OBJECT-TYPE
    SYNTAX          SEQUENCE OF SonusNtpServerAdminEntry
    ACCESS          not-accessible
    STATUS          obsolete
    DESCRIPTION     
            "
             This table contains information about each NTP Server
             configured to provide network time.
             "
    ::= { sonusNtp 5 }

sonusNtpServerAdminEntry OBJECT-TYPE
    SYNTAX          SonusNtpServerAdminEntry
    ACCESS          not-accessible
    STATUS          obsolete
    DESCRIPTION     
            ""
    INDEX           { sonusNtpServerAdminIpAddress }
    ::= { sonusNtpServerAdminTable 1 }

SonusNtpServerAdminEntry ::=
    SEQUENCE {
        sonusNtpServerAdminIpAddress    InetAddressIP,
        sonusNtpServerAdminVersion      SonusNtpServerVersionType,
        sonusNtpServerAdminMinPoll      SonusNtpServerMinPollType,
        sonusNtpServerAdminMaxPoll      SonusNtpServerMaxPollType,
        sonusNtpServerAdminState        INTEGER,
        sonusNtpServerAdminRowstatus    RowStatus
    }

sonusNtpServerAdminIpAddress OBJECT-TYPE
    SYNTAX          InetAddressIP
    ACCESS          not-accessible
    STATUS          obsolete
    DESCRIPTION     
            "
             The IP address of this NTP Server.
             "
    ::= { sonusNtpServerAdminEntry 1 }

sonusNtpServerAdminVersion OBJECT-TYPE
    SYNTAX          SonusNtpServerVersionType
    ACCESS          read-write
    STATUS          obsolete
    DESCRIPTION     
            "
             The NTP version of this NTP Server
             "
    DEFVAL          { version3 }
    ::= { sonusNtpServerAdminEntry 2 }

sonusNtpServerAdminMinPoll OBJECT-TYPE
    SYNTAX          SonusNtpServerMinPollType
    ACCESS          read-write
    STATUS          obsolete
    DESCRIPTION     
            "
             The minimum poll interval to this NTP Server.
             Intervals are set in powers of 2.
             "
    DEFVAL          { 4 }
    ::= { sonusNtpServerAdminEntry 3 }

sonusNtpServerAdminMaxPoll OBJECT-TYPE
    SYNTAX          SonusNtpServerMaxPollType
    ACCESS          read-write
    STATUS          obsolete
    DESCRIPTION     
            "
             The maxiimum poll interval to this NTP Server.
             Intervals are set in powers of 2.
             "
    DEFVAL          { 10 }
    ::= { sonusNtpServerAdminEntry 4 }

sonusNtpServerAdminState OBJECT-TYPE
    SYNTAX          INTEGER { disabled(1), enabled(2) }
    ACCESS          read-write
    STATUS          obsolete
    DESCRIPTION     
            "
             The configured state of the NTP server entry.
             "
    ::= { sonusNtpServerAdminEntry 5 }

sonusNtpServerAdminRowstatus OBJECT-TYPE
    SYNTAX          RowStatus
    ACCESS          read-write
    STATUS          obsolete
    DESCRIPTION     
            ""
    ::= { sonusNtpServerAdminEntry 6 }

sonusNtpKeysTable OBJECT-TYPE
    SYNTAX          SEQUENCE OF SonusNtpKeysEntry
    ACCESS          not-accessible
    STATUS          obsolete
    DESCRIPTION     
            "
             This table contains information about the NTP authentication
             keys.
             "
    ::= { sonusNtp 6 }

sonusNtpKeysEntry OBJECT-TYPE
    SYNTAX          SonusNtpKeysEntry
    ACCESS          not-accessible
    STATUS          obsolete
    DESCRIPTION     
            ""
    INDEX           { sonusNtpKeysKeyId }
    ::= { sonusNtpKeysTable 1 }

SonusNtpKeysEntry ::=
    SEQUENCE {
        sonusNtpKeysKeyId               SonusNtpKeyIdType,
        sonusNtpKeysKeyType             SonusNtpKeyType,
        sonusNtpKeysKeyValue            SonusNtpKeysValueType,
        sonusNtpKeysRowstatus           RowStatus
    }

sonusNtpKeysKeyId OBJECT-TYPE
    SYNTAX          SonusNtpKeyIdType
    ACCESS          not-accessible
    STATUS          obsolete
    DESCRIPTION     
            "
             The ID of the NTP authentication key.
             "
    ::= { sonusNtpKeysEntry 1 }

sonusNtpKeysKeyType OBJECT-TYPE
    SYNTAX          SonusNtpKeyType
    ACCESS          read-write
    STATUS          obsolete
    DESCRIPTION     
            "
             The type of the NTP authentication key.
             "
    ::= { sonusNtpKeysEntry 2 }

sonusNtpKeysKeyValue OBJECT-TYPE
    SYNTAX          SonusNtpKeysValueType
    ACCESS          read-write
    STATUS          obsolete
    DESCRIPTION     
            "
             The NTP authentication key.
             "
    ::= { sonusNtpKeysEntry 3 }

sonusNtpKeysRowstatus OBJECT-TYPE
    SYNTAX          RowStatus
    ACCESS          read-write
    STATUS          obsolete
    DESCRIPTION     
            ""
    ::= { sonusNtpKeysEntry 8 }

END -- end of module SONUS-GEN2-NTP-SERVICES-MIB.
