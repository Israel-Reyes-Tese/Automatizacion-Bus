--
-- This SMIv2 module has been generated by smidump 0.2-cvs. Do not edit.
--

SONUS-TC DEFINITIONS ::= BEGIN

IMPORTS
    Integer32, MODULE-IDENTITY
        FROM SNMPv2-SMI
    TEXTUAL-CONVENTION
        FROM SNMPv2-TC
    sonusModules
        FROM SONUS-SMI;

sonusTextualConventions MODULE-IDENTITY
    LAST-UPDATED    "201107230000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "This module defines textual conventions used throughout
             sonus enterprise mibs."
    ::= { sonusModules 1 }


HwTypeID ::= TEXTUAL-CONVENTION
    STATUS          current
    DESCRIPTION     
            "Represents the different types of hardware components
             that are available in a GSX9000 shelf."
    SYNTAX          INTEGER { none(1), unknown(14), undefined(15), 
                        mns10(16), pns10(17), cns10(18), cns30(19), 
                        mta01(20), mna10(21), pna10(22), cna33(23), 
                        cna10(24), cna30(25), sonicPlane(26), 
                        fanTray(27), mta10(28), cna01(29), cna03(30), 
                        cns20(31), pns20(32), sps60(33), cna20(34), 
                        cna21(35), pna21(36), pna23(37), cns61(38), 
                        cna61(39), mta20(40), mta21(41), cna06(42), 
                        cns31(43), cns25(44), cna25(45), pns30(46), 
                        pna30(47), sonicPlane2(48), cna02(49), cna05(50), 
                        cns60(51), cns70(52), cna60(53), cna70(54), 
                        cna07(55), cpim70(56), cpim71(57), mns11(58), 
                        mta30(59), cns71(60), sps70(61), pna35(63), 
                        mns20(64), mna20(65), mna21(66), mna25(67), 
                        mns25(68), pns40(69), pns41(70), pna40(71), 
                        pna41(72), pna45(73), gns15(74), gna10(75), 
                        fmp10(76), gns16(77), gns30(78), gna30(79), 
                        fmp30(80), gca30(81), gca31(82), gns31(83), 
                        gns35(84), gns36(85), cns40(86), cns45(87), 
                        cns80(88), cns81(89), cns85(90), cns86(91), 
                        sps80(92), cna40(93), cna80(94), cna81(95), 
                        cpim81(96), cna08(97), cna04(98), mns21(99), 
                        mns26(100) }

ServerTypeID ::= TEXTUAL-CONVENTION
    STATUS          current
    DESCRIPTION     
            "Represents the different types of server modules
             which are available in a GSX9000 shelf."
    SYNTAX          INTEGER { mns10(16), pns10(17), cns10(18), cns30(19), 
                        cns20(31), pns20(32), cns25(44), cns31(43), 
                        pns30(46), cns61(38), cns60(51), cns70(52), 
                        mns11(58), cns71(60), sps70(61), mns20(64), 
                        mns25(68), pns40(69), pns41(70), gns15(74), 
                        gns16(77), gns30(78), gns31(83), gns35(84), 
                        gns36(85), cns40(86), cns45(87), cns80(88), 
                        cns81(89), cns85(90), cns86(91), sps80(92), 
                        mns21(99), mns26(100) }

AdapterTypeID ::= TEXTUAL-CONVENTION
    STATUS          current
    DESCRIPTION     
            "Represents the different types of adapter modules
             which are available in a GSX9000 shelf."
    SYNTAX          INTEGER { none(1), mna10(21), pna10(22), cna10(24), 
                        cna30(25), cna33(23), cna01(29), cna03(30), 
                        cna20(34), cna21(35), pna21(36), cna25(45), 
                        pna30(47), cna02(49), cna05(50), cna61(39), 
                        cna06(42), cna60(53), cna70(54), cna07(55), 
                        pna35(63), mna20(65), mna21(66), mna25(67), 
                        pna40(71), pna41(72), pna45(73), gna10(75), 
                        gna30(79), cna40(93), cna80(94), cna81(95), 
                        cna08(97), cna04(98) }

PimTypeID ::= TEXTUAL-CONVENTION
    STATUS          current
    DESCRIPTION     
            "Represents the different types of pim modules
             which are available in a GSX9000 shelf."
    SYNTAX          INTEGER { cpim70(56), cpim71(57), cpim81(96) }

ServerFunctionType ::= TEXTUAL-CONVENTION
    STATUS          current
    DESCRIPTION     
            "Represents the logical function of the server/adapter pair"
    SYNTAX          INTEGER { default(1), atm(2), mgmt(3), t1(4), e1(5), 
                        t3(6), sps(7), oc3tdm(8), pos(9), enet(10), 
                        enetLayer3(11), stm1oc3(12), stm0oc1(13), 
                        stm1oc3t1(14), stm1oc3e1(15), stm1oc3st(16), 
                        hiCapacityEnet(17), hiCapacityEnetLayer3(18), 
                        stm1oc3ds3(19) }

SonusShelfIndex ::= TEXTUAL-CONVENTION
    STATUS          current
    DESCRIPTION     
            "The index for a Sonus shelf."
    SYNTAX          Integer32 (1..6)

SonusSlotIndex ::= TEXTUAL-CONVENTION
    STATUS          current
    DESCRIPTION     
            "The index for a Sonus slot."
    SYNTAX          Integer32 (1..18)

SonusMnsSlotIndex ::= TEXTUAL-CONVENTION
    STATUS          current
    DESCRIPTION     
            "The index for a Sonus MNS slot."
    SYNTAX          Integer32 (1..2 | 9..10)

SonusPimIndex ::= TEXTUAL-CONVENTION
    STATUS          current
    DESCRIPTION     
            "The index for a Sonus Pim slot."
    SYNTAX          Integer32 (1..2)

SonusSfpIndex ::= TEXTUAL-CONVENTION
    STATUS          current
    DESCRIPTION     
            "The index for a Sonus Pim SFP slot."
    SYNTAX          Integer32 (1)

SonusEventString ::= TEXTUAL-CONVENTION
    DISPLAY-HINT    "255a"
    STATUS          current
    DESCRIPTION     
            "This data type is used to model textual information taken
             from the NVT ASCII character set."
    SYNTAX          OCTET STRING (SIZE(0..1023))

SonusEventClass ::= TEXTUAL-CONVENTION
    STATUS          current
    DESCRIPTION     
            "The categories of which events are classified by."
    SYNTAX          INTEGER { sysmgmt(1), callproc(2), resmgmt(3), 
                        directory(4), netmgmt(5), signaling(6), 
                        routing(7), trace(8) }

SonusEventLevel ::= TEXTUAL-CONVENTION
    STATUS          current
    DESCRIPTION     
            "The severity level of events."
    SYNTAX          INTEGER { critical(1), major(2), minor(3), info(4) }

SonusEventFilterLevel ::= TEXTUAL-CONVENTION
    STATUS          current
    DESCRIPTION     
            "The filter severity level of events."
    SYNTAX          INTEGER { noevents(0), critical(1), major(2), 
                        minor(3), info(4) }

SonusName ::= TEXTUAL-CONVENTION
    DISPLAY-HINT    "255a"
    STATUS          current
    DESCRIPTION     
            "This data type is used to model textual information taken
             from the NVT ASCII character set.  The SonusName type is used
             to label Sonus Named objects."
    SYNTAX          OCTET STRING (SIZE(1..23))

SonusExtendedName ::= TEXTUAL-CONVENTION
    DISPLAY-HINT    "255a"
    STATUS          current
    DESCRIPTION     
            "This data type is used to model textual information taken
             from the NVT ASCII character set.  The SonusExtendedName type is used
             to label Sonus Named extended objects."
    SYNTAX          OCTET STRING (SIZE(1..64))

SonusNameReference ::= TEXTUAL-CONVENTION
    DISPLAY-HINT    "255a"
    STATUS          current
    DESCRIPTION     
            "This data type is used to model textual information taken
             from the NVT ASCII character set.  The SonusNameReference
             type is used to refer to Sonus Named objects."
    SYNTAX          OCTET STRING (SIZE(0..23))

SonusBoolean ::= TEXTUAL-CONVENTION
    STATUS          current
    DESCRIPTION     
            "This data type is used to model a boolean value expressed
             as true or false."
    SYNTAX          INTEGER { false(1), true(2) }

PointCode ::= TEXTUAL-CONVENTION
    STATUS          current
    DESCRIPTION     
            "A three octet data type representing the SS7 PointCode.
             The octets represent Network-Cluster-Member values
             respectively."
    SYNTAX          Integer32 (0..16777215)

SonusSysId ::= TEXTUAL-CONVENTION
    STATUS          current
    DESCRIPTION     
            "An INTEGER representing the sub-system identifiers for
             software components in a GSX9000 node."
    SYNTAX          INTEGER { evlog(1), ncm(2), nrs(3), fm(4), sm(5), 
                        sma(6), nrm(7), nrma(8), brm(9), drm(10), 
                        prm(11), xrm(12), cc(13), icm(14), ipdh(15), 
                        epdh(16), ds(17), debug(18), trm(19), sg(20), 
                        gwfe(21), gwsg(22), sg-7(23), rtcp(24), tccs(25), 
                        cli(26), snmp(27), hsim(28), lesim(29), 
                        ss7fe(30), led(31), param(32), cb(33), acm(34), 
                        ntp(35), diag(36), cam(37), asg(38), mgsg(39), 
                        ipdcfe(40), ltt(41), tm(42), stm(43), sta(44), 
                        nfs(45), isdn(46), enm(47), arm(48), arma(49), 
                        rtm(50), psdh(51), atmrm(52), dcl(53), psd(54), 
                        cassg(55), pfa(56), mgcpfe(57), spm(58), 
                        spma(59), h323sg(60), h323fe(61), sipsg(62), 
                        sipfe(63), dnsc(64), ncomm(69), dm(70), ftpd(71), 
                        dd(72), fmwd(73), mtrm(74), sec(75), cmtsg(76), 
                        mtp2(77), tmw(78), ipm(80), im(81), pchk(82), 
                        isakpd(83), dlcm(84), lt303(85), ars(86), 
                        dflush(87), diamc(88) }

SonusServiceState ::= TEXTUAL-CONVENTION
    STATUS          current
    DESCRIPTION     
            "The service state of a resource."
    SYNTAX          INTEGER { outOfService(1), inService(2) }

SonusAdminState ::= TEXTUAL-CONVENTION
    STATUS          current
    DESCRIPTION     
            "The administrative state of a resource."
    SYNTAX          INTEGER { disabled(1), enabled(2) }

SonusAdminAction ::= TEXTUAL-CONVENTION
    STATUS          current
    DESCRIPTION     
            "The action assignment of a resource."
    SYNTAX          INTEGER { dryUp(1), force(2) }

SonusCircuitState ::= TEXTUAL-CONVENTION
    STATUS          current
    DESCRIPTION     
            "The state of an ISUP circuit."
    SYNTAX          INTEGER { unblocked(1), blocked(2), 
                        transientUnblock(3), transientBlock(4), 
                        notAvailable(5) }

SonusMtaSlotIndex ::= TEXTUAL-CONVENTION
    STATUS          current
    DESCRIPTION     
            "The index identifying an MTA slot"
    SYNTAX          INTEGER { mta1(1), mta2(2) }

SonusTimingSource ::= TEXTUAL-CONVENTION
    STATUS          current
    DESCRIPTION     
            "Timing source types. extClkA and extClkB specifiy
             either BITS or SETS clock inputs, depending
             on whether the MTA is an MTA10(BITS) or MTA20(SETS).
             refClkA and refClkB indicate recovered/derived from
             a DS1 (for instance)"
    SYNTAX          INTEGER { extClkA(1), extClkB(2), refClkA(3), 
                        refClkB(4), oscillator(5), holdover(6) }

SonusSoftwareVersion ::= TEXTUAL-CONVENTION
    DISPLAY-HINT    "1d.1d.1d.1d.2d"
    STATUS          current
    DESCRIPTION     
            "Octet string that identifies the version of the runtime
             software application:
             
             Byte(s)  Code
             -------  ----
             0        major version
             1        minor version
             2        release version
             3        type (1:alpha, 2:beta, 3:release, 4:special)
             4-5      type build number"
    SYNTAX          OCTET STRING (SIZE(6))

SonusSystemName ::= TEXTUAL-CONVENTION
    DISPLAY-HINT    "255a"
    STATUS          current
    DESCRIPTION     
            "This data type refers to the name of networking device."
    SYNTAX          OCTET STRING (SIZE(0..255))

SonusTrapType ::= TEXTUAL-CONVENTION
    STATUS          current
    DESCRIPTION     
            "The type of trap PDU to be generated:
             
             none   - no PDU is generated
             trapv1 - SNMPv1-Trap-PDU
             trapv2 - SNMPv2-Trap-PDU
             inform - InformRequestPDU"
    SYNTAX          INTEGER { none(0), trapv1(1), trapv2(2), inform(3) }

SonusAccessLevel ::= TEXTUAL-CONVENTION
    STATUS          current
    DESCRIPTION     
            "The User and Mgmt Client access level."
    SYNTAX          INTEGER { readOnly(1), readWrite(2), admin(3) }

SonusPointCode ::= TEXTUAL-CONVENTION
    DISPLAY-HINT    "2d-"
    STATUS          current
    DESCRIPTION     
            "Octet string that represents a point code.  A point code
             may be comprised of one or more sub-values.  Each sub-value
             is stored in two bytes of the octet string.  The first two
             bytes of the octet string contains the count of the two-byte
             sub-values that comprise the point code.  The remaining bytes
             of the octet string contain the two-byte sub-values.
             
             For example:
             
             Point Code          Octet String
             ----------          ------------
             4-200-7             00 04 00 C8 00 07
             2-1000-3            00 02 03 E8 00 08
             15-750              00 FF 02 EE
             16000               3E 80"
    SYNTAX          OCTET STRING (SIZE(1..64))

SonusPointCodeFormat ::= TEXTUAL-CONVENTION
    DISPLAY-HINT    "1d-"
    STATUS          current
    DESCRIPTION     
            "Octet string that represents a point code format, such
             as 2-10-2, 3-8-3, 4-10 or 14.  A point code format
             specifies the number of bits that each sub-value of a
             point code value is stored in.  The total number of bits
             should be 14.  A point code format is used to specify
             how a point code value should be stored in a 14 bit value.
             
             A point code format may be comprised of one or more numbers.
             Each number is stored in one byte of the octet string.  The
             first byte of the octet string contains the count of the
             one-byte numbers that comprise the point code format.  The
             remaining bytes of the octet string contain the one-byte
             numbers.
             
             For example:
             
             Point Code Format   Octet String
             -----------------   ------------
             3-8-3               03 08 03
             2-10-2              02 0A 02
             4-10                04 0A
             14                  0E"
    SYNTAX          OCTET STRING (SIZE(1..32))

SonusSupportFlag ::= TEXTUAL-CONVENTION
    STATUS          current
    DESCRIPTION     
            "The flag to indicate if the attribute is supported."
    SYNTAX          INTEGER { unsupported(1), supported(2) }

SonusGMTTime ::= TEXTUAL-CONVENTION
    DISPLAY-HINT    "1d:1d:1d.1d"
    STATUS          current
    DESCRIPTION     
            "The pure GMT time specification ( without YY-MM-DD ) 
             for daily reoccurring events.
             
             field  octets  contents                  range
             -----  ------  --------                  -----
               1       1    hour                      0..23
               2       2    minutes                   0..59
               3       3    seconds                   0..60
                            (use 60 for leap-second)
               4       4    deci-seconds              0..9
             "
    SYNTAX          OCTET STRING (SIZE(4))

SonusLinkVersion ::= TEXTUAL-CONVENTION
    DISPLAY-HINT    "1d.1d"
    STATUS          current
    DESCRIPTION     
            "Octet string that identifies the stream versions from 
             GSX to remote peripherals :
             
              Byte(s)  Code
              -------  ----
              0        major version
              1        minor version"
    SYNTAX          OCTET STRING (SIZE(2))

SonusAcctRecordType ::= TEXTUAL-CONVENTION
    STATUS          current
    DESCRIPTION     
            "Represents the different types of call accounting records
             that are available in Sonus Products."
    SYNTAX          INTEGER { start(1), stop(2), attempt(3), 
                        intermediate(4), reboot(5), switchover(6) }

SonusTransportProtocolType ::= TEXTUAL-CONVENTION
    STATUS          current
    DESCRIPTION     
            "The tranport protocol selected by a Service Group."
    SYNTAX          INTEGER { none(0), tcp(1), udp(2), sctp(4), 
                        tls-tcp(8) }

SonusTlsCipherSuite ::= TEXTUAL-CONVENTION
    STATUS          current
    DESCRIPTION     
            "The cipher suites of Transport Layler Security.
             The first component of the suite name below
             (e.g. rsa ) identifies the authentication mechanism
             used in the TLS Handshake protocol. The middle components
             (e.g. aes128) identifie the confidentiality cipher
             and mode used for the TLS Record protocol. The last
             component (e.g. SHA) identifies the integrity cipher
             used for the TLS Record protocol."
    SYNTAX          INTEGER { nosuite(0), rsa-with-null-sha(1), 
                        rsa-with-aes-128-cbc-sha(2), 
                        rsa-with-3des-ede-cbc-sha(3) }

SonusSipSmmCriterionType ::= TEXTUAL-CONVENTION
    STATUS          current
    DESCRIPTION     
            "Represents the SIP Message Manipulation Criterion Types"
    SYNTAX          INTEGER { message(1), header(2), parameter(3), 
                        token(4), variable(5), globalvar(6), msgbody(7) }

SonusSipSmmParamType ::= TEXTUAL-CONVENTION
    STATUS          current
    DESCRIPTION     
            "Represents the SIP Message Manipulation Parameter Types"
    SYNTAX          INTEGER { userinfo(1), uri(2), generic(3) }

SonusSipSmmTokenType ::= TEXTUAL-CONVENTION
    STATUS          current
    DESCRIPTION     
            "Represents the SIP Message Manipulation Token Types"
    SYNTAX          INTEGER { uridisplayname(1), uriusername(2), 
                        urihostname(3), urischeme(4), urihostport(5) }

SonusSipSmmActionType ::= TEXTUAL-CONVENTION
    STATUS          current
    DESCRIPTION     
            "Represents the SIP Message Manipulation Action Types"
    SYNTAX          INTEGER { header(1), parameter(2), token(3), 
                        variable(4), msgbody(5) }

SonusSipSmmOperationType ::= TEXTUAL-CONVENTION
    STATUS          current
    DESCRIPTION     
            "Represents the SIP Message Manipulation Operation Types"
    SYNTAX          INTEGER { add(1), delete(2), modify(3), store(4), 
                        append(5), regsub(6), regdel(7), regpresub(8), 
                        regpredel(9), regpostsub(10), regpostdel(11), 
                        regprepend(12), regappend(13), regstore(14) }

SonusSipSmmVariableType ::= TEXTUAL-CONVENTION
    STATUS          current
    DESCRIPTION     
            "Represents the SIP Message Manipulation Variable Types"
    SYNTAX          INTEGER { var1(1), var2(2), var3(3), var4(4), 
                        var5(5), var6(6), var7(7), var8(8), var9(9), 
                        var10(10) }

SonusSipSmmHdrInstance ::= TEXTUAL-CONVENTION
    STATUS          current
    DESCRIPTION     
            "Represents the SIP header instance for Message Manipulation."
    SYNTAX          INTEGER { one(1), two(2), three(3), four(4), five(5), 
                        six(6), seven(7), eight(8), nine(9), ten(10), 
                        all(63), last(64) }

SonusSipSmmHdrRange ::= TEXTUAL-CONVENTION
    STATUS          current
    DESCRIPTION     
            "Represents the SIP header range for Message Manipulation."
    SYNTAX          INTEGER { two(2), three(3), four(4), five(5), six(6), 
                        seven(7), eight(8), nine(9), ten(10), last(64) }

SonusSipSmmGlobalVariableType ::= TEXTUAL-CONVENTION
    STATUS          current
    DESCRIPTION     
            "Represents the SIP Message Manipulation Environment Variable Types"
    SYNTAX          INTEGER { srcipaddr(1), srcport(2) }

END -- end of module SONUS-TC.
