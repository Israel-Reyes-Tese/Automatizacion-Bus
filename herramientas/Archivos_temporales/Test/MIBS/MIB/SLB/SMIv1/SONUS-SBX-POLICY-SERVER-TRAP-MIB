--
-- This SMIv1 module has been generated by smidump 0.2-cvs. Do not edit.
--

SONUS-SBX-POLICY-SERVER-TRAP-MIB DEFINITIONS ::= BEGIN

IMPORTS
    OBJECT-TYPE
        FROM RFC-1212
    TRAP-TYPE
        FROM RFC-1215
    Counter, IpAddress
        FROM RFC1155-SMI
    DisplayString
        FROM SNMPv2-TC
    SonusName
        FROM SONUS-COMMON-TC
    sonusAlarmDescription, sonusAlarmLevel, sonusAlarmNodeID, 
    sonusAlarmSequenceId, sonusAlarmTime
        FROM SONUS-COMMON-TRAP-MIB
    sonusSBX5000NotificationMIBs
        FROM SONUS-SMI;

sonusSbxPolicyServerTrapsMIB OBJECT IDENTIFIER
    ::= { sonusSBX5000NotificationMIBs 2 }

-- sonusSbxPolicyServerTrapsMIB MODULE-IDENTITY
--     LAST-UPDATED    "201003120000Z"
--     ORGANIZATION    
--             "Sonus Networks, Inc."
--     CONTACT-INFO    
--             "   Customer Support    
--              Sonus Networks, Inc.
--              7 Technology Park Drive
--              Westford, MA 01886
--              USA
--              
--              Tel: 978-614-8100
--              Fax: 978-614-8609"
--     DESCRIPTION     
--             "The MIB Module for SoftSwitch Policy Execution Server Management."
--     ::= { sonusSBX5000NotificationMIBs 2 }


sonusPolicyServerTraps OBJECT IDENTIFIER
    ::= { sonusSbxPolicyServerTrapsMIB 1 }

sonusPolicyServerNotifications OBJECT IDENTIFIER
    ::= { sonusPolicyServerTraps 1 }

sonusPolicyServerNotificationPrefix OBJECT IDENTIFIER
    ::= { sonusPolicyServerNotifications 0 }

sonusPolicyServerNotificationObjects OBJECT IDENTIFIER
    ::= { sonusPolicyServerNotifications 1 }

sonusPolicyServerRegisterReason OBJECT-TYPE
    SYNTAX          INTEGER { new(1) }
    ACCESS          read-only
    STATUS          mandatory
    DESCRIPTION     
            "Register operation reason."
    ::= { sonusPolicyServerNotificationObjects 1 }

sonusPolicyServerUnregisterReason OBJECT-TYPE
    SYNTAX          INTEGER { threshold(1), unknown(2), duplicate(3), 
                        lostConnection(4), clientUnregistered(5), 
                        unknownGateway(6), maxClientsExceeded(7) }
    ACCESS          read-only
    STATUS          mandatory
    DESCRIPTION     
            "Unregister operation reason."
    ::= { sonusPolicyServerNotificationObjects 2 }

sonusPolicyServerCongestionLevel OBJECT-TYPE
    SYNTAX          Gauge
    ACCESS          read-only
    STATUS          mandatory
    DESCRIPTION     
            "Congestion level to which the PSX is transitioning."
    ::= { sonusPolicyServerNotificationObjects 3 }

sonusPolicyServerPipeErrorCode OBJECT-TYPE
    SYNTAX          Gauge
    ACCESS          read-only
    STATUS          mandatory
    DESCRIPTION     
            "The unix error code, if any, will be available in this field."
    ::= { sonusPolicyServerNotificationObjects 4 }

sonusPolicyServerPipeMwiQueueLevel OBJECT-TYPE
    SYNTAX          INTEGER { mwiQueueSafe(0), mwiQueueLevelMinor(1), 
                        mwiQueueLevelMajor(2), mwiQueueLevelCritical(3) }
    ACCESS          read-only
    STATUS          mandatory
    DESCRIPTION     
            "This field contains the MWI queue level information."
    ::= { sonusPolicyServerNotificationObjects 5 }

sonusPolicyServerDbOperationFailureReason OBJECT-TYPE
    SYNTAX          INTEGER { connection(1), update(2) }
    ACCESS          read-only
    STATUS          mandatory
    DESCRIPTION     
            "DB operation failure reason."
    ::= { sonusPolicyServerNotificationObjects 6 }

sonusPolicyServerTMIdentifier1 OBJECT-TYPE
    SYNTAX          DisplayString
    ACCESS          read-only
    STATUS          mandatory
    DESCRIPTION     
            "Identifies the control. For Destination and Origination element type 
             this is the national number. For Trunkgroup type, it is the trunkgroup 
             identifier"
    ::= { sonusPolicyServerNotificationObjects 7 }

sonusPolicyServerTMIdentifier2 OBJECT-TYPE
    SYNTAX          DisplayString
    ACCESS          read-only
    STATUS          mandatory
    DESCRIPTION     
            "Identifies the control.  For Destination and Origination element type 
             this is the country code. For Trunkgroup type it is the gateway identifier."
    ::= { sonusPolicyServerNotificationObjects 8 }

sonusPolicyServerTMElementType OBJECT-TYPE
    SYNTAX          INTEGER { destination(1), trunkgroup(2), 
                        origination(3), routingLabel(4) }
    ACCESS          read-only
    STATUS          mandatory
    DESCRIPTION     
            "Type of element on which this traffic management control operates."
    ::= { sonusPolicyServerNotificationObjects 9 }

sonusPolicyServerTMProvControlType OBJECT-TYPE
    SYNTAX          INTEGER { unknown(0), canf(1), cantdr(2), skipdr(3), 
                        skipar(4), dialeddestination(5), 
                        translateddestination(6), cantar(7), strdr(8), 
                        strar(9), irrdr(10), sirrdr(11), orrdr(12), 
                        sorrdr(13), rralternate(14), irrar(15), 
                        sirrar(16), orrar(17), sorrar(18), 
                        origination(19), finalCallingNumber(20), 
                        finalDestination(21), 
                        contractorBasedOrigination(22), 
                        cdDNBasedDestination(23) }
    ACCESS          read-only
    STATUS          mandatory
    DESCRIPTION     
            "Type of control provisioned."
    ::= { sonusPolicyServerNotificationObjects 10 }

sonusPolicyServerTMAppliedControlType OBJECT-TYPE
    SYNTAX          INTEGER { dialeddestination(1), 
                        translateddestination(2), origination(3), 
                        finalCallingNumber(4), finalDestination(5), 
                        contractorBasedOrigination(6), 
                        cdDNBasedDestination(7) }
    ACCESS          read-only
    STATUS          mandatory
    DESCRIPTION     
            "Type of control applied."
    ::= { sonusPolicyServerNotificationObjects 11 }

sonusPolicyServerTMAddressNature OBJECT-TYPE
    SYNTAX          INTEGER { unknown(0), national(1), international(2), 
                        nochange(3), subscriber(4), networkspecific(5), 
                        natureunknown(6), subscriberoperator(7), 
                        nationaloperator(8), internationaloperator(9), 
                        testcode(10), nonumberoprequested(11), 
                        nonumbercutthrough(12), nature950(13), 
                        anicallingpartysubscriber(14), 
                        aninotavailable(15), anicallingpartynational(16), 
                        anicalledpartysubscriber(17), 
                        anicalledpartynonumber(18), 
                        anicalledpartynational(19), ss7reserved(20), 
                        nationalnotrestricted(21), 
                        nationalrestricted(22), 
                        internationalnotrestricted(23), 
                        internationalrestricted(24), 
                        partialcallinglineid(126), all(255) }
    ACCESS          read-only
    STATUS          mandatory
    DESCRIPTION     
            "Specifies whether the call was national,international or any other type 
             like network specific."
    ::= { sonusPolicyServerNotificationObjects 12 }

sonusPolicyServerClientName OBJECT-TYPE
    SYNTAX          SonusName
    ACCESS          read-only
    STATUS          mandatory
    DESCRIPTION     
            "Name of the PolicyServer client, usually a gateway."
    ::= { sonusPolicyServerNotificationObjects 13 }

sonusPolicyServerLWRESDBlacklisted OBJECT-TYPE
    SYNTAX          DisplayString
    ACCESS          read-only
    STATUS          mandatory
    DESCRIPTION     
            "Specifies the DNS Server ip."
    ::= { sonusPolicyServerNotificationObjects 14 }

sonusPolicyServerLWRESDWhitelisted OBJECT-TYPE
    SYNTAX          DisplayString
    ACCESS          read-only
    STATUS          mandatory
    DESCRIPTION     
            "Specifies the DNS Server ip."
    ::= { sonusPolicyServerNotificationObjects 15 }

sonusPolicyServerADServerSyncFailed OBJECT-TYPE
    SYNTAX          DisplayString
    ACCESS          read-only
    STATUS          mandatory
    DESCRIPTION     
            "Specifies the AD Server sync status."
    ::= { sonusPolicyServerNotificationObjects 16 }

sonusPolicyServerADServerSyncSuccess OBJECT-TYPE
    SYNTAX          DisplayString
    ACCESS          read-only
    STATUS          mandatory
    DESCRIPTION     
            "Specifies the AD Server sync status."
    ::= { sonusPolicyServerNotificationObjects 17 }

sonusPolicyServerDbOperationFailureNotification TRAP-TYPE
    ENTERPRISE      sonusPolicyServerNotifications
    VARIABLES       { sonusAlarmNodeID, sonusAlarmLevel, 
                      sonusAlarmSequenceId, sonusAlarmTime, 
                      sonusAlarmDescription, 
                      sonusPolicyServerDbOperationFailureReason }
--     STATUS          mandatory
    DESCRIPTION     
            "DB operation failed. Look at the failure reason."
    ::= 1

sonusPolicyServerRegisterNotification TRAP-TYPE
    ENTERPRISE      sonusPolicyServerNotifications
    VARIABLES       { sonusAlarmNodeID, sonusAlarmLevel, 
                      sonusAlarmSequenceId, sonusAlarmTime, 
                      sonusAlarmDescription, sonusPolicyServerClientName, 
                      sonusPolicyServerRegisterReason }
--     STATUS          mandatory
    DESCRIPTION     
            "Register operation. Look at register reason."
    ::= 2

sonusPolicyServerUnregisterNotification TRAP-TYPE
    ENTERPRISE      sonusPolicyServerNotifications
    VARIABLES       { sonusAlarmNodeID, sonusAlarmLevel, 
                      sonusAlarmSequenceId, sonusAlarmTime, 
                      sonusAlarmDescription, sonusPolicyServerClientName, 
                      sonusPolicyServerUnregisterReason }
--     STATUS          mandatory
    DESCRIPTION     
            "Unregister operation. Look at unregister reason."
    ::= 3

sonusPolicyServerScpCommunicationUpNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "Communication to SCP is UP."
    ::= 4

sonusPolicyServerScpCommunicationDownNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "Communication to SCP is DOWN."
    ::= 5

sonusPolicyServerCallProcessTimeHighThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX overload condition set."
    ::= 6

sonusPolicyServerCallProcessTimeLowThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX overload condition cleared."
    ::= 7

sonusPolicyServerScpTimeoutNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "SCP queries timing out."
    ::= 8

sonusPolicyServerNoRouteFoundNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "No route found for Pes request"
    ::= 9

sonusPolicyServerTMControlAppliedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMAppliedControlType, 
                      sonusPolicyServerTMAddressNature }
--     STATUS          mandatory
    DESCRIPTION     
            "A traffic control has been applied."
    ::= 10

sonusPolicyServerCongestionNotification TRAP-TYPE
    ENTERPRISE      sonusPolicyServerNotifications
    VARIABLES       { sonusAlarmNodeID, sonusAlarmLevel, 
                      sonusAlarmSequenceId, sonusAlarmTime, 
                      sonusAlarmDescription, 
                      sonusPolicyServerCongestionLevel }
--     STATUS          mandatory
    DESCRIPTION     
            "The PSX congestion control level is changed"
    ::= 11

sonusPolicyServerDbConnSuccessNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "The 'pes' process establishes connection to the PSX DB."
    ::= 12

sonusPolicyServerPipeCommunicationDownNotification TRAP-TYPE
    ENTERPRISE      sonusPolicyServerNotifications
    VARIABLES       { sonusAlarmNodeID, sonusAlarmLevel, 
                      sonusAlarmSequenceId, sonusAlarmTime, 
                      sonusAlarmDescription, 
                      sonusPolicyServerPipeErrorCode }
--     STATUS          mandatory
    DESCRIPTION     
            "'pes' process was unable to establish connection with master 'pipe' process."
    ::= 13

sonusPolicyServerPipeRegistrationFailureNotification TRAP-TYPE
    ENTERPRISE      sonusPolicyServerNotifications
    VARIABLES       { sonusAlarmNodeID, sonusAlarmLevel, 
                      sonusAlarmSequenceId, sonusAlarmTime, 
                      sonusAlarmDescription, 
                      sonusPolicyServerPipeErrorCode }
--     STATUS          mandatory
    DESCRIPTION     
            "'pes' process was unable to register with master 'pipe' process."
    ::= 14

sonusPolicyServerPipeIOErrorNotification TRAP-TYPE
    ENTERPRISE      sonusPolicyServerNotifications
    VARIABLES       { sonusAlarmNodeID, sonusAlarmLevel, 
                      sonusAlarmSequenceId, sonusAlarmTime, 
                      sonusAlarmDescription, 
                      sonusPolicyServerPipeErrorCode }
--     STATUS          mandatory
    DESCRIPTION     
            "'pes' process was unable to send/receive an update to 'pipe' process."
    ::= 15

sonusPolicyServerPipeMWIQueueLevelChanged TRAP-TYPE
    ENTERPRISE      sonusPolicyServerNotifications
    VARIABLES       { sonusAlarmNodeID, sonusAlarmLevel, 
                      sonusAlarmSequenceId, sonusAlarmTime, 
                      sonusAlarmDescription, 
                      sonusPolicyServerPipeMwiQueueLevel }
--     STATUS          mandatory
    DESCRIPTION     
            "The MWI queue level changed. There is a safe level, followed by yellow, 
             orange and red levels. If the incoming message rate is far higher than 
             the consumption rate (updating the database), then the queue builds up 
             and crosses levels. Once the red level is reached, incoming messages 
             will be floored (not put in the queue)."
    ::= 16

sonusPolicyServerPipeCommunicationUpNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "'pes' process establishes connection with master 'pipe' process."
    ::= 17

sonusPolicyServerPipeRegistrationSuccessNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "'pes' process registers with master 'pipe' process."
    ::= 18

sonusPolicyServerLwresdCommunicationUpNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "Communication to LWRESD is UP."
    ::= 19

sonusPolicyServerLwresdCommunicationDownNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "Communication to LWRESD is DOWN."
    ::= 20

sonusPolicyServerSqlErrorHighThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PES communication ports closed due to excessive failures."
    ::= 21

sonusPolicyServerInternalErrorHighThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX excessive Internal communication failure crossed configured threshold."
    ::= 22

sonusPolicyServerExternalErrorHighThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX excessive External communication failure crossed configured threshold."
    ::= 23

sonusPolicyServerInternalErrorLowThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX excessive Internal communication failure cleared."
    ::= 24

sonusPolicyServerExternalErrorLowThresholdNotification TRAP-TYPE
    ENTERPRISE      sonusPolicyServerNotifications
    VARIABLES       { sonusAlarmNodeID, sonusAlarmLevel, 
                      sonusAlarmSequenceId, sonusAlarmTime, 
                      sonusAlarmDescription }
--     STATUS          mandatory
    DESCRIPTION     
            "PSX excessive External communication failure cleared."
    ::= 25

sonusPipeTMControlProvisionedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
--     STATUS          mandatory
    DESCRIPTION     
            "A traffic control has been provisioned."
    ::= 26

sonusPipeTMControlRemovedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
--     STATUS          mandatory
    DESCRIPTION     
            "A traffic control has been removed."
    ::= 27

sonusPipeTMControlModifiedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
--     STATUS          mandatory
    DESCRIPTION     
            "A traffic control has been modified."
    ::= 28

sonusPolicyServerLWRESDDNSServerBlacklistedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerLWRESDBlacklisted }
--     STATUS          mandatory
    DESCRIPTION     
            "ENUM Server is Blacklisted."
    ::= 29

sonusPolicyServerLWRESDDNSServerRecoveredNotification TRAP-TYPE
    ENTERPRISE      sonusPolicyServerNotifications
    VARIABLES       { sonusAlarmNodeID, sonusAlarmLevel, 
                      sonusAlarmSequenceId, sonusAlarmTime, 
                      sonusAlarmDescription, 
                      sonusPolicyServerLWRESDWhitelisted }
--     STATUS          mandatory
    DESCRIPTION     
            "ENUM Server is Whitelisted."
    ::= 30

sonusPolicyServerLWRESDENUMServerBlacklistedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerLWRESDBlacklisted }
--     STATUS          mandatory
    DESCRIPTION     
            "ENUM Server is Blacklisted."
    ::= 31

sonusPolicyServerLWRESDENUMServerRecoveredNotification TRAP-TYPE
    ENTERPRISE      sonusPolicyServerNotifications
    VARIABLES       { sonusAlarmNodeID, sonusAlarmLevel, 
                      sonusAlarmSequenceId, sonusAlarmTime, 
                      sonusAlarmDescription, 
                      sonusPolicyServerLWRESDWhitelisted }
--     STATUS          mandatory
    DESCRIPTION     
            "ENUM Server is Whitelisted."
    ::= 32

sonusPolicyServerADServerSyncFailedNotification TRAP-TYPE
    ENTERPRISE      sonusPolicyServerNotifications
    VARIABLES       { sonusAlarmNodeID, sonusAlarmLevel, 
                      sonusAlarmSequenceId, sonusAlarmTime, 
                      sonusAlarmDescription, 
                      sonusPolicyServerADServerSyncFailed }
--     STATUS          mandatory
    DESCRIPTION     
            "AD Server sync failed."
    ::= 33

sonusPolicyServerADServerSyncSuccessNotification TRAP-TYPE
    ENTERPRISE      sonusPolicyServerNotifications
    VARIABLES       { sonusAlarmNodeID, sonusAlarmLevel, 
                      sonusAlarmSequenceId, sonusAlarmTime, 
                      sonusAlarmDescription, 
                      sonusPolicyServerADServerSyncSuccess }
--     STATUS          mandatory
    DESCRIPTION     
            "Ad Server sync up and syncing."
    ::= 34

END -- end of module SONUS-SBX-POLICY-SERVER-TRAP-MIB.
