--
-- This SMIv1 module has been generated by smidump 0.2-cvs. Do not edit.
--

CPQSTDEQ-MIB DEFINITIONS ::= BEGIN

IMPORTS
    compaq, cpqHoTrapFlags
        FROM CPQHOST-MIB
    OBJECT-TYPE
        FROM RFC-1212
    TRAP-TYPE
        FROM RFC-1215
    DisplayString, sysName
        FROM RFC1213-MIB;

TruthValue ::=
    INTEGER { false(1), true(2) }

cpqStdEquipment OBJECT IDENTIFIER
    ::= { compaq 1 }

cpqSeMibRev OBJECT IDENTIFIER
    ::= { cpqStdEquipment 1 }

cpqSeMibRevMajor OBJECT-TYPE
    SYNTAX          INTEGER (1..65535)
    ACCESS          read-only
    STATUS          mandatory
    DESCRIPTION     
            "The Major Revision level of the MIB.
             
             A change in the major revision level represents a major change
             in the architecture of the MIB.  A change in the major revision
             level may indicate a significant change in the information
             supported and/or the meaning of the supported information,
             correct interpretation of data may require a MIB document with
             the same major revision level."
    ::= { cpqSeMibRev 1 }

cpqSeMibRevMinor OBJECT-TYPE
    SYNTAX          INTEGER (0..65535)
    ACCESS          read-only
    STATUS          mandatory
    DESCRIPTION     
            "The Minor Revision level of the MIB.
             
             A change in the minor revision level may represent some minor
             additional support, no changes to any pre-existing information
             has occurred."
    ::= { cpqSeMibRev 2 }

cpqSeMibCondition OBJECT-TYPE
    SYNTAX          INTEGER { other(1), ok(2), degraded(3), failed(4) }
    ACCESS          read-only
    STATUS          mandatory
    DESCRIPTION     
            "The overall condition.
             
             This object represents the overall status of the server
             represented by this MIB."
    ::= { cpqSeMibRev 3 }

cpqSeComponent OBJECT IDENTIFIER
    ::= { cpqStdEquipment 2 }

cpqSeInterface OBJECT IDENTIFIER
    ::= { cpqSeComponent 1 }

cpqSeOsCommon OBJECT IDENTIFIER
    ::= { cpqSeInterface 4 }

cpqSeOsCommonPollFreq OBJECT-TYPE
    SYNTAX          INTEGER (0..65535)
    ACCESS          read-write
    STATUS          mandatory
    DESCRIPTION     
            "The Insight Agent's polling frequency.
             
             The frequency, in seconds, at which the Insight Agent requests
             information from the device driver.  A frequency of zero (0)
             indicates that the Insight Agent retrieves the information upon
             request of a management station, it does not poll the device
             driver at a specific interval.
             
             If the poll frequency is zero (0) all attempts to write to this
             object will fail.  If the poll frequency is non-zero,
             setting this value will change the polling frequency of the
             Insight Agent.  Setting the poll frequency to zero (0) will
             always fail, an agent may also choose to fail any request to
             change the poll frequency to a value that would severely impact
             system performance."
    ::= { cpqSeOsCommon 1 }

cpqSeOsCommonModuleTable OBJECT-TYPE
    SYNTAX          SEQUENCE OF CpqSeOsCommonModuleEntry
    ACCESS          not-accessible
    STATUS          obsolete
    DESCRIPTION     
            "A table of software modules that provide an interface to the
             device this MIB describes."
    ::= { cpqSeOsCommon 2 }

cpqSeOsCommonModuleEntry OBJECT-TYPE
    SYNTAX          CpqSeOsCommonModuleEntry
    ACCESS          not-accessible
    STATUS          obsolete
    DESCRIPTION     
            "A description of a software module that provides an interface
             to the device this MIB describes."
    INDEX           { cpqSeOsCommonModuleIndex }
    ::= { cpqSeOsCommonModuleTable 1 }

CpqSeOsCommonModuleEntry ::=
    SEQUENCE {
        cpqSeOsCommonModuleIndex        INTEGER,
        cpqSeOsCommonModuleName         DisplayString,
        cpqSeOsCommonModuleVersion      DisplayString,
        cpqSeOsCommonModuleDate         OCTET STRING,
        cpqSeOsCommonModulePurpose      DisplayString
    }

cpqSeOsCommonModuleIndex OBJECT-TYPE
    SYNTAX          INTEGER (0..255)
    ACCESS          read-only
    STATUS          obsolete
    DESCRIPTION     
            "A unique index for this module description."
    ::= { cpqSeOsCommonModuleEntry 1 }

cpqSeOsCommonModuleName OBJECT-TYPE
    SYNTAX          DisplayString (SIZE(0..255))
    ACCESS          read-only
    STATUS          obsolete
    DESCRIPTION     
            "The module name."
    ::= { cpqSeOsCommonModuleEntry 2 }

cpqSeOsCommonModuleVersion OBJECT-TYPE
    SYNTAX          DisplayString (SIZE(0..5))
    ACCESS          read-only
    STATUS          obsolete
    DESCRIPTION     
            "The module version in XX.YY format.
             
             Where XX is the major version number and YY is the minor version
             number.  This field will be a null (size 0) string if the agent
             cannot provide the module version."
    ::= { cpqSeOsCommonModuleEntry 3 }

cpqSeOsCommonModuleDate OBJECT-TYPE
    SYNTAX          OCTET STRING (SIZE(7))
    ACCESS          read-only
    STATUS          obsolete
    DESCRIPTION     
            "The module date.
             
             field  octets  contents                  range
             =====  ======  =======                  =====
               1      1-2   year                      0..65536
               2       3    month                     1..12
               3       4    day                       1..31
               4       5    hour                      0..23
               5       6    minute                    0..59
               6       7    second                    0..60
                            (use 60 for leap-second)
             
             
             This field will be set to year = 0 if the agent cannot provide
             the module date.  The hour, minute, and second field will be set
             to zero (0) if they are not relevant.  The year field is set
             with the most significant octet first."
    ::= { cpqSeOsCommonModuleEntry 4 }

cpqSeOsCommonModulePurpose OBJECT-TYPE
    SYNTAX          DisplayString (SIZE(0..255))
    ACCESS          read-only
    STATUS          obsolete
    DESCRIPTION     
            "The purpose of the module described in this entry."
    ::= { cpqSeOsCommonModuleEntry 5 }

cpqSeProcessor OBJECT IDENTIFIER
    ::= { cpqSeComponent 2 }

cpqSeCpuTable OBJECT-TYPE
    SYNTAX          SEQUENCE OF CpqSeCpuEntry
    ACCESS          not-accessible
    STATUS          mandatory
    DESCRIPTION     
            "A list of the CPUs (processors) in the system.
             
             The main processor (if such a concept is valid for this machine)
             should be the first entry in the table."
    ::= { cpqSeProcessor 1 }

cpqSeCpuEntry OBJECT-TYPE
    SYNTAX          CpqSeCpuEntry
    ACCESS          not-accessible
    STATUS          mandatory
    DESCRIPTION     
            "A description of a CPU (processor) in the system."
    INDEX           { cpqSeCpuUnitIndex }
    ::= { cpqSeCpuTable 1 }

CpqSeCpuEntry ::=
    SEQUENCE {
        cpqSeCpuUnitIndex               INTEGER,
        cpqSeCpuSlot                    INTEGER,
        cpqSeCpuName                    DisplayString,
        cpqSeCpuSpeed                   INTEGER,
        cpqSeCpuStep                    INTEGER,
        cpqSeCpuStatus                  INTEGER,
        cpqSeCpuExtSpeed                INTEGER,
        cpqSeCpuDesigner                INTEGER,
        cpqSeCpuSocketNumber            INTEGER,
        cpqSeCpuThreshPassed            INTEGER,
        cpqSeCpuHwLocation              DisplayString,
        cpqSeCpuCellTablePtr            INTEGER,
        cpqSeCpuPowerpodStatus          INTEGER,
        cpqSeCpuArchitectureRevision    DisplayString,
        cpqSeCpuCore                    INTEGER,
        cpqSeCPUSerialNumber            DisplayString,
        cpqSeCPUPartNumber              DisplayString,
        cpqSeCPUSerialNumberMfgr        DisplayString,
        cpqSeCPUPartNumberMfgr          DisplayString,
        cpqSeCPUCoreIndex               INTEGER,
        cpqSeCPUMaxSpeed                INTEGER,
        cpqSeCPUCoreThreadIndex         INTEGER,
        cpqSeCPUChipGenerationName      DisplayString,
        cpqSeCPUMultiThreadStatus       INTEGER,
        cpqSeCPUCoreMaxThreads          INTEGER,
        cpqSeCpuLowPowerStatus          INTEGER,
        cpqSeCpuPrimary                 INTEGER,
        cpqSeCpuCoreSteppingText        DisplayString,
        cpqSeCpuCurrentPerformanceState INTEGER,
        cpqSeCpuMinPerformanceState     INTEGER,
        cpqSeCpuMaxPerformanceState     INTEGER
    }

cpqSeCpuUnitIndex OBJECT-TYPE
    SYNTAX          INTEGER (0..65535)
    ACCESS          read-only
    STATUS          mandatory
    DESCRIPTION     
            "This is a number that uniquely specifies a processor unit.
             A processing unit may be a set of processing chips that are
             on the same board or for other reasons work together as a unit.
             The main processor unit (if such a concept is valid for this
             machine) will always have the lowest (first) index."
    ::= { cpqSeCpuEntry 1 }

cpqSeCpuSlot OBJECT-TYPE
    SYNTAX          INTEGER (0..255)
    ACCESS          read-only
    STATUS          mandatory
    DESCRIPTION     
            "This value represents this processor's slot.
             If the slot cannot be determined the value of zero (0) will be
             returned."
    ::= { cpqSeCpuEntry 2 }

cpqSeCpuName OBJECT-TYPE
    SYNTAX          DisplayString (SIZE(0..255))
    ACCESS          read-only
    STATUS          mandatory
    DESCRIPTION     
            "The name of this processor.
             For example:
                 80386"
    ::= { cpqSeCpuEntry 3 }

cpqSeCpuSpeed OBJECT-TYPE
    SYNTAX          INTEGER (0..65535)
    ACCESS          read-only
    STATUS          mandatory
    DESCRIPTION     
            "The current internal speed of this processor in megahertz.
             This changes as per the processor performance state
             Zero will be returned if this value is not available."
    ::= { cpqSeCpuEntry 4 }

cpqSeCpuStep OBJECT-TYPE
    SYNTAX          INTEGER (0..65535)
    ACCESS          read-only
    STATUS          mandatory
    DESCRIPTION     
            "This step of the processor.
             This will be zero (0) if the step cannot be determined."
    ::= { cpqSeCpuEntry 5 }

cpqSeCpuStatus OBJECT-TYPE
    SYNTAX          INTEGER { unknown(1), ok(2), degraded(3), failed(4), 
                        disabled(5) }
    ACCESS          read-only
    STATUS          mandatory
    DESCRIPTION     
            "The status of the processor.
             
             The following values are valid for CPU status:
             
             Unknown (1)
               The status of the CPU could not be determined.
             
             OK (2)
               The CPU is functioning normally.
             
             Degraded (3)
               The CPU is in a pre-failure warrantee state.
             
             Failed (4)
               The CPU is in a failed state.
             
             Disabled (5)
               The CPU has been disabled during power-on-self-test."
    ::= { cpqSeCpuEntry 6 }

cpqSeCpuExtSpeed OBJECT-TYPE
    SYNTAX          INTEGER (0..65535)
    ACCESS          read-only
    STATUS          mandatory
    DESCRIPTION     
            "This is the external frequency in megahertz of the processor bus.
             Zero will be returned if this value is not available."
    ::= { cpqSeCpuEntry 7 }

cpqSeCpuDesigner OBJECT-TYPE
    SYNTAX          INTEGER { unknown(1), intel(2), amd(3), cyrix(4), 
                        ti(5), nexgen(6), compaq(7), samsung(8), 
                        mitsubishi(9), mips(10) }
    ACCESS          read-only
    STATUS          mandatory
    DESCRIPTION     
            "This attribute specifies the manufacturer which designs
             this CPU."
    ::= { cpqSeCpuEntry 8 }

cpqSeCpuSocketNumber OBJECT-TYPE
    SYNTAX          INTEGER (0..255)
    ACCESS          read-only
    STATUS          mandatory
    DESCRIPTION     
            "The physical socket number of the CPU chip.  This number
             helps to identify CPUs on processor boards that contain
             multiple CPU chips. In most cases the CPU Socket number
             should be specified on the board silkscreen or in product
             documentation."
    ::= { cpqSeCpuEntry 9 }

cpqSeCpuThreshPassed OBJECT-TYPE
    SYNTAX          INTEGER { unsupported(1), false(2), true(3) }
    ACCESS          read-only
    STATUS          mandatory
    DESCRIPTION     
            "CPU threshold passed (Exceeded). When this attribute is set
             to true, it identifies a pre-failure error condition. Processors
             like the Intel Pentium Pro have the capability built into them
             to correct internal error conditions.  Excessive corrected internal
             errors can predict future hard processor failures.  Agent
             instrumentation will set this attribute to true if an internal
             processor error threshold is passed.  It is recommended that the
             user replace the CPU in this case. If the processor does not
             support monitoring internal corrected errors, this value will
             be set to unsupported. "
    ::= { cpqSeCpuEntry 10 }

cpqSeCpuHwLocation OBJECT-TYPE
    SYNTAX          DisplayString (SIZE(0..255))
    ACCESS          read-only
    STATUS          optional
    DESCRIPTION     
            "A text description of the hardware location, on complex
             multi SBB hardware only, for the CPU.
             A NULL string indicates that the hardware location could not
             be determined or is irrelevant."
    ::= { cpqSeCpuEntry 11 }

cpqSeCpuCellTablePtr OBJECT-TYPE
    SYNTAX          INTEGER (0..15)
    ACCESS          read-only
    STATUS          optional
    DESCRIPTION     
            "This is the index for the cell in cpqSeCellTable where this CPU is physically located."
    ::= { cpqSeCpuEntry 12 }

cpqSeCpuPowerpodStatus OBJECT-TYPE
    SYNTAX          INTEGER { notfailed(1), failed(2) }
    ACCESS          read-only
    STATUS          optional
    DESCRIPTION     
            "This is the status of CPU power pod. Potential values in the future could be present/not present."
    ::= { cpqSeCpuEntry 13 }

cpqSeCpuArchitectureRevision OBJECT-TYPE
    SYNTAX          DisplayString (SIZE(0..255))
    ACCESS          read-only
    STATUS          optional
    DESCRIPTION     
            "This is the CPU architecture revision."
    ::= { cpqSeCpuEntry 14 }

cpqSeCpuCore OBJECT-TYPE
    SYNTAX          INTEGER
    ACCESS          read-only
    STATUS          optional
    DESCRIPTION     
            "The number of cores in this CPU module. Zero will be returned if can not be determined."
    ::= { cpqSeCpuEntry 15 }

cpqSeCPUSerialNumber OBJECT-TYPE
    SYNTAX          DisplayString (SIZE(0..255))
    ACCESS          read-only
    STATUS          optional
    DESCRIPTION     
            "The OEM serial number of the CPU."
    ::= { cpqSeCpuEntry 16 }

cpqSeCPUPartNumber OBJECT-TYPE
    SYNTAX          DisplayString (SIZE(0..255))
    ACCESS          read-only
    STATUS          optional
    DESCRIPTION     
            "The OEM part number of the CPU."
    ::= { cpqSeCpuEntry 17 }

cpqSeCPUSerialNumberMfgr OBJECT-TYPE
    SYNTAX          DisplayString (SIZE(0..255))
    ACCESS          read-only
    STATUS          optional
    DESCRIPTION     
            "The manufacturer serial number of the CPU."
    ::= { cpqSeCpuEntry 18 }

cpqSeCPUPartNumberMfgr OBJECT-TYPE
    SYNTAX          DisplayString (SIZE(0..255))
    ACCESS          read-only
    STATUS          optional
    DESCRIPTION     
            "The manufacturer part number of the CPU."
    ::= { cpqSeCpuEntry 19 }

cpqSeCPUCoreIndex OBJECT-TYPE
    SYNTAX          INTEGER (0..65535)
    ACCESS          read-only
    STATUS          optional
    DESCRIPTION     
            "This is a number that uniquely identifies a core in a CPU unit."
    ::= { cpqSeCpuEntry 20 }

cpqSeCPUMaxSpeed OBJECT-TYPE
    SYNTAX          INTEGER (0..65535)
    ACCESS          read-only
    STATUS          optional
    DESCRIPTION     
            "This is the maximum internal speed in megahertz this processor can support.
             Zero will be returned if this value is not available."
    ::= { cpqSeCpuEntry 21 }

cpqSeCPUCoreThreadIndex OBJECT-TYPE
    SYNTAX          INTEGER (0..65535)
    ACCESS          read-only
    STATUS          optional
    DESCRIPTION     
            "This is an unique number to identify the running threads in a CPU core."
    ::= { cpqSeCpuEntry 22 }

cpqSeCPUChipGenerationName OBJECT-TYPE
    SYNTAX          DisplayString (SIZE(0..255))
    ACCESS          read-only
    STATUS          optional
    DESCRIPTION     
            "CPU chip generation name e.g. Hondo, Montecito, Madison, Opteron."
    ::= { cpqSeCpuEntry 23 }

cpqSeCPUMultiThreadStatus OBJECT-TYPE
    SYNTAX          INTEGER { unknown(1), enabled(2), disabled(3) }
    ACCESS          read-only
    STATUS          optional
    DESCRIPTION     
            "This OID identifies whether the CPU threading is enabled or not."
    ::= { cpqSeCpuEntry 24 }

cpqSeCPUCoreMaxThreads OBJECT-TYPE
    SYNTAX          INTEGER (0..65535)
    ACCESS          read-only
    STATUS          optional
    DESCRIPTION     
            "This OID indicates the maximum number of threads that a cpu core is capable of."
    ::= { cpqSeCpuEntry 25 }

cpqSeCpuLowPowerStatus OBJECT-TYPE
    SYNTAX          INTEGER { unknown(1), lowpowered(2), 
                        normalpowered(3), highpowered(4) }
    ACCESS          read-only
    STATUS          mandatory
    DESCRIPTION     
            "Servers like Itanium has capability to lower power supply
             to CPU if it is idle for specified period of time. Proliant 
             servers can set to high/low/Dynamic mode of power through
             ILO.
             
             The following values are valid for CPU Low Powered state:
             
             Unknown (1)
                The Low Powered status could not be determined.
             
             Low Powered (2)
                The CPU is Low Power state.
             
             Normal Powered (3)
                The CPU is normal Power state.
                
             High Powered (4)
                The CPU is High Power state."
    ::= { cpqSeCpuEntry 26 }

cpqSeCpuPrimary OBJECT-TYPE
    SYNTAX          INTEGER { unknown(1), false(2), true(3) }
    ACCESS          read-only
    STATUS          mandatory
    DESCRIPTION     
            "On SMP systems one of the CPU is set to Primary and the  
             other CPUs as secondary. A value of true is set if the
             CPU is primary.
             
             The following values are valid for CPU availability status:
             
             Unknown (1)
              The CPU Primary/Secondary could not be determined.
             
             false (2)
              The CPU is not primary CPU.
             
             True (3)
              The CUR is primary CPU."
    ::= { cpqSeCpuEntry 27 }

cpqSeCpuCoreSteppingText OBJECT-TYPE
    SYNTAX          DisplayString
    ACCESS          read-only
    STATUS          optional
    DESCRIPTION     
            "The processor stepping version string. A NULL string 
             indicates that the stepping could not be determined."
    ::= { cpqSeCpuEntry 28 }

cpqSeCpuCurrentPerformanceState OBJECT-TYPE
    SYNTAX          INTEGER
    ACCESS          read-only
    STATUS          optional
    DESCRIPTION     
            "This OID returns the current performance state of this processor.
             Processor performance states are denoted as Pn states. The value 
             of n is cpqSeCpuPerformanceState. The higher the value n is, the 
             lower the performance state is being used. Value 0 describes the 
             highest performance state, in which the processor uses its maximum 
             performance capability and may consume maximum power.
             The performance state number should not exceed 16 on Itanium servers.
             (-1) will be returned if this value is not available."
    ::= { cpqSeCpuEntry 29 }

cpqSeCpuMinPerformanceState OBJECT-TYPE
    SYNTAX          INTEGER
    ACCESS          read-only
    STATUS          optional
    DESCRIPTION     
            "This OID returns the minimum performance state set for this processor.
             (-1) will be returned if this value is not available."
    ::= { cpqSeCpuEntry 30 }

cpqSeCpuMaxPerformanceState OBJECT-TYPE
    SYNTAX          INTEGER
    ACCESS          read-only
    STATUS          optional
    DESCRIPTION     
            "This OID returns the maximum performance state set for this processor.
             (-1) will be returned if this value is not available."
    ::= { cpqSeCpuEntry 31 }

cpqSeFpuTable OBJECT-TYPE
    SYNTAX          SEQUENCE OF CpqSeFpuEntry
    ACCESS          not-accessible
    STATUS          mandatory
    DESCRIPTION     
            "A list of the FPUs (floating point coprocessors) in the system."
    ::= { cpqSeProcessor 2 }

cpqSeFpuEntry OBJECT-TYPE
    SYNTAX          CpqSeFpuEntry
    ACCESS          not-accessible
    STATUS          mandatory
    DESCRIPTION     
            "A description of a FPU in the system.
             
             The fpuUnitIndex of any entry in this table will equal the
             cpuUnitIndex of the corresponding CPU in the cpqSeCpu table."
    INDEX           { cpqSeFpuUnitIndex, cpqSeFpuChipIndex }
    ::= { cpqSeFpuTable 1 }

CpqSeFpuEntry ::=
    SEQUENCE {
        cpqSeFpuUnitIndex               INTEGER,
        cpqSeFpuChipIndex               INTEGER,
        cpqSeFpuSlot                    INTEGER,
        cpqSeFpuName                    DisplayString,
        cpqSeFpuSpeed                   INTEGER,
        cpqSeFpuType                    INTEGER,
        cpqSeFpuHwLocation              DisplayString
    }

cpqSeFpuUnitIndex OBJECT-TYPE
    SYNTAX          INTEGER (0..65535)
    ACCESS          read-only
    STATUS          mandatory
    DESCRIPTION     
            "This is a number that uniquely specifies a processor unit.
             
             A processing unit may be a set of processing chips that are
             on the same board or for other reasons work together as a unit.
             The main processor unit (if there is one) will always have the
             lowest (first) index.  This field can be used to associate
             CPUs with their corresponding FPUs."
    ::= { cpqSeFpuEntry 1 }

cpqSeFpuChipIndex OBJECT-TYPE
    SYNTAX          INTEGER (0..65535)
    ACCESS          read-only
    STATUS          mandatory
    DESCRIPTION     
            "This is a number that uniquely specifies the FPU chip.
             
             This field is used to distinguish between multiple FPUs that are
             part of the same processor unit.  For example, If a processor
             board contained a Intel 80386 processor with both a Intel 80387
             and a Weitek 3167, both the 80387 and the 3167 would have the
             same fpuUnitIndex (which would match the 80386's cpuUnitIndex)
             but the 80387 and the 3167 would have different fpuChipIndex
             field values."
    ::= { cpqSeFpuEntry 2 }

cpqSeFpuSlot OBJECT-TYPE
    SYNTAX          INTEGER (0..255)
    ACCESS          read-only
    STATUS          mandatory
    DESCRIPTION     
            "This is the FPU's slot.
             
             If the slot cannot be determined the value of zero (0) will
             be returned."
    ::= { cpqSeFpuEntry 3 }

cpqSeFpuName OBJECT-TYPE
    SYNTAX          DisplayString (SIZE(0..255))
    ACCESS          read-only
    STATUS          mandatory
    DESCRIPTION     
            "This is the name of the FPU.
             
             For example:
                 80387
                 Weitek 3167"
    ::= { cpqSeFpuEntry 4 }

cpqSeFpuSpeed OBJECT-TYPE
    SYNTAX          INTEGER (0..65535)
    ACCESS          read-only
    STATUS          mandatory
    DESCRIPTION     
            "This is speed in megahertz of the FPU.
             
             Zero will be returned if this value is not available."
    ::= { cpqSeFpuEntry 5 }

cpqSeFpuType OBJECT-TYPE
    SYNTAX          INTEGER { other(1), embedded(2), external(3) }
    ACCESS          read-only
    STATUS          mandatory
    DESCRIPTION     
            "This value indicates if the FPU this entry is describing
             is embedded in the CPU or external to the CPU chip."
    ::= { cpqSeFpuEntry 6 }

cpqSeFpuHwLocation OBJECT-TYPE
    SYNTAX          DisplayString (SIZE(0..255))
    ACCESS          read-only
    STATUS          optional
    DESCRIPTION     
            "A text description of the hardware location, on complex
             multi SBB hardware only, for the FPU.
             A NULL string indicates that the hardware location could not
             be determined or is irrelevant."
    ::= { cpqSeFpuEntry 7 }

cpqSeCpuCacheTable OBJECT-TYPE
    SYNTAX          SEQUENCE OF CpqSeCpuCacheEntry
    ACCESS          not-accessible
    STATUS          mandatory
    DESCRIPTION     
            "A list of the CPU caches in the system."
    ::= { cpqSeProcessor 3 }

cpqSeCpuCacheEntry OBJECT-TYPE
    SYNTAX          CpqSeCpuCacheEntry
    ACCESS          not-accessible
    STATUS          mandatory
    DESCRIPTION     
            "A description of a CPU Caches in the system."
    INDEX           { cpqSeCpuCacheUnitIndex, cpqSeCpuCacheLevelIndex }
    ::= { cpqSeCpuCacheTable 1 }

CpqSeCpuCacheEntry ::=
    SEQUENCE {
        cpqSeCpuCacheUnitIndex          INTEGER,
        cpqSeCpuCacheLevelIndex         INTEGER,
        cpqSeCpuCacheSize               INTEGER,
        cpqSeCpuCacheSpeed              INTEGER,
        cpqSeCpuCacheStatus             INTEGER,
        cpqSeCpuCacheWritePolicy        INTEGER,
        cpqSeCpuCacheHwLocation         DisplayString,
        cpqSeCpuCacheCpuSlot            INTEGER,
        cpqSeCpuCacheCpuCoreIndex       INTEGER
    }

cpqSeCpuCacheUnitIndex OBJECT-TYPE
    SYNTAX          INTEGER (0..65535)
    ACCESS          read-only
    STATUS          mandatory
    DESCRIPTION     
            "This is a number that uniquely specifies a processor unit.
             
             A processing unit may be a set of processing chips that are
             on the same board or for other reasons work together as a unit.
             The main processor unit (if such a concept is valid for this
             machine) will always have the lowest (first) index."
    ::= { cpqSeCpuCacheEntry 1 }

cpqSeCpuCacheLevelIndex OBJECT-TYPE
    SYNTAX          INTEGER (0..255)
    ACCESS          read-only
    STATUS          mandatory
    DESCRIPTION     
            "This is the processor cache level.
             
             The lower the processor cache level, the closer the cache is to
             the processor."
    ::= { cpqSeCpuCacheEntry 2 }

cpqSeCpuCacheSize OBJECT-TYPE
    SYNTAX          INTEGER (0..2147483647)
    ACCESS          read-only
    STATUS          mandatory
    DESCRIPTION     
            "The size of the cache in kilobytes."
    ::= { cpqSeCpuCacheEntry 3 }

cpqSeCpuCacheSpeed OBJECT-TYPE
    SYNTAX          INTEGER (0..65535)
    ACCESS          read-only
    STATUS          mandatory
    DESCRIPTION     
            "This is speed in cache memory in nanoseconds (ns).  A value of
             zero (0) means that the cache speed is unknown or unobtainable."
    ::= { cpqSeCpuCacheEntry 4 }

cpqSeCpuCacheStatus OBJECT-TYPE
    SYNTAX          INTEGER { unknown(1), ok(2), degraded(3), failed(4) }
    ACCESS          read-only
    STATUS          mandatory
    DESCRIPTION     
            "The status of the cache unit.  If the cache is optional and not
             installed, unknown(1) will be returned."
    ::= { cpqSeCpuCacheEntry 5 }

cpqSeCpuCacheWritePolicy OBJECT-TYPE
    SYNTAX          INTEGER { unknown(1), write-through(2), 
                        write-back(3) }
    ACCESS          read-only
    STATUS          mandatory
    DESCRIPTION     
            "Specifies write policy of this cache entry."
    ::= { cpqSeCpuCacheEntry 6 }

cpqSeCpuCacheHwLocation OBJECT-TYPE
    SYNTAX          DisplayString (SIZE(0..255))
    ACCESS          read-only
    STATUS          optional
    DESCRIPTION     
            "A text description of the hardware location, on complex
             multi SBB hardware only, for the CPU cache.
             A NULL string indicates that the hardware location could not
             be determined or is irrelevant."
    ::= { cpqSeCpuCacheEntry 7 }

cpqSeCpuCacheCpuSlot OBJECT-TYPE
    SYNTAX          INTEGER (0..65535)
    ACCESS          read-only
    STATUS          optional
    DESCRIPTION     
            "This is the CPU Slot associated with this CPU cache."
    ::= { cpqSeCpuCacheEntry 8 }

cpqSeCpuCacheCpuCoreIndex OBJECT-TYPE
    SYNTAX          INTEGER
    ACCESS          read-only
    STATUS          optional
    DESCRIPTION     
            "This is a unique number that identifies the core in the CPU
             slot to which this cache is associated. If the cache is not
             associated with any core on a multi-core CPU, the value should be -1."
    ::= { cpqSeCpuCacheEntry 9 }

cpqSeCpuCondition OBJECT-TYPE
    SYNTAX          INTEGER { other(1), ok(2), degraded(3), failed(4) }
    ACCESS          read-only
    STATUS          mandatory
    DESCRIPTION     
            "This value specifies the overall condition of the 			
             processor sub-system."
    ::= { cpqSeProcessor 4 }

cpqSeMemory OBJECT IDENTIFIER
    ::= { cpqSeComponent 3 }

cpqSeBaseMem OBJECT-TYPE
    SYNTAX          INTEGER (0..65535)
    ACCESS          read-only
    STATUS          mandatory
    DESCRIPTION     
            "The amount of base memory in kilobytes.
             
             A kilobyte is 1024 bytes."
    ::= { cpqSeMemory 1 }

cpqSeTotalMem OBJECT-TYPE
    SYNTAX          INTEGER (0..2147483647)
    ACCESS          read-only
    STATUS          mandatory
    DESCRIPTION     
            "The total amount of memory in kilobytes.
             
             A kilobyte is 1024 bytes."
    ::= { cpqSeMemory 2 }

cpqSeTotalMemMB OBJECT-TYPE
    SYNTAX          INTEGER (0..2147483647)
    ACCESS          read-only
    STATUS          mandatory
    DESCRIPTION     
            "The total amount of memory in megabytes.
             
             A megabyte is 1024 kilobytes."
    ::= { cpqSeMemory 3 }

cpqSeIsaCmos OBJECT IDENTIFIER
    ::= { cpqSeComponent 4 }

cpqSeIsaCmosRaw OBJECT-TYPE
    SYNTAX          OCTET STRING (SIZE(64))
    ACCESS          read-only
    STATUS          mandatory
    DESCRIPTION     
            "The contents of the ISA CMOS."
    ::= { cpqSeIsaCmos 1 }

cpqSeEisaNvram OBJECT IDENTIFIER
    ::= { cpqSeComponent 5 }

cpqSeEisaSlotTable OBJECT-TYPE
    SYNTAX          SEQUENCE OF CpqSeEisaSlotEntry
    ACCESS          not-accessible
    STATUS          mandatory
    DESCRIPTION     
            "A list of EISA slot information entries."
    ::= { cpqSeEisaNvram 1 }

cpqSeEisaSlotEntry OBJECT-TYPE
    SYNTAX          CpqSeEisaSlotEntry
    ACCESS          not-accessible
    STATUS          mandatory
    DESCRIPTION     
            "A description of an EISA slot."
    INDEX           { cpqSeEisaSlotIndex }
    ::= { cpqSeEisaSlotTable 1 }

CpqSeEisaSlotEntry ::=
    SEQUENCE {
        cpqSeEisaSlotIndex              INTEGER,
        cpqSeEisaSlotRaw                OCTET STRING,
        cpqSeEisaSlotBoardId            DisplayString,
        cpqSeEisaSlotBoardName          DisplayString,
        cpqSeEisaSlotCfRev              DisplayString,
        cpqSeEisaSlotType               INTEGER
    }

cpqSeEisaSlotIndex OBJECT-TYPE
    SYNTAX          INTEGER (0..255)
    ACCESS          read-only
    STATUS          mandatory
    DESCRIPTION     
            "The EISA slot number for this entry describes."
    ::= { cpqSeEisaSlotEntry 1 }

cpqSeEisaSlotRaw OBJECT-TYPE
    SYNTAX          OCTET STRING (SIZE(12))
    ACCESS          read-only
    STATUS          mandatory
    DESCRIPTION     
            "The EISA slot data for the board in this slot.
             
             This octet string contains the following EISA slot information:
             
             The first octet will be zero (0) if this slot contains a
             properly configured board.  Any other value indicates that the
             EISA configuration information for this board is invalid or an
             error occurred when trying to retrieve the information.
             
             The second octet contains several bit flags about the product ID
             and slot type.
             
                 Bit 7:      0 = No duplicate ID
                             1 = Duplicate IDs
             
                 Bit 6:      0 = Product ID readable
                             1 = Product ID not readable
             
                 Bit 5,4:    00 = Expansion slot
                             01 = Embedded device
                             10 = Virtual device
                             11 = Reserved
             
                 Bit 3..0:   This nibble indicates which CFG file is loaded
                             when duplicate file names are present.
                             0000 = No duplicate ID
                             0001 = First duplicate ID
                             0010 = Second duplicate ID
                             0011 = Third duplicate ID
                               .
                               .
                               .
                             1111 = Fifteenth duplicate ID
             
             NOTE:   Bit 7 is the most significant bit, bit 0 is the least
                     significant.
             
             The third octet contains the major revision level of the
             configuration utility.
             
             The fourth octet contains the minor revision level of the
             configuration utility.
             
             The fifth octet contains the most significant byte of the
             configuration file checksum.
             
             The sixth octet contains the least significant byte of the
             configuration file checksum.
             
             The seventh octet contains the number of device functions defined
             for the board in this slot.
             
             The eighth octet contains the combined function information.
             This is a set of flags.  Each bit has the following meaning when
             set (1):
                 Bit 7:  reserved (0)
                 Bit 6:  slot has one or more free form data entries
                 Bit 5:  slot has one or more port initialization entries.
                 Bit 4:  slot has one or more port range entries.
                 Bit 3:  slot has one or more DMA entries.
                 Bit 2:  slot has one or more interrupt (IRQ) entries.
                 Bit 1:  slot has one or more memory entries.
                 Bit 0:  slot has one or more function type definitions.
             
             NOTE:   bit 7 is the most significant bit, bit 0 is the least
                     significant.
             
             The ninth, tenth, eleventh, and twelfth octets contain the four
             byte compressed EISA ID.
             
             For more information about the meaning of this information
             consult the EISA Technical Reference Guide."
    ::= { cpqSeEisaSlotEntry 2 }

cpqSeEisaSlotBoardId OBJECT-TYPE
    SYNTAX          DisplayString (SIZE(7))
    ACCESS          read-only
    STATUS          mandatory
    DESCRIPTION     
            "A seven character board ID.
             
             The first three characters are the manufacturers ID followed by 
             three character product ID followed by a one character revision
             level."
    ::= { cpqSeEisaSlotEntry 3 }

cpqSeEisaSlotBoardName OBJECT-TYPE
    SYNTAX          DisplayString (SIZE(0..255))
    ACCESS          read-only
    STATUS          mandatory
    DESCRIPTION     
            "The product name (or other suitable description) of this board.
             
             This field may be empty if no descriptive information is known
             about the board."
    ::= { cpqSeEisaSlotEntry 4 }

cpqSeEisaSlotCfRev OBJECT-TYPE
    SYNTAX          DisplayString (SIZE(0..5))
    ACCESS          read-only
    STATUS          mandatory
    DESCRIPTION     
            "The revision level of the EISA configuration utility that was
             used to configure the system.
             
             This should be the same version information displayed by the EISA
             configuration utility."
    ::= { cpqSeEisaSlotEntry 5 }

cpqSeEisaSlotType OBJECT-TYPE
    SYNTAX          INTEGER { unknown(1), isa8Bit(2), isa16Bit(3), 
                        eisa32Bit(4), eisaBusMaster32Bit(5), other(6), 
                        reserved(7), reserved2(8) }
    ACCESS          read-only
    STATUS          mandatory
    DESCRIPTION     
            "The type of slot described by this entry."
    ::= { cpqSeEisaSlotEntry 6 }

cpqSeEisaFunctTable OBJECT-TYPE
    SYNTAX          SEQUENCE OF CpqSeEisaFunctEntry
    ACCESS          not-accessible
    STATUS          mandatory
    DESCRIPTION     
            "A list EISA function information entries."
    ::= { cpqSeEisaNvram 2 }

cpqSeEisaFunctEntry OBJECT-TYPE
    SYNTAX          CpqSeEisaFunctEntry
    ACCESS          not-accessible
    STATUS          mandatory
    DESCRIPTION     
            "A description of an EISA function."
    INDEX           { cpqSeEisaFunctSlotIndex, cpqSeEisaFunctIndex }
    ::= { cpqSeEisaFunctTable 1 }

CpqSeEisaFunctEntry ::=
    SEQUENCE {
        cpqSeEisaFunctSlotIndex         INTEGER,
        cpqSeEisaFunctIndex             INTEGER,
        cpqSeEisaFunctStatus            INTEGER,
        cpqSeEisaFunctType              DisplayString,
        cpqSeEisaFunctCfgRev            DisplayString,
        cpqSeEisaFunctSels              OCTET STRING,
        cpqSeEisaFunctInfo              INTEGER
    }

cpqSeEisaFunctSlotIndex OBJECT-TYPE
    SYNTAX          INTEGER (0..255)
    ACCESS          read-only
    STATUS          mandatory
    DESCRIPTION     
            "The EISA slot of the board that registered this function"
    ::= { cpqSeEisaFunctEntry 1 }

cpqSeEisaFunctIndex OBJECT-TYPE
    SYNTAX          INTEGER (0..255)
    ACCESS          read-only
    STATUS          mandatory
    DESCRIPTION     
            "The number of the function this entry describes."
    ::= { cpqSeEisaFunctEntry 2 }

cpqSeEisaFunctStatus OBJECT-TYPE
    SYNTAX          INTEGER { disabled(2), enabled(3) }
    ACCESS          read-only
    STATUS          mandatory
    DESCRIPTION     
            "The status of the function described by this entry."
    ::= { cpqSeEisaFunctEntry 3 }

cpqSeEisaFunctType OBJECT-TYPE
    SYNTAX          DisplayString (SIZE(0..80))
    ACCESS          read-only
    STATUS          mandatory
    DESCRIPTION     
            "The type of the function.
             
             The type may be followed by one or more subtype description
             fields. Some currently defined types are:
             
             Type            Meaning
             ==============  ==================================================
             COM             Communication device
             COM,ASY         ISA compatible 8250 based serial port
             COM,ASY,FIFO    ISA compatible 16550 based serial port (with fifo)
             COM,SYN         ISA compatible SDLC port
             CPU             Microprocessor
             CPU,8086        8086 compatible microprocessor
             CPU,80286       80286 compatible microprocessor
             CPU,80386SX     80386SX compatible microprocessor
             CPU,80386       80386 compatible microprocessor
             CPU,80486       80486 compatible microprocessor
             JOY             ISA compatible joystick adapter
             KEY             Keyboard
             KEY,nnn,KBD=xx  Standard keyboard with nnn keys for country xx
             MEM             Memory board
             MFC             Multifunction board
             MSD             Mass storage device
             MSD,DSKCTL      ISA compatible fixed disk controller
             MSD,FPYCTL      ISA compatible floppy disk controller
             MSD,TAPCTL      Primary tape controller
             NET             Network board
             NPX             Numeric coprocessor
             NPX,287         Intel 287 numeric coprocessor
             NPX,387         Intel 387 numeric coprocessor
             NPX,387SX       Intel 387SX numeric coprocessor
             NPX,W1167       Weitek 1167 numeric coprocessor
             NPX,W3167       Weitek 3167 numeric coprocessor
             OSE             Operating system/environment
             OTH             Other
             PAR             ISA compatible parallel port
             PAR,BID         Bidirectional parallel port
             PTR             Pointing device
             PTR,8042        8042 pointing device (mouse) interface
             SYS             System board
             VID             Video board
             VID,MDA         ISA compatible monochrome adapter
             VID,MDA,MGA     Hercules monochrome adapter
             VID,CGA         CGA, no write sync during retrace required
             VID,CGA,RTR     CGA, write sync during retrace required
             VID,EGA         ISA compatible EGA adapter
             VID,VGA         ISA compatible VGA adapter
             
             This list is not intended to be complete.  Other types may be
             found in this field.  This list describes some of the more
             common types found, other types should be similarly recognizable
             to someone sufficiently knowledgeable about computer hardware."
    ::= { cpqSeEisaFunctEntry 4 }

cpqSeEisaFunctCfgRev OBJECT-TYPE
    SYNTAX          DisplayString (SIZE(0..5))
    ACCESS          read-only
    STATUS          mandatory
    DESCRIPTION     
            "The revision of the EISA configuration .OVL file used to
             configure this board."
    ::= { cpqSeEisaFunctEntry 5 }

cpqSeEisaFunctSels OBJECT-TYPE
    SYNTAX          OCTET STRING (SIZE(0..26))
    ACCESS          read-only
    STATUS          mandatory
    DESCRIPTION     
            "The selections that were chosen with the EISA CONFIGURATION
             UTILITY to create this function."
    ::= { cpqSeEisaFunctEntry 6 }

cpqSeEisaFunctInfo OBJECT-TYPE
    SYNTAX          INTEGER (0..255)
    ACCESS          read-only
    STATUS          mandatory
    DESCRIPTION     
            "The EISA function information block.
             
             This is a set of flags indicating the resources that are
             configured in this EISA function.  Each bit has the following
             meaning when it is set (1):
             
                 Bit 7:  Function is disabled
                 Bit 6:  This function contains free-form information.
                 Bit 5:  This function contains port initialization entries.
                 Bit 4:  This function contains port range entries.
                 Bit 3:  This function contains DMA entries.
                 Bit 2:  This function contains interrupt (IRQ) entries.
                 Bit 1:  This function contains memory entries.
                 Bit 0:  This function contains function type definitions.
             
             NOTE:   bit 7 is the most significant bit, bit 0 is the least
                     significant."
    ::= { cpqSeEisaFunctEntry 7 }

cpqSeEisaMemTable OBJECT-TYPE
    SYNTAX          SEQUENCE OF CpqSeEisaMemEntry
    ACCESS          not-accessible
    STATUS          mandatory
    DESCRIPTION     
            "A list of EISA function memory configuration entries."
    ::= { cpqSeEisaNvram 3 }

cpqSeEisaMemEntry OBJECT-TYPE
    SYNTAX          CpqSeEisaMemEntry
    ACCESS          not-accessible
    STATUS          mandatory
    DESCRIPTION     
            "A description of an EISA function memory configuration."
    INDEX           { cpqSeEisaMemSlotIndex, cpqSeEisaMemFunctIndex, 
                      cpqSeEisaMemAllocIndex }
    ::= { cpqSeEisaMemTable 1 }

CpqSeEisaMemEntry ::=
    SEQUENCE {
        cpqSeEisaMemSlotIndex           INTEGER,
        cpqSeEisaMemFunctIndex          INTEGER,
        cpqSeEisaMemAllocIndex          INTEGER,
        cpqSeEisaMemStartAddr           INTEGER,
        cpqSeEisaMemSize                INTEGER,
        cpqSeEisaMemShare               INTEGER,
        cpqSeEisaMemType                INTEGER,
        cpqSeEisaMemCache               INTEGER,
        cpqSeEisaMemAccess              INTEGER,
        cpqSeEisaMemDecode              INTEGER,
        cpqSeEisaMemDataSize            INTEGER
    }

cpqSeEisaMemSlotIndex OBJECT-TYPE
    SYNTAX          INTEGER (0..255)
    ACCESS          read-only
    STATUS          mandatory
    DESCRIPTION     
            "The EISA slot number of the board that registered the memory
             configuration this entry describes."
    ::= { cpqSeEisaMemEntry 1 }

cpqSeEisaMemFunctIndex OBJECT-TYPE
    SYNTAX          INTEGER (0..255)
    ACCESS          read-only
    STATUS          mandatory
    DESCRIPTION     
            "The function in which this memory configuration was registered."
    ::= { cpqSeEisaMemEntry 2 }

cpqSeEisaMemAllocIndex OBJECT-TYPE
    SYNTAX          INTEGER (0..255)
    ACCESS          read-only
    STATUS          mandatory
    DESCRIPTION     
            "The index for this memory allocation entry in the EISA function
             block."
    ::= { cpqSeEisaMemEntry 3 }

cpqSeEisaMemStartAddr OBJECT-TYPE
    SYNTAX          INTEGER
    ACCESS          read-only
    STATUS          mandatory
    DESCRIPTION     
            "The starting address of the memory configuration."
    ::= { cpqSeEisaMemEntry 4 }

cpqSeEisaMemSize OBJECT-TYPE
    SYNTAX          INTEGER (0..2147483647)
    ACCESS          read-only
    STATUS          mandatory
    DESCRIPTION     
            "The size in bytes of the memory configuration."
    ::= { cpqSeEisaMemEntry 5 }

cpqSeEisaMemShare OBJECT-TYPE
    SYNTAX          INTEGER { nonshareable(1), shareable(2) }
    ACCESS          read-only
    STATUS          mandatory
    DESCRIPTION     
            "This value indicates if the memory is shareable."
    ::= { cpqSeEisaMemEntry 6 }

cpqSeEisaMemType OBJECT-TYPE
    SYNTAX          INTEGER { systemBaseOrExtended(1), expanded(2), 
                        virtual(3), other(4) }
    ACCESS          read-only
    STATUS          mandatory
    DESCRIPTION     
            "The type of memory."
    ::= { cpqSeEisaMemEntry 7 }

cpqSeEisaMemCache OBJECT-TYPE
    SYNTAX          INTEGER { notCached(1), writeThroughCached(2), 
                        writeBackCached(3) }
    ACCESS          read-only
    STATUS          mandatory
    DESCRIPTION     
            "This value indicates if the memory is cached."
    ::= { cpqSeEisaMemEntry 8 }

cpqSeEisaMemAccess OBJECT-TYPE
    SYNTAX          INTEGER { readOnly(1), readWrite(2) }
    ACCESS          read-only
    STATUS          mandatory
    DESCRIPTION     
            "The type of access permitted for this memory."
    ::= { cpqSeEisaMemEntry 9 }

cpqSeEisaMemDecode OBJECT-TYPE
    SYNTAX          INTEGER (0..65536)
    ACCESS          read-only
    STATUS          mandatory
    DESCRIPTION     
            "The memory decode size (the number of address lines supported)."
    ::= { cpqSeEisaMemEntry 10 }

cpqSeEisaMemDataSize OBJECT-TYPE
    SYNTAX          INTEGER (0..65536)
    ACCESS          read-only
    STATUS          mandatory
    DESCRIPTION     
            "The data access size for the memory in bits."
    ::= { cpqSeEisaMemEntry 11 }

cpqSeEisaIntTable OBJECT-TYPE
    SYNTAX          SEQUENCE OF CpqSeEisaIntEntry
    ACCESS          not-accessible
    STATUS          mandatory
    DESCRIPTION     
            "A list of EISA function interrupt configuration entries."
    ::= { cpqSeEisaNvram 4 }

cpqSeEisaIntEntry OBJECT-TYPE
    SYNTAX          CpqSeEisaIntEntry
    ACCESS          not-accessible
    STATUS          mandatory
    DESCRIPTION     
            "A description of an EISA function interrupt configuration."
    INDEX           { cpqSeEisaIntSlotIndex, cpqSeEisaIntFunctIndex, 
                      cpqSeEisaIntAllocIndex }
    ::= { cpqSeEisaIntTable 1 }

CpqSeEisaIntEntry ::=
    SEQUENCE {
        cpqSeEisaIntSlotIndex           INTEGER,
        cpqSeEisaIntFunctIndex          INTEGER,
        cpqSeEisaIntAllocIndex          INTEGER,
        cpqSeEisaIntNum                 INTEGER,
        cpqSeEisaIntShare               INTEGER,
        cpqSeEisaIntTrigger             INTEGER
    }

cpqSeEisaIntSlotIndex OBJECT-TYPE
    SYNTAX          INTEGER (0..255)
    ACCESS          read-only
    STATUS          mandatory
    DESCRIPTION     
            "The EISA slot number of the board that registered the interrupt
             configuration this entry describes."
    ::= { cpqSeEisaIntEntry 1 }

cpqSeEisaIntFunctIndex OBJECT-TYPE
    SYNTAX          INTEGER (0..255)
    ACCESS          read-only
    STATUS          mandatory
    DESCRIPTION     
            "The function in which this interrupt configuration was
             registered."
    ::= { cpqSeEisaIntEntry 2 }

cpqSeEisaIntAllocIndex OBJECT-TYPE
    SYNTAX          INTEGER (0..255)
    ACCESS          read-only
    STATUS          mandatory
    DESCRIPTION     
            "The index for this interrupt allocation entry in the EISA
             function block."
    ::= { cpqSeEisaIntEntry 3 }

cpqSeEisaIntNum OBJECT-TYPE
    SYNTAX          INTEGER (0..65535)
    ACCESS          read-only
    STATUS          mandatory
    DESCRIPTION     
            "The interrupt described in this entry."
    ::= { cpqSeEisaIntEntry 4 }

cpqSeEisaIntShare OBJECT-TYPE
    SYNTAX          INTEGER { nonshareable(1), shareable(2) }
    ACCESS          read-only
    STATUS          mandatory
    DESCRIPTION     
            "This value indicates if the interrupt is shareable."
    ::= { cpqSeEisaIntEntry 5 }

cpqSeEisaIntTrigger OBJECT-TYPE
    SYNTAX          INTEGER { edge(1), level(2) }
    ACCESS          read-only
    STATUS          mandatory
    DESCRIPTION     
            "This value indicates if the interrupt is edge or level
             triggered."
    ::= { cpqSeEisaIntEntry 6 }

cpqSeEisaDmaTable OBJECT-TYPE
    SYNTAX          SEQUENCE OF CpqSeEisaDmaEntry
    ACCESS          not-accessible
    STATUS          mandatory
    DESCRIPTION     
            "A list of EISA function DMA configuration entries."
    ::= { cpqSeEisaNvram 5 }

cpqSeEisaDmaEntry OBJECT-TYPE
    SYNTAX          CpqSeEisaDmaEntry
    ACCESS          not-accessible
    STATUS          mandatory
    DESCRIPTION     
            "A description of an EISA function DMA configuration."
    INDEX           { cpqSeEisaDmaSlotIndex, cpqSeEisaDmaFunctIndex, 
                      cpqSeEisaDmaAllocIndex }
    ::= { cpqSeEisaDmaTable 1 }

CpqSeEisaDmaEntry ::=
    SEQUENCE {
        cpqSeEisaDmaSlotIndex           INTEGER,
        cpqSeEisaDmaFunctIndex          INTEGER,
        cpqSeEisaDmaAllocIndex          INTEGER,
        cpqSeEisaDmaChannel             INTEGER,
        cpqSeEisaDmaShare               INTEGER,
        cpqSeEisaDmaTiming              INTEGER,
        cpqSeEisaDmaXfer                INTEGER,
        cpqSeEisaDmaXferCount           INTEGER
    }

cpqSeEisaDmaSlotIndex OBJECT-TYPE
    SYNTAX          INTEGER (0..255)
    ACCESS          read-only
    STATUS          mandatory
    DESCRIPTION     
            "The EISA slot number of the board that registered the DMA
             configuration this entry describes."
    ::= { cpqSeEisaDmaEntry 1 }

cpqSeEisaDmaFunctIndex OBJECT-TYPE
    SYNTAX          INTEGER (0..255)
    ACCESS          read-only
    STATUS          mandatory
    DESCRIPTION     
            "The function in which this DMA configuration was registered."
    ::= { cpqSeEisaDmaEntry 2 }

cpqSeEisaDmaAllocIndex OBJECT-TYPE
    SYNTAX          INTEGER (0..255)
    ACCESS          read-only
    STATUS          mandatory
    DESCRIPTION     
            "The index for this DMA channel allocation entry in the EISA
             function block."
    ::= { cpqSeEisaDmaEntry 3 }

cpqSeEisaDmaChannel OBJECT-TYPE
    SYNTAX          INTEGER (0..65535)
    ACCESS          read-only
    STATUS          mandatory
    DESCRIPTION     
            "The DMA channel described in this entry."
    ::= { cpqSeEisaDmaEntry 4 }

cpqSeEisaDmaShare OBJECT-TYPE
    SYNTAX          INTEGER { nonshareable(1), shareable(2) }
    ACCESS          read-only
    STATUS          mandatory
    DESCRIPTION     
            "This value indicates if the DMA channel is shareable."
    ::= { cpqSeEisaDmaEntry 5 }

cpqSeEisaDmaTiming OBJECT-TYPE
    SYNTAX          INTEGER { isaTiming(1), typeA(2), typeB(3), 
                        burstTypeC(4) }
    ACCESS          read-only
    STATUS          mandatory
    DESCRIPTION     
            "This value indicates the timing (transfer rate) associated with
             this configuration of the DMA channel."
    ::= { cpqSeEisaDmaEntry 6 }

cpqSeEisaDmaXfer OBJECT-TYPE
    SYNTAX          INTEGER (0..65535)
    ACCESS          read-only
    STATUS          mandatory
    DESCRIPTION     
            "This value indicates the transfer size in bits used over this
             DMA channel."
    ::= { cpqSeEisaDmaEntry 7 }

cpqSeEisaDmaXferCount OBJECT-TYPE
    SYNTAX          INTEGER { byte(1), word(2) }
    ACCESS          read-only
    STATUS          mandatory
    DESCRIPTION     
            "This value indicates the addressing scheme for the DMA channel."
    ::= { cpqSeEisaDmaEntry 8 }

cpqSeEisaPortTable OBJECT-TYPE
    SYNTAX          SEQUENCE OF CpqSeEisaPortEntry
    ACCESS          not-accessible
    STATUS          mandatory
    DESCRIPTION     
            "A list of EISA function port I/O configuration entries."
    ::= { cpqSeEisaNvram 6 }

cpqSeEisaPortEntry OBJECT-TYPE
    SYNTAX          CpqSeEisaPortEntry
    ACCESS          not-accessible
    STATUS          mandatory
    DESCRIPTION     
            "A description of an EISA function port I/O configuration."
    INDEX           { cpqSeEisaPortSlotIndex, cpqSeEisaPortFunctIndex, 
                      cpqSeEisaPortAllocIndex }
    ::= { cpqSeEisaPortTable 1 }

CpqSeEisaPortEntry ::=
    SEQUENCE {
        cpqSeEisaPortSlotIndex          INTEGER,
        cpqSeEisaPortFunctIndex         INTEGER,
        cpqSeEisaPortAllocIndex         INTEGER,
        cpqSeEisaPortAddr               INTEGER,
        cpqSeEisaPortShare              INTEGER,
        cpqSeEisaPortSize               INTEGER
    }

cpqSeEisaPortSlotIndex OBJECT-TYPE
    SYNTAX          INTEGER (0..255)
    ACCESS          read-only
    STATUS          mandatory
    DESCRIPTION     
            "The EISA slot number of the board that registered the I/O port
             configuration this entry describes."
    ::= { cpqSeEisaPortEntry 1 }

cpqSeEisaPortFunctIndex OBJECT-TYPE
    SYNTAX          INTEGER (0..255)
    ACCESS          read-only
    STATUS          mandatory
    DESCRIPTION     
            "The function in which this port I/O configuration was
             registered."
    ::= { cpqSeEisaPortEntry 2 }

cpqSeEisaPortAllocIndex OBJECT-TYPE
    SYNTAX          INTEGER (0..255)
    ACCESS          read-only
    STATUS          mandatory
    DESCRIPTION     
            "The index for this I/O port range allocation entry in the EISA
             function block."
    ::= { cpqSeEisaPortEntry 3 }

cpqSeEisaPortAddr OBJECT-TYPE
    SYNTAX          INTEGER
    ACCESS          read-only
    STATUS          mandatory
    DESCRIPTION     
            "The I/O port address being described in this entry."
    ::= { cpqSeEisaPortEntry 4 }

cpqSeEisaPortShare OBJECT-TYPE
    SYNTAX          INTEGER { nonshareable(1), shareable(2) }
    ACCESS          read-only
    STATUS          mandatory
    DESCRIPTION     
            "This value indicates if the port is shareable."
    ::= { cpqSeEisaPortEntry 5 }

cpqSeEisaPortSize OBJECT-TYPE
    SYNTAX          INTEGER (0..65535)
    ACCESS          read-only
    STATUS          mandatory
    DESCRIPTION     
            "The number of sequential ports starting at the
             eisaPortAddrIndex that are be configured."
    ::= { cpqSeEisaPortEntry 6 }

cpqSeEisaFreeFormTable OBJECT-TYPE
    SYNTAX          SEQUENCE OF CpqSeEisaFreeFormEntry
    ACCESS          not-accessible
    STATUS          mandatory
    DESCRIPTION     
            "A list of EISA function free form entries."
    ::= { cpqSeEisaNvram 7 }

cpqSeEisaFreeFormEntry OBJECT-TYPE
    SYNTAX          CpqSeEisaFreeFormEntry
    ACCESS          not-accessible
    STATUS          mandatory
    DESCRIPTION     
            "A description of an EISA function free form."
    INDEX           { cpqSeEisaFreeFormSlotIndex, 
                      cpqSeEisaFreeFormFunctIndex }
    ::= { cpqSeEisaFreeFormTable 1 }

CpqSeEisaFreeFormEntry ::=
    SEQUENCE {
        cpqSeEisaFreeFormSlotIndex      INTEGER,
        cpqSeEisaFreeFormFunctIndex     INTEGER,
        cpqSeEisaFreeFormValue          OCTET STRING
    }

cpqSeEisaFreeFormSlotIndex OBJECT-TYPE
    SYNTAX          INTEGER (0..255)
    ACCESS          read-only
    STATUS          mandatory
    DESCRIPTION     
            "The EISA slot number of the board that registered the free form
             information this entry describes."
    ::= { cpqSeEisaFreeFormEntry 1 }

cpqSeEisaFreeFormFunctIndex OBJECT-TYPE
    SYNTAX          INTEGER (0..255)
    ACCESS          read-only
    STATUS          mandatory
    DESCRIPTION     
            "The function in which this free form was registered."
    ::= { cpqSeEisaFreeFormEntry 2 }

cpqSeEisaFreeFormValue OBJECT-TYPE
    SYNTAX          OCTET STRING (SIZE(0..205))
    ACCESS          read-only
    STATUS          mandatory
    DESCRIPTION     
            "The free form value."
    ::= { cpqSeEisaFreeFormEntry 3 }

cpqSeEisaInitTable OBJECT-TYPE
    SYNTAX          SEQUENCE OF CpqSeEisaInitEntry
    ACCESS          not-accessible
    STATUS          mandatory
    DESCRIPTION     
            "A list of EISA function port initialization entries."
    ::= { cpqSeEisaNvram 8 }

cpqSeEisaInitEntry OBJECT-TYPE
    SYNTAX          CpqSeEisaInitEntry
    ACCESS          not-accessible
    STATUS          mandatory
    DESCRIPTION     
            "A description of an EISA function port initialization."
    INDEX           { cpqSeEisaInitSlotIndex, cpqSeEisaInitFunctIndex, 
                      cpqSeEisaInitAllocIndex }
    ::= { cpqSeEisaInitTable 1 }

CpqSeEisaInitEntry ::=
    SEQUENCE {
        cpqSeEisaInitSlotIndex          INTEGER,
        cpqSeEisaInitFunctIndex         INTEGER,
        cpqSeEisaInitAllocIndex         INTEGER,
        cpqSeEisaInitUseMask            INTEGER,
        cpqSeEisaInitAccess             INTEGER,
        cpqSeEisaInitAddr               INTEGER,
        cpqSeEisaInitValue              INTEGER,
        cpqSeEisaInitMask               INTEGER
    }

cpqSeEisaInitSlotIndex OBJECT-TYPE
    SYNTAX          INTEGER (0..255)
    ACCESS          read-only
    STATUS          mandatory
    DESCRIPTION     
            "The EISA slot number of the board that registered the port
             initialization this entry describes."
    ::= { cpqSeEisaInitEntry 1 }

cpqSeEisaInitFunctIndex OBJECT-TYPE
    SYNTAX          INTEGER (0..255)
    ACCESS          read-only
    STATUS          mandatory
    DESCRIPTION     
            "The function in which this port initialization was registered."
    ::= { cpqSeEisaInitEntry 2 }

cpqSeEisaInitAllocIndex OBJECT-TYPE
    SYNTAX          INTEGER (0..255)
    ACCESS          read-only
    STATUS          mandatory
    DESCRIPTION     
            "The index for this port initialization entry in the EISA
             function block."
    ::= { cpqSeEisaInitEntry 3 }

cpqSeEisaInitUseMask OBJECT-TYPE
    SYNTAX          INTEGER { useValueOnly(1), useValueAndMask(2) }
    ACCESS          read-only
    STATUS          mandatory
    DESCRIPTION     
            "This indicates if a mask will be used when performing
             initialization."
    ::= { cpqSeEisaInitEntry 4 }

cpqSeEisaInitAccess OBJECT-TYPE
    SYNTAX          INTEGER { other(1), eightBitAddress(2), 
                        sixteenBitAddress(3), thirtyTwoBitAddress(4) }
    ACCESS          read-only
    STATUS          mandatory
    DESCRIPTION     
            "This value indicates the number of bits this entry initializes."
    ::= { cpqSeEisaInitEntry 5 }

cpqSeEisaInitAddr OBJECT-TYPE
    SYNTAX          INTEGER
    ACCESS          read-only
    STATUS          mandatory
    DESCRIPTION     
            "This value indicates the port address this entry initializes."
    ::= { cpqSeEisaInitEntry 6 }

cpqSeEisaInitValue OBJECT-TYPE
    SYNTAX          INTEGER
    ACCESS          read-only
    STATUS          mandatory
    DESCRIPTION     
            "This indicates the value to which this port is initialized."
    ::= { cpqSeEisaInitEntry 7 }

cpqSeEisaInitMask OBJECT-TYPE
    SYNTAX          INTEGER
    ACCESS          read-only
    STATUS          mandatory
    DESCRIPTION     
            "This value indicates the mask to use when performing
             initialization."
    ::= { cpqSeEisaInitEntry 8 }

cpqSeRom OBJECT IDENTIFIER
    ::= { cpqSeComponent 6 }

cpqSeSysRomVer OBJECT-TYPE
    SYNTAX          DisplayString (SIZE(0..255))
    ACCESS          read-only
    STATUS          mandatory
    DESCRIPTION     
            "System ROM version information."
    ::= { cpqSeRom 1 }

cpqSeOptRomTable OBJECT-TYPE
    SYNTAX          SEQUENCE OF CpqSeOptRomEntry
    ACCESS          not-accessible
    STATUS          mandatory
    DESCRIPTION     
            "A table of option ROM descriptions."
    ::= { cpqSeRom 2 }

cpqSeOptRomEntry OBJECT-TYPE
    SYNTAX          CpqSeOptRomEntry
    ACCESS          not-accessible
    STATUS          mandatory
    DESCRIPTION     
            "An option ROM description."
    INDEX           { cpqSeOptRomAddrIndex }
    ::= { cpqSeOptRomTable 1 }

CpqSeOptRomEntry ::=
    SEQUENCE {
        cpqSeOptRomAddrIndex            INTEGER,
        cpqSeOptRomSize                 INTEGER
    }

cpqSeOptRomAddrIndex OBJECT-TYPE
    SYNTAX          INTEGER (0..4294967295)
    ACCESS          read-only
    STATUS          mandatory
    DESCRIPTION     
            "The starting address of the option ROM.
             
             This value indicates the number of bytes from the start of
             physical memory to the beginning of this option ROM."
    ::= { cpqSeOptRomEntry 1 }

cpqSeOptRomSize OBJECT-TYPE
    SYNTAX          INTEGER (0..2147483647)
    ACCESS          read-only
    STATUS          mandatory
    DESCRIPTION     
            "The size in bytes of the option ROM."
    ::= { cpqSeOptRomEntry 2 }

cpqSeBiosRomDataRaw OBJECT-TYPE
    SYNTAX          OCTET STRING (SIZE(256))
    ACCESS          read-only
    STATUS          mandatory
    DESCRIPTION     
            "The BIOS ROM data area.  This may be the current contents or
             a copy of the BIOS ROM data area from when the Insight Agent was
             initialized."
    ::= { cpqSeRom 3 }

cpqSeRedundantSysRomVer OBJECT-TYPE
    SYNTAX          DisplayString (SIZE(0..255))
    ACCESS          read-only
    STATUS          mandatory
    DESCRIPTION     
            "System ROM version information for the redundant ROM
             image.  This will be left blank if the system does not
             support a redundant ROM."
    ::= { cpqSeRom 4 }

cpqSeSmbiosVer OBJECT-TYPE
    SYNTAX          DisplayString (SIZE(0..255))
    ACCESS          read-only
    STATUS          mandatory
    DESCRIPTION     
            "SMBIOS version information."
    ::= { cpqSeRom 5 }

cpqSeMPFwVer OBJECT-TYPE
    SYNTAX          DisplayString (SIZE(0..255))
    ACCESS          read-only
    STATUS          optional
    DESCRIPTION     
            "The version of Management Processor Firmware."
    ::= { cpqSeRom 6 }

cpqSeBMCFwVer OBJECT-TYPE
    SYNTAX          DisplayString (SIZE(0..255))
    ACCESS          read-only
    STATUS          optional
    DESCRIPTION     
            "The version of the manageability firmware."
    ::= { cpqSeRom 7 }

cpqSeHPVMFwVer OBJECT-TYPE
    SYNTAX          DisplayString (SIZE(0..255))
    ACCESS          read-only
    STATUS          optional
    DESCRIPTION     
            "The version of the virtual machine firmware."
    ::= { cpqSeRom 8 }

cpqSeKeyboard OBJECT IDENTIFIER
    ::= { cpqSeComponent 7 }

cpqSeKeyboardDesc OBJECT-TYPE
    SYNTAX          DisplayString (SIZE(0..255))
    ACCESS          read-only
    STATUS          mandatory
    DESCRIPTION     
            "A description of the keyboard."
    ::= { cpqSeKeyboard 1 }

cpqSeVideo OBJECT IDENTIFIER
    ::= { cpqSeComponent 8 }

cpqSeVideoDesc OBJECT-TYPE
    SYNTAX          DisplayString (SIZE(0..255))
    ACCESS          read-only
    STATUS          mandatory
    DESCRIPTION     
            "A description of the video system in the computer.  This may
             include the manufacturer, board name, modes supported, etc.."
    ::= { cpqSeVideo 1 }

cpqSeSerialPort OBJECT IDENTIFIER
    ::= { cpqSeComponent 9 }

cpqSeSerialPortTable OBJECT-TYPE
    SYNTAX          SEQUENCE OF CpqSeSerialPortEntry
    ACCESS          not-accessible
    STATUS          mandatory
    DESCRIPTION     
            "A table of serial port descriptions."
    ::= { cpqSeSerialPort 1 }

cpqSeSerialPortEntry OBJECT-TYPE
    SYNTAX          CpqSeSerialPortEntry
    ACCESS          not-accessible
    STATUS          mandatory
    DESCRIPTION     
            "A description of a serial port."
    INDEX           { cpqSeSerialPortIndex }
    ::= { cpqSeSerialPortTable 1 }

CpqSeSerialPortEntry ::=
    SEQUENCE {
        cpqSeSerialPortIndex            INTEGER,
        cpqSeSerialPortAddr             INTEGER,
        cpqSeSerialPortDesc             DisplayString,
        cpqSeSerialPortHwLocation       DisplayString
    }

cpqSeSerialPortIndex OBJECT-TYPE
    SYNTAX          INTEGER (0..65535)
    ACCESS          read-only
    STATUS          mandatory
    DESCRIPTION     
            "An index that uniquely specifies this entry."
    ::= { cpqSeSerialPortEntry 1 }

cpqSeSerialPortAddr OBJECT-TYPE
    SYNTAX          INTEGER
    ACCESS          read-only
    STATUS          mandatory
    DESCRIPTION     
            "The I/O port address used by this serial port."
    ::= { cpqSeSerialPortEntry 2 }

cpqSeSerialPortDesc OBJECT-TYPE
    SYNTAX          DisplayString (SIZE(0..255))
    ACCESS          read-only
    STATUS          mandatory
    DESCRIPTION     
            "A text description of further information known about the serial
             port.  This may be an empty string if no further information is
             known."
    ::= { cpqSeSerialPortEntry 3 }

cpqSeSerialPortHwLocation OBJECT-TYPE
    SYNTAX          DisplayString (SIZE(0..255))
    ACCESS          read-only
    STATUS          optional
    DESCRIPTION     
            "A text description of the hardware location, on complex
             multi SBB hardware only, for the serial port.
             A NULL string indicates that the hardware location could not
             be determined or is irrelevant."
    ::= { cpqSeSerialPortEntry 4 }

cpqSeParallelPort OBJECT IDENTIFIER
    ::= { cpqSeComponent 10 }

cpqSeParallelPortTable OBJECT-TYPE
    SYNTAX          SEQUENCE OF CpqSeParallelPortEntry
    ACCESS          not-accessible
    STATUS          mandatory
    DESCRIPTION     
            "A table of parallel port descriptions."
    ::= { cpqSeParallelPort 1 }

cpqSeParallelPortEntry OBJECT-TYPE
    SYNTAX          CpqSeParallelPortEntry
    ACCESS          not-accessible
    STATUS          mandatory
    DESCRIPTION     
            "A description of a parallel port."
    INDEX           { cpqSeParallelPortIndex }
    ::= { cpqSeParallelPortTable 1 }

CpqSeParallelPortEntry ::=
    SEQUENCE {
        cpqSeParallelPortIndex          INTEGER,
        cpqSeParallelPortAddr           INTEGER,
        cpqSeParallelPortDesc           DisplayString,
        cpqSeParrallelPortHwLocation    DisplayString
    }

cpqSeParallelPortIndex OBJECT-TYPE
    SYNTAX          INTEGER (0..65535)
    ACCESS          read-only
    STATUS          mandatory
    DESCRIPTION     
            "An index that uniquely specifies this entry."
    ::= { cpqSeParallelPortEntry 1 }

cpqSeParallelPortAddr OBJECT-TYPE
    SYNTAX          INTEGER
    ACCESS          read-only
    STATUS          mandatory
    DESCRIPTION     
            "The I/O port address used by this parallel port."
    ::= { cpqSeParallelPortEntry 2 }

cpqSeParallelPortDesc OBJECT-TYPE
    SYNTAX          DisplayString (SIZE(0..255))
    ACCESS          read-only
    STATUS          mandatory
    DESCRIPTION     
            "A text description of further information known about the
             parallel port.  This may be an empty string if no further
             information is known."
    ::= { cpqSeParallelPortEntry 3 }

cpqSeParrallelPortHwLocation OBJECT-TYPE
    SYNTAX          DisplayString (SIZE(0..255))
    ACCESS          read-only
    STATUS          optional
    DESCRIPTION     
            "A text description of the hardware location, on complex
             multi SBB hardware only, for the parallel port.
             A NULL string indicates that the hardware location could not
             be determined or is irrelevant."
    ::= { cpqSeParallelPortEntry 4 }

cpqSeFloppyDisk OBJECT IDENTIFIER
    ::= { cpqSeComponent 11 }

cpqSeFloppyDiskTable OBJECT-TYPE
    SYNTAX          SEQUENCE OF CpqSeFloppyDiskEntry
    ACCESS          not-accessible
    STATUS          mandatory
    DESCRIPTION     
            "A table of floppy drive descriptions."
    ::= { cpqSeFloppyDisk 1 }

cpqSeFloppyDiskEntry OBJECT-TYPE
    SYNTAX          CpqSeFloppyDiskEntry
    ACCESS          not-accessible
    STATUS          mandatory
    DESCRIPTION     
            "A floppy drive description."
    INDEX           { cpqSeFloppyDiskIndex }
    ::= { cpqSeFloppyDiskTable 1 }

CpqSeFloppyDiskEntry ::=
    SEQUENCE {
        cpqSeFloppyDiskIndex            INTEGER,
        cpqSeFloppyDiskType             INTEGER,
        cpqSeFloppyDiskHwLocation       DisplayString
    }

cpqSeFloppyDiskIndex OBJECT-TYPE
    SYNTAX          INTEGER (0..65535)
    ACCESS          read-only
    STATUS          mandatory
    DESCRIPTION     
            "An index that uniquely specifies this entry.  If possible, this
             field will map directly to the drive letter (0 for A:, 1 for B:)."
    ::= { cpqSeFloppyDiskEntry 1 }

cpqSeFloppyDiskType OBJECT-TYPE
    SYNTAX          INTEGER { other(1), drive360k(2), drive1200k(3), 
                        drive720k(4), drive1440k(5), drive120mb(6) }
    ACCESS          read-only
    STATUS          mandatory
    DESCRIPTION     
            "The type (capacity) of the floppy drive.  The following values
             are valid:
             
             other (1)       This floppy drive could not be identified.
             drive360k (2)   This is a 360 kilobyte, 5.25 inch floppy drive.
             drive1200k (3)  This is a 1.2 megabyte, 5.25 inch floppy drive.
             drive720k (4)   This is a 720 kilobyte, 3.5 inch floppy drive.
             drive1440k (5)  This is a 1.44 megabyte, 3.5 inch floppy drive.
             drive120mb(6)   This is a 120 megabyte, 3.5 inch floptical
                             drive."
    ::= { cpqSeFloppyDiskEntry 2 }

cpqSeFloppyDiskHwLocation OBJECT-TYPE
    SYNTAX          DisplayString (SIZE(0..255))
    ACCESS          read-only
    STATUS          optional
    DESCRIPTION     
            "A text description of the hardware location, on complex
             multi SBB hardware only, for the floppy disk.
             A NULL string indicates that the hardware location could not
             be determined or is irrelevant."
    ::= { cpqSeFloppyDiskEntry 3 }

cpqSeFixedDisk OBJECT IDENTIFIER
    ::= { cpqSeComponent 12 }

cpqSeFixedDiskTable OBJECT-TYPE
    SYNTAX          SEQUENCE OF CpqSeFixedDiskEntry
    ACCESS          not-accessible
    STATUS          mandatory
    DESCRIPTION     
            "A table of ST-506 interface accessible fixed disk descriptions."
    ::= { cpqSeFixedDisk 1 }

cpqSeFixedDiskEntry OBJECT-TYPE
    SYNTAX          CpqSeFixedDiskEntry
    ACCESS          not-accessible
    STATUS          mandatory
    DESCRIPTION     
            "A fixed disk description."
    INDEX           { cpqSeFixedDiskIndex }
    ::= { cpqSeFixedDiskTable 1 }

CpqSeFixedDiskEntry ::=
    SEQUENCE {
        cpqSeFixedDiskIndex             INTEGER,
        cpqSeFixedDiskType              INTEGER,
        cpqSeFixedDiskCyls              INTEGER,
        cpqSeFixedDiskHeads             INTEGER,
        cpqSeFixedDiskSectors           INTEGER,
        cpqSeFixedDiskCapacity          INTEGER,
        cpqSeFixedDiskHwLocation        DisplayString
    }

cpqSeFixedDiskIndex OBJECT-TYPE
    SYNTAX          INTEGER (0..65535)
    ACCESS          read-only
    STATUS          mandatory
    DESCRIPTION     
            "An index that uniquely specifies this entry.  Each possible
             index value indicates a specific drive as shown in the table
             below:
             
                 fixedDiskIndex   IDE/ESDI Controller  Drive Unit
                 =============   ===================  ==========
                     0               Primary             1
                     1               Primary             2
                     2               Secondary           1
                     3               Secondary           2
             
             Any other index value would be implementation specific."
    ::= { cpqSeFixedDiskEntry 1 }

cpqSeFixedDiskType OBJECT-TYPE
    SYNTAX          INTEGER (0..2147483647)
    ACCESS          read-only
    STATUS          mandatory
    DESCRIPTION     
            "The drive type."
    ::= { cpqSeFixedDiskEntry 2 }

cpqSeFixedDiskCyls OBJECT-TYPE
    SYNTAX          INTEGER (0..2147483647)
    ACCESS          read-only
    STATUS          mandatory
    DESCRIPTION     
            "The number of cylinders on the drive."
    ::= { cpqSeFixedDiskEntry 3 }

cpqSeFixedDiskHeads OBJECT-TYPE
    SYNTAX          INTEGER (0..2147483647)
    ACCESS          read-only
    STATUS          mandatory
    DESCRIPTION     
            "The number of heads on the drive."
    ::= { cpqSeFixedDiskEntry 4 }

cpqSeFixedDiskSectors OBJECT-TYPE
    SYNTAX          INTEGER (0..2147483647)
    ACCESS          read-only
    STATUS          mandatory
    DESCRIPTION     
            "The number of sectors per track on the drive."
    ::= { cpqSeFixedDiskEntry 5 }

cpqSeFixedDiskCapacity OBJECT-TYPE
    SYNTAX          INTEGER (0..2147483647)
    ACCESS          read-only
    STATUS          mandatory
    DESCRIPTION     
            "The capacity of the drive in megabytes."
    ::= { cpqSeFixedDiskEntry 6 }

cpqSeFixedDiskHwLocation OBJECT-TYPE
    SYNTAX          DisplayString (SIZE(0..255))
    ACCESS          read-only
    STATUS          optional
    DESCRIPTION     
            "A text description of the hardware location, on complex
             multi SBB hardware only, for the fixed disk.
             A NULL string indicates that the hardware location could not
             be determined or is irrelevant."
    ::= { cpqSeFixedDiskEntry 7 }

cpqSePci OBJECT IDENTIFIER
    ::= { cpqSeComponent 13 }

cpqSePciSlotTable OBJECT-TYPE
    SYNTAX          SEQUENCE OF CpqSePciSlotEntry
    ACCESS          not-accessible
    STATUS          mandatory
    DESCRIPTION     
            "A list of PCI slot information entries."
    ::= { cpqSePci 1 }

cpqSePciSlotEntry OBJECT-TYPE
    SYNTAX          CpqSePciSlotEntry
    ACCESS          not-accessible
    STATUS          mandatory
    DESCRIPTION     
            "A description of a PCI slot."
    INDEX           { cpqSePciSlotBusNumberIndex, 
                      cpqSePciSlotDeviceNumberIndex }
    ::= { cpqSePciSlotTable 1 }

CpqSePciSlotEntry ::=
    SEQUENCE {
        cpqSePciSlotBusNumberIndex      INTEGER,
        cpqSePciSlotDeviceNumberIndex   INTEGER,
        cpqSePciPhysSlot                INTEGER,
        cpqSePciSlotSubSystemID         OCTET STRING,
        cpqSePciSlotBoardName           DisplayString,
        cpqSePciSlotWidth               INTEGER,
        cpqSePciSlotSpeed               INTEGER,
        cpqSePciSlotExtendedInfo        INTEGER,
        cpqSePciSlotType                INTEGER,
        cpqSePciSlotCurrentMode         INTEGER,
        cpqSePciMaxSlotSpeed            INTEGER,
        cpqSePciXMaxSlotSpeed           INTEGER,
        cpqSePciCurrentSlotSpeed        INTEGER,
        cpqSePciHwLocation              DisplayString,
        cpqSePciSlotIOCTablePtr         INTEGER,
        cpqSePciSlotHeaderType          INTEGER,
        cpqSePciIsSlot0Embedded         INTEGER,
        cpqSePcieSlotMaxLinkSpeed       INTEGER,
        cpqSePcieSlotMaxLinkWidth       INTEGER
    }

cpqSePciSlotBusNumberIndex OBJECT-TYPE
    SYNTAX          INTEGER
    ACCESS          read-only
    STATUS          mandatory
    DESCRIPTION     
            "A number that uniquely identifies this device on its PCI bus. 
             Values greater than 255 are considered dummy bus numbers for empty PCI slots.
             For systems supporting multiple PCI segments, the segment will be encoded into the high order
             word of this value (Bit16 to Bit31). If PCI segment is not supported, the high order word will be 0."
    ::= { cpqSePciSlotEntry 1 }

cpqSePciSlotDeviceNumberIndex OBJECT-TYPE
    SYNTAX          INTEGER (0..255)
    ACCESS          read-only
    STATUS          mandatory
    DESCRIPTION     
            "A number that uniquely identifies this device on its PCI bus."
    ::= { cpqSePciSlotEntry 2 }

cpqSePciPhysSlot OBJECT-TYPE
    SYNTAX          INTEGER (0..255)
    ACCESS          read-only
    STATUS          mandatory
    DESCRIPTION     
            "The physical PCI slot number of this device.  Embedded devices
             will return 0 for this variable."
    ::= { cpqSePciSlotEntry 3 }

cpqSePciSlotSubSystemID OBJECT-TYPE
    SYNTAX          OCTET STRING (SIZE(0..7))
    ACCESS          read-only
    STATUS          mandatory
    DESCRIPTION     
            "Uniquely identifies the board configured in this slot. A zero
             length ID indicates the Subsystem ID is not supported and the
             (Device ID/Vendor ID) should be used for identification purposes.
             An ID of all 0xFFh indicates an empty slot."
    ::= { cpqSePciSlotEntry 4 }

cpqSePciSlotBoardName OBJECT-TYPE
    SYNTAX          DisplayString (SIZE(0..255))
    ACCESS          read-only
    STATUS          mandatory
    DESCRIPTION     
            "The product name (or other suitable description) of this PCI
             board. This field may be empty if no descriptive information
             is known about the board."
    ::= { cpqSePciSlotEntry 5 }

cpqSePciSlotWidth OBJECT-TYPE
    SYNTAX          INTEGER { other(1), unknown(2), thirtyTwoBit(3), 
                        sixtyFourBit(4), oneTwentyEightBit(5), x1(6), 
                        x2(7), x4(8), x8(9), x12(10), x16(11), x32(12) }
    ACCESS          read-only
    STATUS          mandatory
    DESCRIPTION     
            "The maximum data width supported by this PCI slot."
    ::= { cpqSePciSlotEntry 6 }

cpqSePciSlotSpeed OBJECT-TYPE
    SYNTAX          INTEGER { other(1), unknown(2), thirtyThreeMHz(3), 
                        sixtySixMHz(4) }
    ACCESS          read-only
    STATUS          obsolete
    DESCRIPTION     
            "The maximum speed supported by this PCI slot."
    ::= { cpqSePciSlotEntry 7 }

cpqSePciSlotExtendedInfo OBJECT-TYPE
    SYNTAX          INTEGER
    ACCESS          read-only
    STATUS          mandatory
    DESCRIPTION     
            "The PCI Extended Slot Information.
             
             This is a set of flags indicating extended features for the
             PCI slot.  Each bit has the following meaning when it is
             set (1):
             
                 Bit  0:     Extended SCSI PCI Slot
                 Bit  1:     PCI-X capable
                 Bits 2-31:  reserved (set to 0)
             
             NOTE:   bit 31 is the most significant bit, bit 0 is the least
                     significant."
    ::= { cpqSePciSlotEntry 8 }

cpqSePciSlotType OBJECT-TYPE
    SYNTAX          INTEGER { other(1), unknown(2), pci(3), pci66(4), 
                        pcix(5), pciexpress(6) }
    ACCESS          read-only
    STATUS          mandatory
    DESCRIPTION     
            "The type of PCI the slot.
             
             This indicates the capability of the slot, not the currently
             operating mode."
    ::= { cpqSePciSlotEntry 9 }

cpqSePciSlotCurrentMode OBJECT-TYPE
    SYNTAX          INTEGER { other(1), unknown(2), pci(3), pci66(4), 
                        pcix(5) }
    ACCESS          read-only
    STATUS          mandatory
    DESCRIPTION     
            "The current operating mode of PCI/PCI-X slot.
             
             This indicates the current operating mode of the device in the
             slot.  If the slot is empty, this value would be unknown."
    ::= { cpqSePciSlotEntry 10 }

cpqSePciMaxSlotSpeed OBJECT-TYPE
    SYNTAX          INTEGER
    ACCESS          read-only
    STATUS          mandatory
    DESCRIPTION     
            "The maximum speed in megahertz supported by this PCI slot.  If
             the slot also supports PCI-X, this value indicates the maximum
             speed of the slot when a non-PCI-X adapter is used.
             
             An entry of 0 indicates the speed is unknown."
    ::= { cpqSePciSlotEntry 11 }

cpqSePciXMaxSlotSpeed OBJECT-TYPE
    SYNTAX          INTEGER
    ACCESS          read-only
    STATUS          mandatory
    DESCRIPTION     
            "The maximum speed in megahertz supported by this PCI-X slot.
             
             An entry of 0 indicates the speed is unknown.  An entry
             of -1 indicates the slot does not support PCI-X."
    ::= { cpqSePciSlotEntry 12 }

cpqSePciCurrentSlotSpeed OBJECT-TYPE
    SYNTAX          INTEGER
    ACCESS          read-only
    STATUS          mandatory
    DESCRIPTION     
            "The current speed in megahertz of the adapter in this PCI
             or PCI-X slot.
             
             An entry of 0 indicates the speed is could not be determined or
             the slot is empty."
    ::= { cpqSePciSlotEntry 13 }

cpqSePciHwLocation OBJECT-TYPE
    SYNTAX          DisplayString (SIZE(0..255))
    ACCESS          read-only
    STATUS          optional
    DESCRIPTION     
            "A text description of the hardware location, on complex
             multi SBB hardware only, for the Peripheral Component
             Interconnect (PCI)  bus.
             A NULL string indicates that the hardware location could not
             be determined or is irrelevant."
    ::= { cpqSePciSlotEntry 14 }

cpqSePciSlotIOCTablePtr OBJECT-TYPE
    SYNTAX          INTEGER (0..19)
    ACCESS          read-only
    STATUS          mandatory
    DESCRIPTION     
            "Index for the I/O Chassis in cpqSePCISlotIOCTablePtr where this PCI slot is physically located."
    ::= { cpqSePciSlotEntry 15 }

cpqSePciSlotHeaderType OBJECT-TYPE
    SYNTAX          INTEGER
    ACCESS          read-only
    STATUS          mandatory
    DESCRIPTION     
            "This represents header type byte of a PCI device"
    ::= { cpqSePciSlotEntry 16 }

cpqSePciIsSlot0Embedded OBJECT-TYPE
    SYNTAX          INTEGER { true(1), false(2) }
    ACCESS          read-only
    STATUS          optional
    DESCRIPTION     
            "This OID indicates whether PCI slot 0 is embedded in the machine or not."
    ::= { cpqSePciSlotEntry 17 }

cpqSePcieSlotMaxLinkSpeed OBJECT-TYPE
    SYNTAX          INTEGER
    ACCESS          read-only
    STATUS          optional
    DESCRIPTION     
            "This is the maximum link speed for the PCIe slot. An entry of 0 indicates 
             the maximum link speed could not be determined or the slot is not PCIe. 
             The unit is Mb/s."
    ::= { cpqSePciSlotEntry 18 }

cpqSePcieSlotMaxLinkWidth OBJECT-TYPE
    SYNTAX          INTEGER
    ACCESS          read-only
    STATUS          optional
    DESCRIPTION     
            "This is the maximum link for the PCIe slot. Value N means N lanes.
             An entry of 0 indicates the maximum link width could not be determined 
             or the slot is not PCIe."
    ::= { cpqSePciSlotEntry 19 }

cpqSePciFunctTable OBJECT-TYPE
    SYNTAX          SEQUENCE OF CpqSePciFunctEntry
    ACCESS          not-accessible
    STATUS          mandatory
    DESCRIPTION     
            "A list of PCI function information entries."
    ::= { cpqSePci 2 }

cpqSePciFunctEntry OBJECT-TYPE
    SYNTAX          CpqSePciFunctEntry
    ACCESS          not-accessible
    STATUS          mandatory
    DESCRIPTION     
            "A description of the functions in each PCI slot."
    INDEX           { cpqSePciFunctBusNumberIndex, 
                      cpqSePciFunctDeviceNumberIndex, cpqSePciFunctIndex }
    ::= { cpqSePciFunctTable 1 }

CpqSePciFunctEntry ::=
    SEQUENCE {
        cpqSePciFunctBusNumberIndex     INTEGER,
        cpqSePciFunctDeviceNumberIndex  INTEGER,
        cpqSePciFunctIndex              INTEGER,
        cpqSePciFunctClassCode          OCTET STRING,
        cpqSePciFunctClassDescription   DisplayString,
        cpqSePciFunctDeviceID           INTEGER,
        cpqSePciFunctVendorID           INTEGER,
        cpqSePciFunctRevID              INTEGER,
        cpqSePciFunctIntLine            INTEGER,
        cpqSePciFunctDevStatus          INTEGER,
        cpqSePciFunctHwLocation         DisplayString,
        cpqSePcieFunctNegotiatedLinkSpeed INTEGER,
        cpqSePcieFunctNegotiatedLinkWidth INTEGER,
        cpqSePcieFunctMaxLinkSpeed      INTEGER,
        cpqSePcieFunctMaxLinkWidth      INTEGER
    }

cpqSePciFunctBusNumberIndex OBJECT-TYPE
    SYNTAX          INTEGER
    ACCESS          read-only
    STATUS          mandatory
    DESCRIPTION     
            "The PCI  bus number for this device function.
             For systems supporting multiple PCI segments, the segment will be encoded into the high order
             word of this value (Bit16 to Bit31). If PCI segment is not supported, the high order word will be 0."
    ::= { cpqSePciFunctEntry 1 }

cpqSePciFunctDeviceNumberIndex OBJECT-TYPE
    SYNTAX          INTEGER (0..255)
    ACCESS          read-only
    STATUS          mandatory
    DESCRIPTION     
            "The device index for this function."
    ::= { cpqSePciFunctEntry 2 }

cpqSePciFunctIndex OBJECT-TYPE
    SYNTAX          INTEGER (0..7)
    ACCESS          read-only
    STATUS          mandatory
    DESCRIPTION     
            " The unique index that specifies this function."
    ::= { cpqSePciFunctEntry 3 }

cpqSePciFunctClassCode OBJECT-TYPE
    SYNTAX          OCTET STRING (SIZE(0..3))
    ACCESS          read-only
    STATUS          mandatory
    DESCRIPTION     
            "The class code register as defined in the PCI Local
             Bus Specification in the following format:
                      Octet        Register
                      -----        --------
                        1          Programming Interface
                        2          Sub-class code
                        3          Base class code"
    ::= { cpqSePciFunctEntry 4 }

cpqSePciFunctClassDescription OBJECT-TYPE
    SYNTAX          DisplayString (SIZE(0..80))
    ACCESS          read-only
    STATUS          mandatory
    DESCRIPTION     
            "A text string which describes the PCI Base Class and
             Sub Class to which this device belongs. This field
             may empty if no descriptive information is known about
             this function's class."
    ::= { cpqSePciFunctEntry 5 }

cpqSePciFunctDeviceID OBJECT-TYPE
    SYNTAX          INTEGER (0..65535)
    ACCESS          read-only
    STATUS          mandatory
    DESCRIPTION     
            "This variable identifies this particular device.  This
             identifier is allocated by the component manufacturer."
    ::= { cpqSePciFunctEntry 6 }

cpqSePciFunctVendorID OBJECT-TYPE
    SYNTAX          INTEGER (0..65535)
    ACCESS          read-only
    STATUS          mandatory
    DESCRIPTION     
            "This variable identifies the component manufacturer.  Valid
             identifiers are assigned by the PCI SIG."
    ::= { cpqSePciFunctEntry 7 }

cpqSePciFunctRevID OBJECT-TYPE
    SYNTAX          INTEGER (0..255)
    ACCESS          read-only
    STATUS          mandatory
    DESCRIPTION     
            "This variable is a vendor defined extension to the device ID and
             specifies a device specific revision identifier."
    ::= { cpqSePciFunctEntry 8 }

cpqSePciFunctIntLine OBJECT-TYPE
    SYNTAX          INTEGER (0..255)
    ACCESS          read-only
    STATUS          mandatory
    DESCRIPTION     
            "This variable specifies which input of the system interrupt
             controller(s) the device's interrupt pin is connected to.
             A value of 0ffh means unknown or no connection."
    ::= { cpqSePciFunctEntry 9 }

cpqSePciFunctDevStatus OBJECT-TYPE
    SYNTAX          INTEGER { unknown(1), enabled(2), disabled(3) }
    ACCESS          read-only
    STATUS          mandatory
    DESCRIPTION     
            "The status of the device described by this function.
             Some PCI devices, such as embedded devices, have the
             potential of being present but disabled. "
    ::= { cpqSePciFunctEntry 10 }

cpqSePciFunctHwLocation OBJECT-TYPE
    SYNTAX          DisplayString (SIZE(0..255))
    ACCESS          read-only
    STATUS          optional
    DESCRIPTION     
            "A text description of the hardware location, on complex 
             multi SBB hardware only, for the Peripheral Component
             Interconnect (PCI)  bus.
             A NULL string indicates that the hardware location could not
             be determined or is irrelevant."
    ::= { cpqSePciFunctEntry 11 }

cpqSePcieFunctNegotiatedLinkSpeed OBJECT-TYPE
    SYNTAX          INTEGER
    ACCESS          read-only
    STATUS          optional
    DESCRIPTION     
            "This is the negotiated link speed for the PCIe link of the PCI device. 
             An entry of 0 indicates the negotiated link speed could not be determined 
             or the device is not PCIe. The unit is Mb/s."
    ::= { cpqSePciFunctEntry 12 }

cpqSePcieFunctNegotiatedLinkWidth OBJECT-TYPE
    SYNTAX          INTEGER
    ACCESS          read-only
    STATUS          optional
    DESCRIPTION     
            "This is the negotiated link width for the PCIe link of the device. 
             Value N means N lanes. An entry of 0 indicates the negotiated link width 
             could not be determined or the device is not PCIe."
    ::= { cpqSePciFunctEntry 13 }

cpqSePcieFunctMaxLinkSpeed OBJECT-TYPE
    SYNTAX          INTEGER
    ACCESS          read-only
    STATUS          optional
    DESCRIPTION     
            "This is the maximum link speed for the PCIe device. An entry of 0 indicates 
             the maximum link speed could not be determined or the device is not PCIe. 
             The unit is Mb/s."
    ::= { cpqSePciFunctEntry 14 }

cpqSePcieFunctMaxLinkWidth OBJECT-TYPE
    SYNTAX          INTEGER
    ACCESS          read-only
    STATUS          optional
    DESCRIPTION     
            "This is the maximum link width for the PCIe device. Value N means N lanes. 
             An entry of 0 indicates the maximum link width could not be determined 
             or the device is not PCIe."
    ::= { cpqSePciFunctEntry 15 }

cpqSePciMemoryTable OBJECT-TYPE
    SYNTAX          SEQUENCE OF CpqSePciMemoryEntry
    ACCESS          not-accessible
    STATUS          mandatory
    DESCRIPTION     
            "A list of PCI base memory entries"
    ::= { cpqSePci 3 }

cpqSePciMemoryEntry OBJECT-TYPE
    SYNTAX          CpqSePciMemoryEntry
    ACCESS          not-accessible
    STATUS          mandatory
    DESCRIPTION     
            "A description of the base memory usage in each function"
    INDEX           { cpqSePciMemoryBusNumberIndex, 
                      cpqSePciMemoryDeviceNumberIndex, 
                      cpqSePciMemoryFunctionIndex, cpqSePciMemoryIndex }
    ::= { cpqSePciMemoryTable 1 }

CpqSePciMemoryEntry ::=
    SEQUENCE {
        cpqSePciMemoryBusNumberIndex    INTEGER,
        cpqSePciMemoryDeviceNumberIndex INTEGER,
        cpqSePciMemoryFunctionIndex     INTEGER,
        cpqSePciMemoryIndex             INTEGER,
        cpqSePciMemoryBaseAddr          INTEGER,
        cpqSePciMemoryType              INTEGER,
        cpqSePciMemorySize              INTEGER,
        cpqSePciMemoryHwLocation        DisplayString
    }

cpqSePciMemoryBusNumberIndex OBJECT-TYPE
    SYNTAX          INTEGER
    ACCESS          read-only
    STATUS          mandatory
    DESCRIPTION     
            "The PCI  bus number for this memory entry.
             For systems supporting multiple PCI segments, the segment will be encoded into the high order 
             word of this value (Bit16 to Bit31). If PCI segment is not supported, the high order word will be 0."
    ::= { cpqSePciMemoryEntry 1 }

cpqSePciMemoryDeviceNumberIndex OBJECT-TYPE
    SYNTAX          INTEGER (0..255)
    ACCESS          read-only
    STATUS          mandatory
    DESCRIPTION     
            "The device index for this memory entry"
    ::= { cpqSePciMemoryEntry 2 }

cpqSePciMemoryFunctionIndex OBJECT-TYPE
    SYNTAX          INTEGER (0..7)
    ACCESS          read-only
    STATUS          mandatory
    DESCRIPTION     
            " The unique index that specifies the function associated
             with this memory entry."
    ::= { cpqSePciMemoryEntry 3 }

cpqSePciMemoryIndex OBJECT-TYPE
    SYNTAX          INTEGER (0..6)
    ACCESS          read-only
    STATUS          mandatory
    DESCRIPTION     
            " The unique index that specifies this memory entry. "
    ::= { cpqSePciMemoryEntry 4 }

cpqSePciMemoryBaseAddr OBJECT-TYPE
    SYNTAX          INTEGER
    ACCESS          read-only
    STATUS          mandatory
    DESCRIPTION     
            "Base address of this memory usage entry."
    ::= { cpqSePciMemoryEntry 5 }

cpqSePciMemoryType OBJECT-TYPE
    SYNTAX          INTEGER { unknown(1), io(2), memory-mapped(3), 
                        exp-rom(4) }
    ACCESS          read-only
    STATUS          mandatory
    DESCRIPTION     
            "The type of memory this entry describes.  This variable
             is used to determine if this memory entry maps into
             memory, expansion rom or I/O space."
    ::= { cpqSePciMemoryEntry 6 }

cpqSePciMemorySize OBJECT-TYPE
    SYNTAX          INTEGER
    ACCESS          read-only
    STATUS          mandatory
    DESCRIPTION     
            "This variable specifies how much address space this function
             requires.  A value of 0 will be returned if the agent cannot
             obtain this information."
    ::= { cpqSePciMemoryEntry 7 }

cpqSePciMemoryHwLocation OBJECT-TYPE
    SYNTAX          DisplayString (SIZE(0..255))
    ACCESS          read-only
    STATUS          optional
    DESCRIPTION     
            "A text description of the hardware location, on complex
             multi SBB hardware only, for the Peripheral Component
             Interconnect (PCI)  bus.
             A NULL string indicates that the hardware location could not
             be determined or is irrelevant."
    ::= { cpqSePciMemoryEntry 8 }

cpqSePciSegmentMode OBJECT-TYPE
    SYNTAX          INTEGER { unknown(1), single-segment(2), 
                        multi-segment(3), auto-segment(4) }
    ACCESS          read-only
    STATUS          optional
    DESCRIPTION     
            "The PCI segment mode of the system, if supported."
    ::= { cpqSePci 4 }

cpqSePCCard OBJECT IDENTIFIER
    ::= { cpqSeComponent 14 }

cpqSePCCardSlotTable OBJECT-TYPE
    SYNTAX          SEQUENCE OF CpqSePCCardSlotEntry
    ACCESS          not-accessible
    STATUS          mandatory
    DESCRIPTION     
            "A list of PC Card slot information entries."
    ::= { cpqSePCCard 1 }

cpqSePCCardSlotEntry OBJECT-TYPE
    SYNTAX          CpqSePCCardSlotEntry
    ACCESS          not-accessible
    STATUS          mandatory
    DESCRIPTION     
            "A PC Card slot description table entry.
             A table entry is defined for each PC Card Slot in the
             current system configuration."
    INDEX           { cpqSePCCardSlotIndex }
    ::= { cpqSePCCardSlotTable 1 }

CpqSePCCardSlotEntry ::=
    SEQUENCE {
        cpqSePCCardSlotIndex            INTEGER,
        cpqSePCCardCondition            INTEGER,
        cpqSePCCardPhysLocation         DisplayString,
        cpqSePCCardSlotType             INTEGER,
        cpqSePCCardSlotWidth            INTEGER,
        cpqSePCCardSlotThermalCapacity  INTEGER,
        cpqSePCCardSlotThermalSensor    INTEGER,
        cpqSePCCardSlotPowerState       INTEGER,
        cpqSePCCardStatus               INTEGER,
        cpqSePCCardDeviceInfo           DisplayString,
        cpqSePCCardProductInfo          DisplayString,
        cpqSePCCardSerialNumber         DisplayString,
        cpqSePCCardAssetTag             DisplayString
    }

cpqSePCCardSlotIndex OBJECT-TYPE
    SYNTAX          INTEGER
    ACCESS          read-only
    STATUS          mandatory
    DESCRIPTION     
            "Defines the logical PC Card slot number for this PC Card Slot.
             In addition, the slot number serves as the index into the
             PC Card data table.  Typical index ranges will be either 1 to
             4 (for 4 slots) or 1 to 2 (for 2 slots).  (Un)Docking may
             cause the supported index range to change dynamically."
    ::= { cpqSePCCardSlotEntry 1 }

cpqSePCCardCondition OBJECT-TYPE
    SYNTAX          INTEGER { unknown(1), ok(2), degraded(3), failed(4) }
    ACCESS          read-only
    STATUS          mandatory
    DESCRIPTION     
            "Defines the overall condition of the PC Card.
             The supported values are defined as follows:
             
                unknown(1)
                     The current condition is unknown for the PC Card or PC Card Slot.
             
                ok(2)
                     PC Card operations are normal.
                     No user action required.
             
                degraded (3)
                     PC Card operations have degraded.
                     Consult the cpqSePCCardStatus field for recommended actions.
             
                failed (4)
                     PC Card operations have failed.
                     Consult the cpqSePCCardStatus field for recommended actions."
    ::= { cpqSePCCardSlotEntry 2 }

cpqSePCCardPhysLocation OBJECT-TYPE
    SYNTAX          DisplayString (SIZE(0..40))
    ACCESS          read-only
    STATUS          mandatory
    DESCRIPTION     
            "Defines the user level PC Card Slot location description.
             Text strings supported are:
                 - System Unit Top Slot,
                 - System Unit Bottom Slot,
                 - Docking Station Top Slot,
                 - Docking Station Bottom Slot."
    ::= { cpqSePCCardSlotEntry 3 }

cpqSePCCardSlotType OBJECT-TYPE
    SYNTAX          INTEGER
    ACCESS          read-only
    STATUS          mandatory
    DESCRIPTION     
            "Defines the PC Card Slot capabilities.
             This is a bit mapped value defined by DMI Mobile Supplement for the System Slots Group,
             Slot Type. Bits of interest for PC Card support are:
                 Bit 6 - PCMCIA slot (if set),
                 Bit 13 - 16 bit PC Card capable (if set),
                 Bit 14 - CardBus PC Card capable (if set),
                 Bit 15 - ZV Port capable (if set),
                 Bit 16 - Modem Ring Resume capable (if set), 
             All other bits should be zero (reset) for PC Card slots."
    ::= { cpqSePCCardSlotEntry 4 }

cpqSePCCardSlotWidth OBJECT-TYPE
    SYNTAX          INTEGER { other(1), unknown(2), width8bit(3), 
                        width16bit(4), width32bit(5), width64bit(6), 
                        width128bit(7) }
    ACCESS          read-only
    STATUS          mandatory
    DESCRIPTION     
            "Defines the maximum bus width for this PC Card Slot.
             The supported values are defined as follows:
             
                 Other (1)
                     Value is not in defined list.
             
                 Unknown (2)
                     Actual value is not known.
             
                 width 8 bit (3)
                     Bus is 8 bits wide.
             
                 width 16 bit (4)
                     Bus is 16 bits wide.
             
                 width 32 bit (5)
                     Bus is 32 bits wide.
             
                 width 64 bit (6)
                     Bus is 64 bits wide.
             
                 width 128 bit (7)
                     Bus is 128 bits wide."
    ::= { cpqSePCCardSlotEntry 5 }

cpqSePCCardSlotThermalCapacity OBJECT-TYPE
    SYNTAX          INTEGER
    ACCESS          read-only
    STATUS          mandatory
    DESCRIPTION     
            "Defines the maximum thermal dissipation capacity (milliwatts)
             for this PC Card Slot.  A value of zero indicates the thermal
             capacity is unknown.  A non-zero value indicates the thermal
             capacity in milliwatts."
    ::= { cpqSePCCardSlotEntry 6 }

cpqSePCCardSlotThermalSensor OBJECT-TYPE
    SYNTAX          INTEGER (0..65535)
    ACCESS          read-only
    STATUS          mandatory
    DESCRIPTION     
            "Defines the Thermal Sensor ID that monitors this PC Card Slot.
             A value of zero indicates that a sensor is not present or
             unknown for this slot.  A non-zero value indicates the sensor
             ID as defined by the platform firmware."
    ::= { cpqSePCCardSlotEntry 7 }

cpqSePCCardSlotPowerState OBJECT-TYPE
    SYNTAX          INTEGER { unknown(1), on(2), off(3) }
    ACCESS          read-only
    STATUS          mandatory
    DESCRIPTION     
            "Defines the current power state (On/Off) for this PC Card Slot.
             The supported values are defined as follows:
             
                 unknown (1)
                   Current power state is unknown.
             
                 on (2)
                   Power is currently on.
             
                 off (3)
                   Power is currently off."
    ::= { cpqSePCCardSlotEntry 8 }

cpqSePCCardStatus OBJECT-TYPE
    SYNTAX          INTEGER { unknown(1), ok(2), thermalDegraded(3), 
                        thermalFailure(4) }
    ACCESS          read-only
    STATUS          mandatory
    DESCRIPTION     
            "Defines the operating status for the card in this PC Card Slot.
             The supported values are defined as follows:
             
                 unknown (1)
                     The current status is not known for the PC Card or
                     PC Card Slot.
             
                 ok (2)
                     PC Card operations are normal.
                     No user action required.
             
                 thermalDegraded (3)
                     PC Card operations have degraded due to unsafe thermal
                     conditions.
                     Recommended Actions include: 
                         Discontinue the use of the PC Card as soon as
                         possible.  If a Modem or LAN card then close
                         all communication applications/links.   If a
                         Memory, ATA, or SCSI device then close all
                         open/related files.  Remove PC Card from slot
                         after use is discontinued, if possible.
             
                 thermalFailure (4)
                     PC Card operations have failed due to unsafe thermal
                     conditions.  The PC Card will automatically be powered
                     off to protect itself and the system.
                     Recommended Actions include:
                         Discontinue the use of the PC Card immediately.
                         If a Modem or LAN card then close all communication applications/links.
                         If a Memory, ATA, or SCSI device then close all open/related files.
                         Remove PC Card from slot after use is discontinued, if possible."
    ::= { cpqSePCCardSlotEntry 9 }

cpqSePCCardDeviceInfo OBJECT-TYPE
    SYNTAX          DisplayString (SIZE(0..80))
    ACCESS          read-only
    STATUS          mandatory
    DESCRIPTION     
            "Defines the PC Card Manufacturer / Device information for
             the card in this PC Card Slot.  The returned string data is
             read from the PC Card's onboard Card Information Structure
             (CIS)."
    ::= { cpqSePCCardSlotEntry 10 }

cpqSePCCardProductInfo OBJECT-TYPE
    SYNTAX          DisplayString (SIZE(0..80))
    ACCESS          read-only
    STATUS          mandatory
    DESCRIPTION     
            "Defines the PC Card Model / Part Number information for
             the card in this PC Card Slot.  The returned string data
             is read from the PC Card's onboard Card Information
             Structure (CIS)."
    ::= { cpqSePCCardSlotEntry 11 }

cpqSePCCardSerialNumber OBJECT-TYPE
    SYNTAX          DisplayString (SIZE(0..80))
    ACCESS          read-only
    STATUS          mandatory
    DESCRIPTION     
            "Defines the PC Card Serial Number information for the
             card in this PC Card Slot.   The returned string data is
             read from the PC Card's onboard Card Information Structure
             (CIS)."
    ::= { cpqSePCCardSlotEntry 12 }

cpqSePCCardAssetTag OBJECT-TYPE
    SYNTAX          DisplayString (SIZE(0..80))
    ACCESS          read-only
    STATUS          mandatory
    DESCRIPTION     
            "Defines the PC Card Asset Tag information for the card in
             this PC Card Slot.   The returned string data is read from
             the PC Card's onboard Card Information Structure (CIS)."
    ::= { cpqSePCCardSlotEntry 13 }

cpqSeUSBPort OBJECT IDENTIFIER
    ::= { cpqSeComponent 15 }

cpqSeUSBPortTable OBJECT-TYPE
    SYNTAX          SEQUENCE OF CpqSeUSBPortEntry
    ACCESS          not-accessible
    STATUS          mandatory
    DESCRIPTION     
            "A table of USB built-in port descriptions containing one entry 
             for each physical USB connector shipped on the system. 
             Add-in USB ports are not reflected in this table."
    ::= { cpqSeUSBPort 1 }

cpqSeUSBPortEntry OBJECT-TYPE
    SYNTAX          CpqSeUSBPortEntry
    ACCESS          not-accessible
    STATUS          mandatory
    DESCRIPTION     
            "A description of a USB port."
    INDEX           { cpqSeUSBPortIndex }
    ::= { cpqSeUSBPortTable 1 }

CpqSeUSBPortEntry ::=
    SEQUENCE {
        cpqSeUSBPortIndex               INTEGER,
        cpqSeUSBPortType                INTEGER,
        cpqSeUSBPortHwLocation          DisplayString,
        cpqSeUSBPortStatus              INTEGER,
        cpqSeUSBPortDeviceName          DisplayString
    }

cpqSeUSBPortIndex OBJECT-TYPE
    SYNTAX          INTEGER (1..65535)
    ACCESS          read-only
    STATUS          mandatory
    DESCRIPTION     
            "An index that uniquely specifies this entry."
    ::= { cpqSeUSBPortEntry 1 }

cpqSeUSBPortType OBJECT-TYPE
    SYNTAX          INTEGER { other(1), usbPort(2), sdPort(3) }
    ACCESS          read-only
    STATUS          mandatory
    DESCRIPTION     
            "The port type.
             The supported values are defined as follows:
             
             other (1)
                 USB/SD port data is not available.
             
             usbPort (2)
                 The port is a USB Port.
             
             usbPort (3)
                 The port is a SD Port."
    ::= { cpqSeUSBPortEntry 2 }

cpqSeUSBPortHwLocation OBJECT-TYPE
    SYNTAX          DisplayString (SIZE(0..255))
    ACCESS          read-only
    STATUS          optional
    DESCRIPTION     
            "A text description of the hardware location, on complex
             multi SBB hardware only, for the USB port.
             A NULL string indicates that the hardware location could not
             be determined or is irrelevant."
    ::= { cpqSeUSBPortEntry 3 }

cpqSeUSBPortStatus OBJECT-TYPE
    SYNTAX          INTEGER { other(1), notPopulated(2), populated(3) }
    ACCESS          read-only
    STATUS          mandatory
    DESCRIPTION     
            "The port status.
             The supported values are defined as follows:
             
             other (1)
                 USB/SD port is not available.
             
             notPopulated (2)
                 The port is a USB/SD Port is not populated.
             
             populated (3)
                 The port is a USB/SD Port is populated."
    ::= { cpqSeUSBPortEntry 4 }

cpqSeUSBPortDeviceName OBJECT-TYPE
    SYNTAX          DisplayString (SIZE(0..255))
    ACCESS          read-only
    STATUS          optional
    DESCRIPTION     
            "A text description of the USB/SD port device name.
             A NULL string indicates that the device name could not
             be determined or is irrelevant."
    ::= { cpqSeUSBPortEntry 5 }

cpqSeCell OBJECT IDENTIFIER
    ::= { cpqSeComponent 16 }

cpqSeCellTable OBJECT-TYPE
    SYNTAX          SEQUENCE OF CpqSeCellEntry
    ACCESS          not-accessible
    STATUS          optional
    DESCRIPTION     
            "A list of cells in the partition."
    ::= { cpqSeCell 1 }

cpqSeCellEntry OBJECT-TYPE
    SYNTAX          CpqSeCellEntry
    ACCESS          not-accessible
    STATUS          optional
    DESCRIPTION     
            "A description of a cell in the system."
    INDEX           { cpqSeCellUnitIndex }
    ::= { cpqSeCellTable 1 }

CpqSeCellEntry ::=
    SEQUENCE {
        cpqSeCellUnitIndex              INTEGER,
        cpqSeCellCabinetNumber          INTEGER,
        cpqSeCellCellNumber             INTEGER,
        cpqSeCellIOCTablePtr            INTEGER,
        cpqSeCellPDHCFirmwareRevision   DisplayString,
        cpqSeCellSysFwVersion           DisplayString,
        cpqSeCellBootInhibited          TruthValue,
        cpqSeCellToScanBusConnectionStatus  INTEGER,
        cpqSeCellHasCoreIO              TruthValue,
        cpqSeCellBoardSpeed             INTEGER,
        cpqSeCellPresent                TruthValue,
        cpqSeCellHasPower               TruthValue,
        cpqSeCellReadyForReconfig       TruthValue,
        cpqSeCellTotalMemory            INTEGER,
        cpqSeCellLEDState               INTEGER,
        cpqSeCellState                  INTEGER,
        cpqSeCellCLMRequestPercentage   INTEGER,
        cpqSeCellCLMRequestSize         INTEGER,
        cpqSeCellCLMAllocatedSize       INTEGER,
        cpqSeCellInterleaveAllocatedSize INTEGER,
        cpqSeCellHasInterleaveMem       INTEGER,
        cpqSeCellSerialNumber           DisplayString,
        cpqSeCellCLMCondition           INTEGER
    }

cpqSeCellUnitIndex OBJECT-TYPE
    SYNTAX          INTEGER (0..15)
    ACCESS          read-only
    STATUS          optional
    DESCRIPTION     
            "This is a number that uniquely specifies the cell."
    ::= { cpqSeCellEntry 1 }

cpqSeCellCabinetNumber OBJECT-TYPE
    SYNTAX          INTEGER (0..1)
    ACCESS          read-only
    STATUS          optional
    DESCRIPTION     
            "This value represents the cabinet that the cell belongs to."
    ::= { cpqSeCellEntry 2 }

cpqSeCellCellNumber OBJECT-TYPE
    SYNTAX          INTEGER (0..7)
    ACCESS          read-only
    STATUS          optional
    DESCRIPTION     
            "This value is cell/slot number that is unique across the cabinet."
    ::= { cpqSeCellEntry 3 }

cpqSeCellIOCTablePtr OBJECT-TYPE
    SYNTAX          INTEGER (0..19)
    ACCESS          read-only
    STATUS          optional
    DESCRIPTION     
            "Table index for the I/O chassis which is connected to this cell."
    ::= { cpqSeCellEntry 4 }

cpqSeCellPDHCFirmwareRevision OBJECT-TYPE
    SYNTAX          DisplayString (SIZE(0..255))
    ACCESS          read-only
    STATUS          optional
    DESCRIPTION     
            "HP SAL Revision"
    ::= { cpqSeCellEntry 5 }

cpqSeCellSysFwVersion OBJECT-TYPE
    SYNTAX          DisplayString (SIZE(0..255))
    ACCESS          read-only
    STATUS          optional
    DESCRIPTION     
            "This is the revision of system firmware on the cell board"
    ::= { cpqSeCellEntry 6 }

cpqSeCellBootInhibited OBJECT-TYPE
    SYNTAX          TruthValue
    ACCESS          read-only
    STATUS          optional
    DESCRIPTION     
            "This value indicates whether the cell is active."
    ::= { cpqSeCellEntry 7 }

cpqSeCellToScanBusConnectionStatus OBJECT-TYPE
    SYNTAX          INTEGER
    ACCESS          read-only
    STATUS          optional
    DESCRIPTION     
            "This bitmap represents the state of cell to scan 
             bus connection/RIO cable state.
             
             if bit 6 is set to 1, Cable port swapped.
             if bit 5 is set to 1, Cable ID mismatched.
             if bit 4 is set to 1, Output Cable parity error.
             if bit 3 is set to 1, Output Cable detached.
             if bit 2 is set to 1, Input Cable parity error.
             if bit 1 is set to 1, Input Cable detached.
             if bit 0 is set to 1, Connection valid."
    ::= { cpqSeCellEntry 8 }

cpqSeCellHasCoreIO OBJECT-TYPE
    SYNTAX          TruthValue
    ACCESS          read-only
    STATUS          optional
    DESCRIPTION     
            "This value indicates whether the cell has core I/O attached to it."
    ::= { cpqSeCellEntry 9 }

cpqSeCellBoardSpeed OBJECT-TYPE
    SYNTAX          INTEGER
    ACCESS          read-only
    STATUS          optional
    DESCRIPTION     
            "This value represents the speed of the cell board/FSB ratio"
    ::= { cpqSeCellEntry 10 }

cpqSeCellPresent OBJECT-TYPE
    SYNTAX          TruthValue
    ACCESS          read-only
    STATUS          optional
    DESCRIPTION     
            "This value represents whether there is a cell in the slot"
    ::= { cpqSeCellEntry 11 }

cpqSeCellHasPower OBJECT-TYPE
    SYNTAX          TruthValue
    ACCESS          read-only
    STATUS          optional
    DESCRIPTION     
            "This value represents whether the cell has power"
    ::= { cpqSeCellEntry 12 }

cpqSeCellReadyForReconfig OBJECT-TYPE
    SYNTAX          TruthValue
    ACCESS          read-only
    STATUS          optional
    DESCRIPTION     
            "This value represents whether the cell is ready for reconfiguration"
    ::= { cpqSeCellEntry 13 }

cpqSeCellTotalMemory OBJECT-TYPE
    SYNTAX          INTEGER
    ACCESS          read-only
    STATUS          optional
    DESCRIPTION     
            "This value represents total memory in the cell"
    ::= { cpqSeCellEntry 14 }

cpqSeCellLEDState OBJECT-TYPE
    SYNTAX          INTEGER
    ACCESS          read-write
    STATUS          optional
    DESCRIPTION     
            "This value represents state of the cell LED.
             This is a bit-mapped value defined as follows.
             Bit 31..30 = 00, LED 3 is Off
                        = 01, LED 3 is On
                        = 10, LED 3 is Blinking
                        = 11, For LED 3 future use
             
             Bit 29..27 = 000, LED 3 is Red
                        = 001, LED 3 is Yellow
                        = 010, LED 3 is Green
                        = 011, LED 3 is Blue
                        = 100, For LED 3 future use
                        = 101, For LED 3 future use
                        = 110, For LED 3 future use
                        = 111, For LED 3 future use
             
             Bit 26..24 = 000, LED 3 indicates Power
                        = 001, LED 3 indicates Run
                        = 010, LED 3 indicates Attention
                        = 011, LED 3 indicates Fault
                        = 100, For LED 3 future use
                        = 101, For LED 3 future use
                        = 110, For LED 3 future use
                        = 111, For LED 3 future use
             
             Bit 23..22 = 00, LED 2 is Off
                        = 01, LED 2 is On
                        = 10, LED 2 is Blinking
                        = 11, For LED 2 future use
             
             Bit 21..19 = 000, LED 2 is Red
                        = 001, LED 2 is Yellow
                        = 010, LED 2 is Green
                        = 011, LED 2 is Blue
                        = 100, For LED 2 future use
                        = 101, For LED 2 future use
                        = 110, For LED 2 future use
                        = 111, For LED 2 future use
             
             Bit 18..16 = 000, LED 2 indicates Power
                        = 001, LED 2 indicates Run
                        = 010, LED 2 indicates Attention
                        = 011, LED 2 indicates Fault
                        = 100, For LED 2 future use
                        = 101, For LED 2 future use
                        = 110, For LED 2 future use
                        = 111, For LED 2 future use
             
             Bit 15..14 = 00, LED 1 is Off
                        = 01, LED 1 is On
                        = 10, LED 1 is Blinking
                        = 11, For LED 1 future use
             
             Bit 13..11 = 000, LED 1 is Red
                        = 001, LED 1 is Yellow
                        = 010, LED 1 is Green
                        = 011, LED 1 is Blue
                        = 100, For LED 1 future use
                        = 101, For LED 1 future use
                        = 110, For LED 1 future use
                        = 111, For LED 1 future use
             
             Bit 10..8  = 000, LED 1 indicates Power
                        = 001, LED 1 indicates Run
                        = 010, LED 1 indicates Attention
                        = 011, LED 1 indicates Fault
                        = 100, For LED 1 future use
                        = 101, For LED 1 future use
                        = 110, For LED 1 future use
                        = 111, For LED 1 future use
             
             Bit 7..6   = 00, LED 0 is Off
                        = 01, LED 0 is On
                        = 10, LED 0 is Blinking
                        = 11, For LED 0 future use
             
             Bit 5..3   = 000, LED 0 is Red
                        = 001, LED 0 is Yellow
                        = 010, LED 0 is Green
                        = 011, LED 0 is Blue
                        = 100, For LED 0 future use
                        = 101, For LED 0 future use
                        = 110, For LED 0 future use
                        = 111, For LED 0 future use
             
             Bit 2..0   = 000, LED 0 indicates Power
                        = 001, LED 0 indicates Run
                        = 010, LED 0 indicates Attention
                        = 011, LED 0 indicates Fault
                        = 100, For LED 0 future use
                        = 101, For LED 0 future use
                        = 110, For LED 0 future use
                        = 111, For LED 0 future use "
    ::= { cpqSeCellEntry 15 }

cpqSeCellState OBJECT-TYPE
    SYNTAX          INTEGER
    ACCESS          read-write
    STATUS          optional
    DESCRIPTION     
            "This value represents state of the cell"
    ::= { cpqSeCellEntry 16 }

cpqSeCellCLMRequestPercentage OBJECT-TYPE
    SYNTAX          INTEGER
    ACCESS          read-only
    STATUS          optional
    DESCRIPTION     
            "The requested percentage of CLM memory to be configured in the cell."
    ::= { cpqSeCellEntry 17 }

cpqSeCellCLMRequestSize OBJECT-TYPE
    SYNTAX          INTEGER
    ACCESS          read-only
    STATUS          optional
    DESCRIPTION     
            "The size of requested CLM memory in the cell in kilobytes."
    ::= { cpqSeCellEntry 18 }

cpqSeCellCLMAllocatedSize OBJECT-TYPE
    SYNTAX          INTEGER
    ACCESS          read-only
    STATUS          optional
    DESCRIPTION     
            "The size of allocated CLM memory in the cell in kilobytes."
    ::= { cpqSeCellEntry 19 }

cpqSeCellInterleaveAllocatedSize OBJECT-TYPE
    SYNTAX          INTEGER
    ACCESS          read-only
    STATUS          optional
    DESCRIPTION     
            "The size of allocated interleaved memory in the cell
             in kilobytes."
    ::= { cpqSeCellEntry 20 }

cpqSeCellHasInterleaveMem OBJECT-TYPE
    SYNTAX          INTEGER
    ACCESS          read-only
    STATUS          optional
    DESCRIPTION     
            "When set indicates that there is an interleaved memory
             configured in the cell."
    ::= { cpqSeCellEntry 21 }

cpqSeCellSerialNumber OBJECT-TYPE
    SYNTAX          DisplayString (SIZE(0..255))
    ACCESS          read-only
    STATUS          optional
    DESCRIPTION     
            "This is the cell board serial number."
    ::= { cpqSeCellEntry 22 }

cpqSeCellCLMCondition OBJECT-TYPE
    SYNTAX          INTEGER { unknown(1), ok(2), degraded(3), failed(4) }
    ACCESS          read-only
    STATUS          optional
    DESCRIPTION     
            "The CLM (Cell Local Memory) settings condition of this cell."
    ::= { cpqSeCellEntry 23 }

cpqSeIOC OBJECT IDENTIFIER
    ::= { cpqSeComponent 17 }

cpqSeIOCTable OBJECT-TYPE
    SYNTAX          SEQUENCE OF CpqSeIOCEntry
    ACCESS          not-accessible
    STATUS          optional
    DESCRIPTION     
            "A list of I/O chassis in the partition."
    ::= { cpqSeIOC 1 }

cpqSeIOCEntry OBJECT-TYPE
    SYNTAX          CpqSeIOCEntry
    ACCESS          not-accessible
    STATUS          optional
    DESCRIPTION     
            "A description of an I/O chassis in the system."
    INDEX           { cpqSeIOCUnitIndex }
    ::= { cpqSeIOCTable 1 }

CpqSeIOCEntry ::=
    SEQUENCE {
        cpqSeIOCUnitIndex               INTEGER,
        cpqSeIOCCabinetNumber           INTEGER,
        cpqSeIOCBayNumber               INTEGER,
        cpqSeIOCIOCNumber               INTEGER,
        cpqSeIOCPowerState              INTEGER,
        cpqSeIOCLEDState                INTEGER
    }

cpqSeIOCUnitIndex OBJECT-TYPE
    SYNTAX          INTEGER (0..19)
    ACCESS          read-only
    STATUS          optional
    DESCRIPTION     
            "This is a number that uniquely specifies the I/O chassis."
    ::= { cpqSeIOCEntry 1 }

cpqSeIOCCabinetNumber OBJECT-TYPE
    SYNTAX          INTEGER (0..255)
    ACCESS          read-only
    STATUS          optional
    DESCRIPTION     
            "This value represents the cabinet that the I/O chassis belongs to.
             The default value is 255 if the cabinet number can not be obtained."
    ::= { cpqSeIOCEntry 2 }

cpqSeIOCBayNumber OBJECT-TYPE
    SYNTAX          INTEGER (0..2)
    ACCESS          read-only
    STATUS          optional
    DESCRIPTION     
            "This value indicates the bay in the cabinet where the I/O chassis resides."
    ::= { cpqSeIOCEntry 3 }

cpqSeIOCIOCNumber OBJECT-TYPE
    SYNTAX          INTEGER (0..1)
    ACCESS          read-only
    STATUS          optional
    DESCRIPTION     
            "This is the I/O chassis number that is unique across the bay."
    ::= { cpqSeIOCEntry 4 }

cpqSeIOCPowerState OBJECT-TYPE
    SYNTAX          INTEGER { unknown(1), powered-off(2), powered-on(3) }
    ACCESS          read-only
    STATUS          optional
    DESCRIPTION     
            "This value indicates I/O chassis power state."
    ::= { cpqSeIOCEntry 5 }

cpqSeIOCLEDState OBJECT-TYPE
    SYNTAX          INTEGER
    ACCESS          read-write
    STATUS          optional
    DESCRIPTION     
            "This value represents the state of a IO Chassis LED.
             This is a bit-mapped value defined as follows.
             Bit 31..30 = 00, LED 3 is Off
                        = 01, LED 3 is On
                        = 10, LED 3 is Blinking
                        = 11, For LED 3 future use
             
             Bit 29..27 = 000, LED 3 is Red
                        = 001, LED 3 is Yellow
                        = 010, LED 3 is Green
                        = 011, LED 3 is Blue
                        = 100, For LED 3 future use
                        = 101, For LED 3 future use
                        = 110, For LED 3 future use
                        = 111, For LED 3 future use
             
             Bit 26..24 = 000, LED 3 indicates Power
                        = 001, LED 3 indicates Run
                        = 010, LED 3 indicates Attention
                        = 011, LED 3 indicates Fault
                        = 100, For LED 3 future use
                        = 101, For LED 3 future use
                        = 110, For LED 3 future use
                        = 111, For LED 3 future use
             
             Bit 23..22 = 00, LED 2 is Off
                        = 01, LED 2 is On
                        = 10, LED 2 is Blinking
                        = 11, For LED 2 future use
             
             Bit 21..19 = 000, LED 2 is Red
                        = 001, LED 2 is Yellow
                        = 010, LED 2 is Green
                        = 011, LED 2 is Blue
                        = 100, For LED 2 future use
                        = 101, For LED 2 future use
                        = 110, For LED 2 future use
                        = 111, For LED 2 future use
             
             Bit 18..16 = 000, LED 2 indicates Power
                        = 001, LED 2 indicates Run
                        = 010, LED 2 indicates Attention
                        = 011, LED 2 indicates Fault
                        = 100, For LED 2 future use
                        = 101, For LED 2 future use
                        = 110, For LED 2 future use
                        = 111, For LED 2 future use
             
             Bit 15..14 = 00, LED 1 is Off
                        = 01, LED 1 is On
                        = 10, LED 1 is Blinking
                        = 11, For LED 1 future use
             
             Bit 13..11 = 000, LED 1 is Red
                        = 001, LED 1 is Yellow
                        = 010, LED 1 is Green
                        = 011, LED 1 is Blue
                        = 100, For LED 1 future use
                        = 101, For LED 1 future use
                        = 110, For LED 1 future use
                        = 111, For LED 1 future use
             
             Bit 10..8  = 000, LED 1 indicates Power
                        = 001, LED 1 indicates Run
                        = 010, LED 1 indicates Attention
                        = 011, LED 1 indicates Fault
                        = 100, For LED 1 future use
                        = 101, For LED 1 future use
                        = 110, For LED 1 future use
                        = 111, For LED 1 future use
             
             Bit 7..6   = 00, LED 0 is Off
                        = 01, LED 0 is On
                        = 10, LED 0 is Blinking
                        = 11, For LED 0 future use
             
             Bit 5..3   = 000, LED 0 is Red
                        = 001, LED 0 is Yellow
                        = 010, LED 0 is Green
                        = 011, LED 0 is Blue
                        = 100, For LED 0 future use
                        = 101, For LED 0 future use
                        = 110, For LED 0 future use
                        = 111, For LED 0 future use
             
             Bit 2..0   = 000, LED 0 indicates Power
                        = 001, LED 0 indicates Run
                        = 010, LED 0 indicates Attention
                        = 011, LED 0 indicates Fault
                        = 100, For LED 0 future use
                        = 101, For LED 0 future use
                        = 110, For LED 0 future use
                        = 111, For LED 0 future use "
    ::= { cpqSeIOCEntry 6 }

cpqSePartition OBJECT IDENTIFIER
    ::= { cpqSeComponent 18 }

cpqSePartitionTotalCPU OBJECT-TYPE
    SYNTAX          INTEGER
    ACCESS          read-only
    STATUS          optional
    DESCRIPTION     
            "This is the number of logical CPUs in the partition. Zero will be returned
             if the value can not be determined."
    ::= { cpqSePartition 1 }

cpqSePartitionAvailableCellSlots OBJECT-TYPE
    SYNTAX          INTEGER
    ACCESS          read-only
    STATUS          optional
    DESCRIPTION     
            "This is the number of available cell slots in the partition.
             Zero will be returned if the value can not be determined."
    ::= { cpqSePartition 2 }

cpqSePartitionInstalledCells OBJECT-TYPE
    SYNTAX          INTEGER
    ACCESS          read-only
    STATUS          optional
    DESCRIPTION     
            "This is the number of installed cells in the partition. Zero
             will be returned if the value can not be determined."
    ::= { cpqSePartition 3 }

cpqSePartitionPoweredOnCells OBJECT-TYPE
    SYNTAX          INTEGER
    ACCESS          read-only
    STATUS          optional
    DESCRIPTION     
            "This denotes the number of powered on cells in the partition.
             Zero will be returned if the value can not be determined."
    ::= { cpqSePartition 4 }

cpqSePartitionReadyForReconfigCells OBJECT-TYPE
    SYNTAX          INTEGER
    ACCESS          read-only
    STATUS          optional
    DESCRIPTION     
            "This represents the cells that are ready for reconfiguration.
             Zero will be returned if the value can not be determined."
    ::= { cpqSePartition 5 }

cpqSePartitionMemInterleavingType OBJECT-TYPE
    SYNTAX          INTEGER
    ACCESS          read-only
    STATUS          optional
    DESCRIPTION     
            "This represents memory interleaving type for the partition.
             Zero will be returned if the value can not be determined."
    ::= { cpqSePartition 6 }

cpqSePartitionName OBJECT-TYPE
    SYNTAX          DisplayString (SIZE(0..255))
    ACCESS          read-only
    STATUS          optional
    DESCRIPTION     
            "This represents the partition name."
    ::= { cpqSePartition 7 }

cpqSePartitionCoreCell OBJECT-TYPE
    SYNTAX          INTEGER
    ACCESS          read-only
    STATUS          optional
    DESCRIPTION     
            "The cell slot number of the partition's core cell."
    ::= { cpqSePartition 8 }

cpqSePartitionCoreCellCabinet OBJECT-TYPE
    SYNTAX          INTEGER
    ACCESS          read-only
    STATUS          optional
    DESCRIPTION     
            "The cabinet number of the partition's core cell."
    ::= { cpqSePartition 9 }

cpqSePartitionCLMRequestPercentage OBJECT-TYPE
    SYNTAX          INTEGER
    ACCESS          read-only
    STATUS          optional
    DESCRIPTION     
            "The requested percentage of CLM memory to be configured in the
             partition."
    ::= { cpqSePartition 10 }

cpqSePartitionCLMRequestSize OBJECT-TYPE
    SYNTAX          INTEGER
    ACCESS          read-only
    STATUS          optional
    DESCRIPTION     
            "The size of requested CLM memory in the partition in kilobytes."
    ::= { cpqSePartition 11 }

cpqSePartitionCLMAllocatedSize OBJECT-TYPE
    SYNTAX          INTEGER
    ACCESS          read-only
    STATUS          optional
    DESCRIPTION     
            "The size of allocated CLM memory in the partition in
             kilobytes."
    ::= { cpqSePartition 12 }

cpqSePartitionInterleaveAllocatedSize OBJECT-TYPE
    SYNTAX          INTEGER
    ACCESS          read-only
    STATUS          optional
    DESCRIPTION     
            "The size of allocated interleaved memory in the partition
             in kilobytes."
    ::= { cpqSePartition 13 }

cpqSePartitionHasInterleaveMem OBJECT-TYPE
    SYNTAX          INTEGER
    ACCESS          read-only
    STATUS          optional
    DESCRIPTION     
            "When set, it indicates that there is an interleaved memory
             configured in the partition."
    ::= { cpqSePartition 14 }

cpqSePartitionNumber OBJECT-TYPE
    SYNTAX          INTEGER
    ACCESS          read-only
    STATUS          optional
    DESCRIPTION     
            "This represents the logical partition number of the current
             partition in the complex."
    ::= { cpqSePartition 15 }

cpqSeCabinet OBJECT IDENTIFIER
    ::= { cpqSeComponent 19 }

cpqSeCabinetTable OBJECT-TYPE
    SYNTAX          SEQUENCE OF CpqSeCabinetEntry
    ACCESS          not-accessible
    STATUS          optional
    DESCRIPTION     
            "A list of cabinets that contain cells in the partition."
    ::= { cpqSeCabinet 1 }

cpqSeCabinetEntry OBJECT-TYPE
    SYNTAX          CpqSeCabinetEntry
    ACCESS          not-accessible
    STATUS          optional
    DESCRIPTION     
            "A description of a cabinet in the system."
    INDEX           { cpqSeCabinetUnitIndex }
    ::= { cpqSeCabinetTable 1 }

CpqSeCabinetEntry ::=
    SEQUENCE {
        cpqSeCabinetUnitIndex           INTEGER,
        cpqSeCabinetCPULED              TruthValue,
        cpqSeCabinetIOXLED              TruthValue,
        cpqSeCabinetTypeNum             INTEGER,
        cpqSeCabinetLED                 INTEGER
    }

cpqSeCabinetUnitIndex OBJECT-TYPE
    SYNTAX          INTEGER (0..3)
    ACCESS          read-only
    STATUS          optional
    DESCRIPTION     
            "This is a number that uniquely specifies the cabinet."
    ::= { cpqSeCabinetEntry 1 }

cpqSeCabinetCPULED OBJECT-TYPE
    SYNTAX          TruthValue
    ACCESS          read-only
    STATUS          optional
    DESCRIPTION     
            "This value represents the on/off state of compute cabinet LED."
    ::= { cpqSeCabinetEntry 2 }

cpqSeCabinetIOXLED OBJECT-TYPE
    SYNTAX          TruthValue
    ACCESS          read-only
    STATUS          optional
    DESCRIPTION     
            "This value represents the on/off state of IOX cabinet LED."
    ::= { cpqSeCabinetEntry 3 }

cpqSeCabinetTypeNum OBJECT-TYPE
    SYNTAX          INTEGER
    ACCESS          read-only
    STATUS          optional
    DESCRIPTION     
            "This value represents type and number of a compute or IOX cabinet.
             Bit 31..16 = 0x0000, type of cabinet is Thin Boy
             Bit 31..16 = 0x0001, type of cabinet is Fat Boy
             Bit 31..16 = 0x0002, type of cabinet is Dome Lite
             Bit 31..16 = 0x0003, type of cabinet is Key Stone
             Bit 31..16 = 0x0004, type of cabinet is Matter Horn
             Bit 31..16 = 0x0080, type of cabinet is IOX
             Bit 15..0, represents the compute cabinet number."
    ::= { cpqSeCabinetEntry 4 }

cpqSeCabinetLED OBJECT-TYPE
    SYNTAX          INTEGER
    ACCESS          read-write
    STATUS          optional
    DESCRIPTION     
            "This value represents the state of a cabinet LED.
             This is a bit-mapped value defined as follows.
             Bit 31..30 = 00, LED 3 is Off
                        = 01, LED 3 is On
                        = 10, LED 3 is Blinking
                        = 11, For LED 3 future use
             
             Bit 29..27 = 000, LED 3 is Red
                        = 001, LED 3 is Yellow
                        = 010, LED 3 is Green
                        = 011, LED 3 is Blue
                        = 100, For LED 3 future use
                        = 101, For LED 3 future use
                        = 110, For LED 3 future use
                        = 111, For LED 3 future use
             
             Bit 26..24 = 000, LED 3 indicates Power
                        = 001, LED 3 indicates Run
                        = 010, LED 3 indicates Attention
                        = 011, LED 3 indicates Fault
                        = 100, For LED 3 future use
                        = 101, For LED 3 future use
                        = 110, For LED 3 future use
                        = 111, For LED 3 future use
             
             Bit 23..22 = 00, LED 2 is Off
                        = 01, LED 2 is On
                        = 10, LED 2 is Blinking
                        = 11, For LED 2 future use
             
             Bit 21..19 = 000, LED 2 is Red
                        = 001, LED 2 is Yellow
                        = 010, LED 2 is Green
                        = 011, LED 2 is Blue
                        = 100, For LED 2 future use
                        = 101, For LED 2 future use
                        = 110, For LED 2 future use
                        = 111, For LED 2 future use
             
             Bit 18..16 = 000, LED 2 indicates Power
                        = 001, LED 2 indicates Run
                        = 010, LED 2 indicates Attention
                        = 011, LED 2 indicates Fault
                        = 100, For LED 2 future use
                        = 101, For LED 2 future use
                        = 110, For LED 2 future use
                        = 111, For LED 2 future use
             
             Bit 15..14 = 00, LED 1 is Off
                        = 01, LED 1 is On
                        = 10, LED 1 is Blinking
                        = 11, For LED 1 future use
             
             Bit 13..11 = 000, LED 1 is Red
                        = 001, LED 1 is Yellow
                        = 010, LED 1 is Green
                        = 011, LED 1 is Blue
                        = 100, For LED 1 future use
                        = 101, For LED 1 future use
                        = 110, For LED 1 future use
                        = 111, For LED 1 future use
             
             Bit 10..8  = 000, LED 1 indicates Power
                        = 001, LED 1 indicates Run
                        = 010, LED 1 indicates Attention
                        = 011, LED 1 indicates Fault
                        = 100, For LED 1 future use
                        = 101, For LED 1 future use
                        = 110, For LED 1 future use
                        = 111, For LED 1 future use
             
             Bit 7..6   = 00, LED 0 is Off
                        = 01, LED 0 is On
                        = 10, LED 0 is Blinking
                        = 11, For LED 0 future use
             
             Bit 5..3   = 000, LED 0 is Red
                        = 001, LED 0 is Yellow
                        = 010, LED 0 is Green
                        = 011, LED 0 is Blue
                        = 100, For LED 0 future use
                        = 101, For LED 0 future use
                        = 110, For LED 0 future use
                        = 111, For LED 0 future use
             
             Bit 2..0   = 000, LED 0 indicates Power
                        = 001, LED 0 indicates Run
                        = 010, LED 0 indicates Attention
                        = 011, LED 0 indicates Fault
                        = 100, For LED 0 future use
                        = 101, For LED 0 future use
                        = 110, For LED 0 future use
                        = 111, For LED 0 future use "
    ::= { cpqSeCabinetEntry 5 }

cpqSeComplex OBJECT IDENTIFIER
    ::= { cpqSeComponent 20 }

cpqSeComplexUUID OBJECT-TYPE
    SYNTAX          DisplayString (SIZE(0..255))
    ACCESS          read-only
    STATUS          optional
    DESCRIPTION     
            "This is the complex UUID."
    ::= { cpqSeComplex 1 }

cpqSeComplexTotalCabinet OBJECT-TYPE
    SYNTAX          INTEGER (0..4)
    ACCESS          read-only
    STATUS          optional
    DESCRIPTION     
            "This is the total number of cabinets in the complex.
             Zero will be returned if the value can not be determined."
    ::= { cpqSeComplex 2 }

cpqSeComplexComputeCabinet OBJECT-TYPE
    SYNTAX          INTEGER (0..2)
    ACCESS          read-only
    STATUS          optional
    DESCRIPTION     
            "This is the number of compute cabinets in the complex."
    ::= { cpqSeComplex 3 }

cpqSeComplexIOXCabinet OBJECT-TYPE
    SYNTAX          INTEGER (0..1)
    ACCESS          read-only
    STATUS          optional
    DESCRIPTION     
            "This denotes the number of IOX cabinets in the complex."
    ::= { cpqSeComplex 4 }

cpqSeComplexName OBJECT-TYPE
    SYNTAX          DisplayString (SIZE(0..255))
    ACCESS          read-only
    STATUS          optional
    DESCRIPTION     
            "This represents the complex name."
    ::= { cpqSeComplex 5 }

cpqSeComplexLockedProperty OBJECT-TYPE
    SYNTAX          INTEGER
    ACCESS          read-only
    STATUS          optional
    DESCRIPTION     
            "Bit 31 - Indicates that there is a locked IPMI property when set.
             Bit 7:0 - Contains the property number currently locked."
    ::= { cpqSeComplex 6 }

cpqSeComplexCellSlotStatusTable OBJECT-TYPE
    SYNTAX          SEQUENCE OF CpqSeComplexCellSlotStatusEntry
    ACCESS          not-accessible
    STATUS          optional
    DESCRIPTION     
            "A table of cell slot status in a complex."
    ::= { cpqSeComplex 7 }

cpqSeComplexCellSlotStatusEntry OBJECT-TYPE
    SYNTAX          CpqSeComplexCellSlotStatusEntry
    ACCESS          not-accessible
    STATUS          optional
    DESCRIPTION     
            "A cell slot status description."
    INDEX           { cpqSeComplexCellSlotStatusIndex }
    ::= { cpqSeComplexCellSlotStatusTable 1 }

CpqSeComplexCellSlotStatusEntry ::=
    SEQUENCE {
        cpqSeComplexCellSlotStatusIndex INTEGER,
        cpqSeComplexCellSlotStatusCabinetNo   INTEGER,
        cpqSeComplexCellSlotStatusSlotNo INTEGER,
        cpqSeComplexCellSlotStatus      INTEGER,
        cpqSeComplexCellSlotPartitionNo INTEGER,
        cpqSeComplexCellSlotPartitionName DisplayString
    }

cpqSeComplexCellSlotStatusIndex OBJECT-TYPE
    SYNTAX          INTEGER
    ACCESS          read-only
    STATUS          optional
    DESCRIPTION     
            "The table index of cell slot status in a complex.
             
             This value is a unique index for a row in the table of complex
             cell slot status."
    ::= { cpqSeComplexCellSlotStatusEntry 1 }

cpqSeComplexCellSlotStatusCabinetNo OBJECT-TYPE
    SYNTAX          INTEGER
    ACCESS          read-only
    STATUS          optional
    DESCRIPTION     
            "The cabinet number of this cell slot."
    ::= { cpqSeComplexCellSlotStatusEntry 2 }

cpqSeComplexCellSlotStatusSlotNo OBJECT-TYPE
    SYNTAX          INTEGER
    ACCESS          read-only
    STATUS          optional
    DESCRIPTION     
            "The number of this cell slot."
    ::= { cpqSeComplexCellSlotStatusEntry 3 }

cpqSeComplexCellSlotStatus OBJECT-TYPE
    SYNTAX          INTEGER { unknown(1), active(2), inactive(3), 
                        assigned-powered-off(4), free-powered-on(5), 
                        free-powered-off(6), empty(7) }
    ACCESS          read-only
    STATUS          optional
    DESCRIPTION     
            "The status of this cell slot."
    ::= { cpqSeComplexCellSlotStatusEntry 4 }

cpqSeComplexCellSlotPartitionNo OBJECT-TYPE
    SYNTAX          INTEGER
    ACCESS          read-only
    STATUS          optional
    DESCRIPTION     
            "The partition number this cell is assigned."
    ::= { cpqSeComplexCellSlotStatusEntry 5 }

cpqSeComplexCellSlotPartitionName OBJECT-TYPE
    SYNTAX          DisplayString (SIZE(0..255))
    ACCESS          read-only
    STATUS          optional
    DESCRIPTION     
            "The partition this cell belongs to."
    ::= { cpqSeComplexCellSlotStatusEntry 6 }

cpqSeLED OBJECT IDENTIFIER
    ::= { cpqSeComponent 21 }

cpqSeLEDTable OBJECT-TYPE
    SYNTAX          SEQUENCE OF CpqSeLEDEntry
    ACCESS          not-accessible
    STATUS          optional
    DESCRIPTION     
            "A list of LEDs in the system."
    ::= { cpqSeLED 1 }

cpqSeLEDEntry OBJECT-TYPE
    SYNTAX          CpqSeLEDEntry
    ACCESS          not-accessible
    STATUS          optional
    DESCRIPTION     
            "An entry of an LED in the system."
    INDEX           { cpqSeLEDIndex }
    ::= { cpqSeLEDTable 1 }

CpqSeLEDEntry ::=
    SEQUENCE {
        cpqSeLEDIndex                   INTEGER,
        cpqSeLEDState                   INTEGER,
        cpqSeLEDStateDuration           INTEGER,
        cpqSeLEDLocationType            INTEGER,
        cpqSeLEDDescription             DisplayString,
        cpqSeLEDHardwareLocation        DisplayString
    }

cpqSeLEDIndex OBJECT-TYPE
    SYNTAX          INTEGER (0..65535)
    ACCESS          read-only
    STATUS          optional
    DESCRIPTION     
            "This is a number that uniquely identifies the LED."
    ::= { cpqSeLEDEntry 1 }

cpqSeLEDState OBJECT-TYPE
    SYNTAX          INTEGER
    ACCESS          read-write
    STATUS          optional
    DESCRIPTION     
            "This value represents the state of an LED.
             Bit 31..24 = ON-duration time in unit of 0.1 sec
             Bit 23..16 = OFF-duration time in unit of 0.1 sec
             Bit 15..8 = 0, LED state is OFF
                       = 1, LED state is ON
                       = 2, LED state is BLINKING
             Bit 7..0 = 0, invalid color value
                      = 1, LED color is Brown
                      = 2, LED color is Red
                      = 3, LED color is Orange
                      = 4, LED color is Yellow
                      = 5, LED color is Green
                      = 6, LED color is Blue
                      = 7, LED color is Violet
                      = 8, LED color is Gray
                      = 9, LED color is White "
    ::= { cpqSeLEDEntry 2 }

cpqSeLEDStateDuration OBJECT-TYPE
    SYNTAX          INTEGER
    ACCESS          read-write
    STATUS          optional
    DESCRIPTION     
            "This is the duration of an LED state in seconds. "
    ::= { cpqSeLEDEntry 3 }

cpqSeLEDLocationType OBJECT-TYPE
    SYNTAX          INTEGER
    ACCESS          read-only
    STATUS          optional
    DESCRIPTION     
            "This value indicates whether an LED is internal or external.
             0 = External
             1 = Internal "
    ::= { cpqSeLEDEntry 4 }

cpqSeLEDDescription OBJECT-TYPE
    SYNTAX          DisplayString (SIZE(0..255))
    ACCESS          read-only
    STATUS          optional
    DESCRIPTION     
            "Description of the LED entry."
    ::= { cpqSeLEDEntry 5 }

cpqSeLEDHardwareLocation OBJECT-TYPE
    SYNTAX          DisplayString (SIZE(0..255))
    ACCESS          read-only
    STATUS          optional
    DESCRIPTION     
            "Description of the location of an LED entry."
    ::= { cpqSeLEDEntry 6 }

cpqSeUSBDevice OBJECT IDENTIFIER
    ::= { cpqSeComponent 22 }

cpqSeUSBDeviceType OBJECT-TYPE
    SYNTAX          DisplayString (SIZE(0..255))
    ACCESS          read-only
    STATUS          optional
    DESCRIPTION     
            "Attached USB device type."
    ::= { cpqSeUSBDevice 1 }

cpqSeUSBDeviceName OBJECT-TYPE
    SYNTAX          DisplayString (SIZE(0..255))
    ACCESS          read-only
    STATUS          optional
    DESCRIPTION     
            "Attached USB device name."
    ::= { cpqSeUSBDevice 2 }

cpqSeCpuThresholdPassed TRAP-TYPE
    ENTERPRISE      compaq
    VARIABLES       { sysName, cpqHoTrapFlags, cpqSeCpuSlot, 
                      cpqSeCpuSocketNumber }
--     STATUS          mandatory
    DESCRIPTION     
            "This trap is sent when an internal CPU error threshold has been
             passed on a particular CPU causing it to go degraded. This trap
             will be sent when cpqSeCpuThreshPassed transitions from false to
             true."
    ::= 1001

cpqSePCCardThermalDegraded TRAP-TYPE
    ENTERPRISE      compaq
    VARIABLES       { sysName, cpqHoTrapFlags, cpqSePCCardDeviceInfo, 
                      cpqSePCCardProductInfo, cpqSePCCardSlotIndex }
--     STATUS          mandatory
    DESCRIPTION     
            "This trap is sent when the PC Card Slot Thermal Sensor threshold has been
             exceeded for safe operations thereby causing degraded operations. This trap
             will be sent when cpqSePCCardStatus transitions from Normal (1) to Thermal
             Degraded (2).
             The manufacturer and product information strings as well as the slot number
             for the degraded PC Card is provided as parameters for this trap."
    ::= 1002

cpqSePCCardThermalFailure TRAP-TYPE
    ENTERPRISE      compaq
    VARIABLES       { sysName, cpqHoTrapFlags, cpqSePCCardDeviceInfo, 
                      cpqSePCCardProductInfo, cpqSePCCardSlotIndex }
--     STATUS          mandatory
    DESCRIPTION     
            "This trap is sent when the PC Card Slot Thermal Sensor threshold has been
             exceeded for degraded operations thereby causing failed operations.
             This trap will be sent when cpqSePCCardStatus transitions from Thermal Degraded
             (2) to Thermal Failure (3).
             The manufacturer and product information strings as well as the slot number
             for the failed PC Card is provided as parameters for this trap."
    ::= 1003

cpqSePCCardThermalSafe TRAP-TYPE
    ENTERPRISE      compaq
    VARIABLES       { sysName, cpqHoTrapFlags, cpqSePCCardSlotIndex }
--     STATUS          mandatory
    DESCRIPTION     
            "This trap is sent when the PC Card Slot Thermal Sensor threshold has been
             crossed which restored the thermal status to normal operations. This trap will be sent
             when cpqSePCCardStatus transitions from Thermal Degraded (2) or Thermal Failure
             (3) to Normal (1).
             The number of the recovered PC Card slot is provided as a parameter for this trap."
    ::= 1004

cpqSe2CpuThresholdPassed TRAP-TYPE
    ENTERPRISE      compaq
    VARIABLES       { sysName, cpqHoTrapFlags, cpqSeCpuSlot, 
                      cpqSeCpuSocketNumber, cpqSeCpuSpeed, 
                      cpqSeCpuExtSpeed, cpqSeCpuCacheSize }
--     STATUS          mandatory
    DESCRIPTION     
            "This trap is sent when an internal CPU error threshold has been
             passed on a particular CPU causing it to go degraded. This trap
             will be sent when cpqSeCpuThreshPassed transitions from false to
             true."
    ::= 1005

cpqSeCpuStatusChange TRAP-TYPE
    ENTERPRISE      compaq
    VARIABLES       { sysName, cpqHoTrapFlags, cpqSeCpuUnitIndex, 
                      cpqSeCpuSlot, cpqSeCpuName, cpqSeCpuSpeed, 
                      cpqSeCpuStep, cpqSeCpuStatus, cpqSeCpuExtSpeed, 
                      cpqSeCpuSocketNumber, cpqSeCpuHwLocation }
--     STATUS          mandatory
    DESCRIPTION     
            "This trap is sent when CPU status changed.
             
             CPU can be brought down to Stop state and removed
             from O.S Active set or Brought back to Running state
             and made member of O.S Active set.
             
             User Action: None."
    ::= 1006

cpqSeCpuPowerPodstatusChange TRAP-TYPE
    ENTERPRISE      compaq
    VARIABLES       { sysName, cpqHoTrapFlags, cpqSeCpuUnitIndex, 
                      cpqSeCpuSlot, cpqSeCpuName, cpqSeCpuSpeed, 
                      cpqSeCpuStep, cpqSeCpuPowerpodStatus, 
                      cpqSeCpuExtSpeed, cpqSeCpuSocketNumber, 
                      cpqSeCpuHwLocation }
--     STATUS          mandatory
    DESCRIPTION     
            "This Trap is sent if CPU Power Pod status changes.
             
             User Action: None."
    ::= 1007

cpqSeUSBStorageDeviceAttached TRAP-TYPE
    ENTERPRISE      compaq
    VARIABLES       { sysName, cpqHoTrapFlags, cpqSeUSBPortIndex, 
                      cpqSeUSBPortDeviceName }
--     STATUS          mandatory
    DESCRIPTION     
            "This trap is sent when a USB storage device has been attached "
    ::= 1008

cpqSeUSBStorageDeviceRemoved TRAP-TYPE
    ENTERPRISE      compaq
    VARIABLES       { sysName, cpqHoTrapFlags, cpqSeUSBPortIndex, 
                      cpqSeUSBPortDeviceName }
--     STATUS          mandatory
    DESCRIPTION     
            "This trap is sent when a attached USB storage device is removed "
    ::= 1009

END -- end of module CPQSTDEQ-MIB.
