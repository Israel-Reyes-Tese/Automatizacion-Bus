ZTE-NOTIFICATION-IRP-MIB DEFINITIONS ::= BEGIN

IMPORTS
        MODULE-IDENTITY, OBJECT-TYPE, NOTIFICATION-TYPE,
        enterprises, Integer32
                FROM SNMPv2-SMI
        TEXTUAL-CONVENTION, DisplayString, DateAndTime,RowStatus
                FROM SNMPv2-TC
        OBJECT-GROUP, NOTIFICATION-GROUP, MODULE-COMPLIANCE
                FROM SNMPv2-CONF
        alarm
                FROM ZTE-IRP-MIB  	
        sendNotificationId,lastSendNotificationId,systemDN,ManagedObjectInstance,ProbableCause
                FROM ZTE-ALARM-IRP-MIB;


notificationIRP                  OBJECT IDENTIFIER ::= { alarm 10 }
ntsAttribute                     OBJECT IDENTIFIER ::= { notificationIRP 1 }
ntsNotifications        		 OBJECT IDENTIFIER ::= { notificationIRP 2 }
ntsNotificationProfile  		 OBJECT IDENTIFIER ::= { ntsNotifications 1 }
ntsNotificationFilter            OBJECT IDENTIFIER ::= { notificationIRP 3 }

--======================================================================
-- NOTIFICATION ATTR
--======================================================================
notifyEventTime OBJECT-TYPE
        SYNTAX      DateAndTime
        MAX-ACCESS  accessible-for-notify
        STATUS      current
        DESCRIPTION 
                "This object represents the time of occurrence of the notification."
        ::= { ntsAttribute 1 }

notifyCode OBJECT-TYPE
        SYNTAX      DisplayString (SIZE (0..50))
        MAX-ACCESS  accessible-for-notify
        STATUS      current
        DESCRIPTION
                "This object represents an notification code"
        ::= { ntsAttribute 2 }
        
notifyManagedObjectInstance OBJECT-TYPE
        SYNTAX      ManagedObjectInstance
        MAX-ACCESS  accessible-for-notify
        STATUS      current
        DESCRIPTION
                "This object identifies the MO instance of network resource to which the notification is related."
        ::= { ntsAttribute 3 }
        
notifyProbableCause OBJECT-TYPE
        SYNTAX      ProbableCause
        MAX-ACCESS  accessible-for-notify
        STATUS      current
        DESCRIPTION
                "This object represents the probable cause of the current."
        ::= { ntsAttribute 4 }

notifySpecificProblem OBJECT-TYPE
        SYNTAX      DisplayString (SIZE (0..255))
        MAX-ACCESS  accessible-for-notify
        STATUS      current
        DESCRIPTION
                "This object represents the vendor specific problem."
        ::= { ntsAttribute 5 }

notifyAdditionalText OBJECT-TYPE
        SYNTAX      DisplayString (SIZE (0..255))
        MAX-ACCESS  accessible-for-notify
        STATUS      current
        DESCRIPTION
                "This object represents some arbitrary additional information of the notification."
        ::= { ntsAttribute 6 }

notifyNetype OBJECT-TYPE
        SYNTAX      DisplayString (SIZE (0..50))
        MAX-ACCESS  accessible-for-notify
        STATUS      current
        DESCRIPTION
                "This object represents an notification netype"
        ::= { ntsAttribute 7 }   
        
notifyCodeName OBJECT-TYPE
        SYNTAX      DisplayString (SIZE (0..255))
        MAX-ACCESS  accessible-for-notify
        STATUS      current
        DESCRIPTION
                "This object represents an notification code name"
        ::= { ntsAttribute 8 }   
        
notifyManagedObjectInstanceName OBJECT-TYPE
        SYNTAX      DisplayString (SIZE (0..255))
        MAX-ACCESS  accessible-for-notify
        STATUS      current
        DESCRIPTION
                "This object identifies the MO instance name of network resource to which the notification is related."
        ::= { ntsAttribute 9 }     

notifySystemType OBJECT-TYPE
        SYNTAX      DisplayString (SIZE (0..5))
        MAX-ACCESS  accessible-for-notify
        STATUS      current
        DESCRIPTION
                "This object represents systemtype."
        ::= { ntsAttribute 10 }
        
notifyNeIP OBJECT-TYPE
        SYNTAX      DisplayString (SIZE (0..60))
        MAX-ACCESS  accessible-for-notify
        STATUS      current
        DESCRIPTION
                "This object identifies the IP of network resource to which the notification is related."
        ::= { ntsAttribute 11 }  

notifyTimeZoneID OBJECT-TYPE
        SYNTAX      DisplayString (SIZE (0..50))
        MAX-ACCESS  accessible-for-notify
        STATUS      current
        DESCRIPTION
                "This object represents the NE's TimeZoneID. "
        ::= { ntsAttribute 12 }

notifyTimeZoneOffset OBJECT-TYPE
        SYNTAX      Integer32
        MAX-ACCESS  accessible-for-notify
        STATUS      current
        DESCRIPTION
                "This object represents the NE's TimeZoneOffset. "
        ::= { ntsAttribute 13 }
                
notifyDSTSaving OBJECT-TYPE
        SYNTAX      Integer32
        MAX-ACCESS  accessible-for-notify
        STATUS      current
        DESCRIPTION
                "This object represents the NE's DSTSaving. "
        ::= { ntsAttribute 14 }  
        
notifyAid OBJECT-TYPE
        SYNTAX      DisplayString (SIZE (0..255))
        MAX-ACCESS  accessible-for-notify
        STATUS      current
        DESCRIPTION
                "This object represents an notification AID"
        ::= { ntsAttribute 15 }                          
        
notifyId OBJECT-TYPE
        SYNTAX      DisplayString (SIZE (0..50))
        MAX-ACCESS  accessible-for-notify
        STATUS      current
        DESCRIPTION
                "This object represents the number id of the notification. "
        ::= { ntsAttribute 16 }  
        
notifyMocObjectInstance OBJECT-TYPE
        SYNTAX      DisplayString (SIZE (0..255))
        MAX-ACCESS  accessible-for-notify
        STATUS      current
        DESCRIPTION
               "This object identifies the SUB MO instance of network resource to which the notification is related."
        ::= { ntsAttribute 17 }  

notifyCustomAttr1 OBJECT-TYPE
        SYNTAX      DisplayString
        MAX-ACCESS  accessible-for-notify
        STATUS      current
        DESCRIPTION
               "This object identifies the first custom attribute information of notification"
        ::= { ntsAttribute 18 } 
        
notifyCustomAttr2 OBJECT-TYPE
        SYNTAX      DisplayString
        MAX-ACCESS  accessible-for-notify
        STATUS      current
        DESCRIPTION
               "This object identifies the second custom attribute information of notification"
        ::= { ntsAttribute 19 }        
        
notifyCustomAttr3 OBJECT-TYPE
        SYNTAX      DisplayString
        MAX-ACCESS  accessible-for-notify
        STATUS      current
        DESCRIPTION
               "This object identifies the third custom attribute information of notification"
        ::= { ntsAttribute 20 }     
        
notifyCustomAttr4 OBJECT-TYPE
        SYNTAX      DisplayString
        MAX-ACCESS  accessible-for-notify
        STATUS      current
        DESCRIPTION
               "This object identifies the fourth custom attribute information of notification"
        ::= { ntsAttribute 21 }   
        
notifyCustomAttr5 OBJECT-TYPE
        SYNTAX      DisplayString
        MAX-ACCESS  accessible-for-notify
        STATUS      current
        DESCRIPTION
               "This object identifies the fifth custom attribute information of notification"
        ::= { ntsAttribute 22 }
        
notifyCustomAttr6 OBJECT-TYPE
        SYNTAX      DisplayString
        MAX-ACCESS  accessible-for-notify
        STATUS      current
        DESCRIPTION
               "This object identifies the sixth custom attribute information of notification"
        ::= { ntsAttribute 23 }
        
notifyCustomAttr7 OBJECT-TYPE
        SYNTAX      DisplayString
        MAX-ACCESS  accessible-for-notify
        STATUS      current
        DESCRIPTION
               "This object identifies the seventh custom attribute information of notification"
        ::= { ntsAttribute 24 }     
        
notifyCustomAttr8 OBJECT-TYPE
        SYNTAX      DisplayString
        MAX-ACCESS  accessible-for-notify
        STATUS      current
        DESCRIPTION
               "This object identifies the eighth custom attribute information of notification"
        ::= { ntsAttribute 25 } 
        
notifyCustomAttr9 OBJECT-TYPE
        SYNTAX      DisplayString
        MAX-ACCESS  accessible-for-notify
        STATUS      current
        DESCRIPTION
               "This object identifies the ninth custom attribute information of notification"
        ::= { ntsAttribute 26 } 
        
notifyCustomAttr10 OBJECT-TYPE
        SYNTAX      DisplayString
        MAX-ACCESS  accessible-for-notify
        STATUS      current
        DESCRIPTION
               "This object identifies the tenth custom attribute information of notification"
        ::= { ntsAttribute 27 }                                         
--======================================================================
-- ALARM FILTER
--======================================================================
ntsNotificationFilterEnable OBJECT-TYPE
        SYNTAX      Integer32
        MAX-ACCESS  read-write
        STATUS      current
        DESCRIPTION
                "Notification Filter enable or false,0 means false,while 1 means true."
        ::= { ntsNotificationFilter 1 }
        
ntsNotificationFilterCondition  OBJECT IDENTIFIER ::= { ntsNotificationFilter 2}
--======================================================================
-- NOTIFICATION FILTER
--======================================================================                                           
ntsNotificationCodesIncludeFilter OBJECT-TYPE
        SYNTAX     OCTET STRING (SIZE (0..512))
        MAX-ACCESS  read-write
        STATUS      current
        DESCRIPTION
                "This object filters notification according to the system type and notification code.  uses ',' as splitter between alarm codes .for example: 10001,10002 means :The alarm of specifical  system type code of 10001 and 10002 will not be sent. "                 
        ::= { ntsNotificationFilterCondition 1 }  
                  
--======================================================================
-- NOTIFICATION RELATED NOTIFICATIONS
--======================================================================

ntsNotificationNew NOTIFICATION-TYPE
        OBJECTS {   notifyEventTime,
                    sendNotificationId,
                    lastSendNotificationId,
                    systemDN,
		      		notifyCode,
		      		notifyManagedObjectInstance,                
                    notifyProbableCause,
                    notifySpecificProblem,
                    notifyAdditionalText,
		      		notifyNetype,
                    notifyCodeName,
                    notifyManagedObjectInstanceName,
                    notifySystemType,
                    notifyNeIP,
		      		      notifyTimeZoneID,
                    notifyTimeZoneOffset,
                    notifyDSTSaving,
                    notifyAid,
                    notifyId,
                    notifyMocObjectInstance,
				    notifyCustomAttr1,                 
				    notifyCustomAttr2,                 
				    notifyCustomAttr3,                 
				    notifyCustomAttr4,                 
				    notifyCustomAttr5,                 
				    notifyCustomAttr6,                 
				    notifyCustomAttr7,                 
				    notifyCustomAttr8,                 
				    notifyCustomAttr9,                 
	                notifyCustomAttr10 
                     }
        STATUS      current
        DESCRIPTION 
                "This notification is sent when a new notification is generated."
        ::= { ntsNotificationProfile 1 }

END
