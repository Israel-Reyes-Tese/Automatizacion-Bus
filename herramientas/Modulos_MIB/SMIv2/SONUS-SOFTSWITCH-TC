--
-- This SMIv2 module has been generated by smidump 0.2-cvs. Do not edit.
--

SONUS-SOFTSWITCH-TC DEFINITIONS ::= BEGIN

IMPORTS
    MODULE-IDENTITY
        FROM SNMPv2-SMI
    TEXTUAL-CONVENTION
        FROM SNMPv2-TC
    sonusModules
        FROM SONUS-SMI;

sonusSoftSwitchTextualConventions MODULE-IDENTITY
    LAST-UPDATED    "200004230000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "This module defines textual conventions used througout Sonus
             SoftSwitch MIBs."
    ::= { sonusModules 2 }


SonusSoftSwitchDbOperationFailureReason ::= TEXTUAL-CONVENTION
    STATUS          current
    DESCRIPTION     
            "DB operation failure reason."
    SYNTAX          INTEGER { connection(1), update(2) }

SonusSoftSwitchEntityId ::= TEXTUAL-CONVENTION
    STATUS          current
    DESCRIPTION     
            "An INTEGER representing the entity identifiers for
             software entities in a SoftSwitch."
    SYNTAX          INTEGER { pes(1), scpa(2) }

SonusTMIdentifier ::= TEXTUAL-CONVENTION
    DISPLAY-HINT    "31a"
    STATUS          current
    DESCRIPTION     
            "Identifies the control."
    SYNTAX          OCTET STRING (SIZE(0..31))

SonusCriteriaFormat ::= TEXTUAL-CONVENTION
    STATUS          current
    DESCRIPTION     
            "The format of the criteria identifier"
    SYNTAX          INTEGER { calledAddressAndService(1), 
                        calledAddress(2), callingAddressAndService(3), 
                        service(4) }

SonusSoftSwitchTransportType ::= TEXTUAL-CONVENTION
    STATUS          current
    DESCRIPTION     
            "Specifies the transport type used for traffic"
    SYNTAX          INTEGER { tcp(1), udp(2), sctp(3) }

SonusSoftSwitchDomainNameLength ::= TEXTUAL-CONVENTION
    STATUS          current
    DESCRIPTION     
            "Indicates the Domain Name length."
    SYNTAX          Integer32 (0..2147483647)

SonusSoftSwitchDomainName ::= TEXTUAL-CONVENTION
    STATUS          current
    DESCRIPTION     
            "Indicates the Domain Name value."
    SYNTAX          OCTET STRING (SIZE(0..255))

END -- end of module SONUS-SOFTSWITCH-TC.
