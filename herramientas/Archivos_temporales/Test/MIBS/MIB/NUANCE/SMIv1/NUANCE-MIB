--
-- This SMIv1 module has been generated by smidump 0.2-cvs. Do not edit.
--

NUANCE-MIB DEFINITIONS ::= BEGIN

IMPORTS
    OBJECT-TYPE
        FROM RFC-1212
    TRAP-TYPE
        FROM RFC-1215
    enterprises
        FROM SNMPv2-SMI
    TruthValue
        FROM SNMPv2-TC;

nuanceMIB OBJECT IDENTIFIER
    ::= { enterprises 3621 }

-- nuanceMIB MODULE-IDENTITY
--     LAST-UPDATED    "197001010000Z"
--     ORGANIZATION    
--             "Nuance Communications"
--     CONTACT-INFO    
--             "Email:  support@nuance.com
--              Phone:  +1.650.847.0000
--              Postal: 1380 Willow Road
--                      Menlo Park, CA 94025"
--     DESCRIPTION     
--             "The MIB module for managing the Nuance system"
--     REVISION        "199912020000Z"
--     DESCRIPTION     
--             "The initial revision of the Nuance MIB module"
--     REVISION        "197001010000Z"
--     DESCRIPTION     
--             "Update for Nuance v8.0"
--     ::= { enterprises 3621 }


NTimeVal ::=
    OCTET STRING (SIZE(1 | 23))

-- NTimeVal ::= TEXTUAL-CONVENTION
--     STATUS          mandatory
--     DESCRIPTION     
--             "Represents a local time and date string.  The
--              special value '-' indicates an empty value."
--     SYNTAX          OCTET STRING (SIZE(1 | 23))

NString ::=
    OCTET STRING (SIZE(0..4096))

-- NString ::= TEXTUAL-CONVENTION
--     STATUS          mandatory
--     DESCRIPTION     
--             "Represents an arbitrary string."
--     SYNTAX          OCTET STRING (SIZE(0..4096))

watcherDaemonMib OBJECT IDENTIFIER
    ::= { nuanceMIB 100 }

wdControl OBJECT IDENTIFIER
    ::= { watcherDaemonMib 1 }

wdState OBJECT-TYPE
    SYNTAX          INTEGER { readyState(1), quiescingState(2), 
                        goQuiesce(100) }
    ACCESS          read-write
    STATUS          mandatory
    DESCRIPTION     
            "."
    ::= { wdControl 1 }

wdVpSet OBJECT IDENTIFIER
    ::= { watcherDaemonMib 2 }

vpSetControl OBJECT IDENTIFIER
    ::= { wdVpSet 1 }

startVpArgs OBJECT-TYPE
    SYNTAX          NString
    ACCESS          read-write
    STATUS          mandatory
    DESCRIPTION     
            "The full command line of the process to start,
             including the executable name.  The typical
             command line looks like:
             'recserver -package ${MY_PACKAGE}'
             In this case, the recserver executable will be
             found using the typical PATH search list.
             The command line may also include a watcher
             argument list of the form:
             '-wa <watcher_args> -pa <process_args>'
             In this case, the <watcher_args> are args to
             configure the way this process is managed, and
             <process_args> is the full command line of the
             process to start, including the executable name."
    ::= { vpSetControl 1 }

startVpState OBJECT-TYPE
    SYNTAX          INTEGER { nullState(1), doneState(2), goStart(100), 
                        goReset(200) }
    ACCESS          read-write
    STATUS          mandatory
    DESCRIPTION     
            "Control starting a virtual process.  The only valid
             set values are goStart and goReset.  Set to
             goStart to start a process (based on arguments
             supplied in startVpArgs).  After starting and
             the state is doneState, startVpStatus can be
             checked for the status of the start, and
             startVpVpid can be checked for the vpid of the
             process that was started.  Set to goReset to reset
             the startVpStatus and startVpVpid, and reset the
             state back to the nullState."
    ::= { vpSetControl 2 }

startVpStatus OBJECT-TYPE
    SYNTAX          NString
    ACCESS          read-only
    STATUS          mandatory
    DESCRIPTION     
            "The status of the last attempted start."
    ::= { vpSetControl 3 }

startVpVpid OBJECT-TYPE
    SYNTAX          Gauge
    ACCESS          read-only
    STATUS          mandatory
    DESCRIPTION     
            "The vpid of the last attempted start."
    ::= { vpSetControl 4 }

vpControl OBJECT IDENTIFIER
    ::= { wdVpSet 2 }

vpcCount OBJECT-TYPE
    SYNTAX          INTEGER
    ACCESS          read-only
    STATUS          mandatory
    DESCRIPTION     
            "The number of virtual processes running
             on this machine."
    ::= { vpControl 1 }

vpcList OBJECT-TYPE
    SYNTAX          NString
    ACCESS          read-only
    STATUS          mandatory
    DESCRIPTION     
            "A space delimited list of the vpids of the
             virtual processes running on this machine."
    ::= { vpControl 2 }

vpcTable OBJECT-TYPE
    SYNTAX          SEQUENCE OF VpcEntry
    ACCESS          not-accessible
    STATUS          mandatory
    DESCRIPTION     
            "Table of virtual process information."
    ::= { vpControl 3 }

vpcEntry OBJECT-TYPE
    SYNTAX          VpcEntry
    ACCESS          not-accessible
    STATUS          mandatory
    DESCRIPTION     
            "Information and control for a particular
             virtual process.  This table is indexed by vpceVpid
             (not consecutive), and the total number of conceptual
             rows in this table is vpcCount.  The vpids represented
             in this table are listed in vpcList."
    INDEX           { vpceVpid }
    ::= { vpcTable 1 }

VpcEntry ::=
    SEQUENCE {
        vpceVpid                        Gauge,
        vpceVpState                     INTEGER,
        vpceIsWatchable                 TruthValue,
        vpcePVpid                       Gauge,
        vpceAssignedTime                NTimeVal,
        vpceRestartOnFailure            TruthValue,
        vpceShutdownOnDaemonQuiesce     TruthValue,
        vpcePingTimeoutMs               INTEGER,
        vpcePingTimeoutDelayMs          INTEGER,
        vpceMaxMissedPings              INTEGER,
        vpceQuiesceTimeoutMs            INTEGER,
        vpceFailureQuiesceTimeoutMs     INTEGER,
        vpceProcessType                 NString,
        vpceArgc                        INTEGER,
        vpceArgv                        NString,
        vpceTotalStarts                 INTEGER,
        vpceStartedTime                 NTimeVal,
        vpcePid                         INTEGER,
        vpceWPid                        INTEGER,
        vpceConsecutivePingsMissed      INTEGER,
        vpceTotalPingsMissed            INTEGER,
        vpcePingedTime                  NTimeVal,
        vpceIsConnected                 TruthValue,
        vpceStreamRemotePort            Gauge,
        vpceRestartAttemptedTime        NTimeVal,
        vpceQuiesceAttemptedTime        NTimeVal,
        vpceQuiescedTime                NTimeVal,
        vpceKillAttemptedTime           NTimeVal,
        vpceDiedTime                    NTimeVal,
        vpceReleasedTime                NTimeVal
    }

vpceVpid OBJECT-TYPE
    SYNTAX          Gauge
    ACCESS          read-only
    STATUS          mandatory
    DESCRIPTION     
            "The virtual process id."
    ::= { vpcEntry 1 }

vpceVpState OBJECT-TYPE
    SYNTAX          INTEGER { nullState(1), startingState(2), 
                        connectingState(3), initializingState(4), 
                        readyState(5), dyingState(6), quiescingState(7), 
                        terminatingState(8), releasingState(9), 
                        goRestart(100), goQuiesce(101), goKill(102) }
    ACCESS          read-write
    STATUS          mandatory
    DESCRIPTION     
            "The virtual process state.  The only valid set values
             are goRestart, goQuiesce and goKill.  Set to one of
             these values to trigger the appropriate action.
             Check vpceRestartAttemptedTime, vpceQuiesceAttemptedTime
             or vpceKillAttemptedTime to make sure the action was
             attempted."
    ::= { vpcEntry 2 }

vpceIsWatchable OBJECT-TYPE
    SYNTAX          TruthValue
    ACCESS          read-only
    STATUS          mandatory
    DESCRIPTION     
            "Whether the virtual process is watchable."
    ::= { vpcEntry 3 }

vpcePVpid OBJECT-TYPE
    SYNTAX          Gauge
    ACCESS          read-only
    STATUS          mandatory
    DESCRIPTION     
            "The parent virtual process id."
    ::= { vpcEntry 4 }

vpceAssignedTime OBJECT-TYPE
    SYNTAX          NTimeVal
    ACCESS          read-only
    STATUS          mandatory
    DESCRIPTION     
            "The assigned time of the virtual process."
    ::= { vpcEntry 5 }

vpceRestartOnFailure OBJECT-TYPE
    SYNTAX          TruthValue
    ACCESS          read-only
    STATUS          mandatory
    DESCRIPTION     
            "Whether the virtual process will be automatically
             restarted on failure."
    ::= { vpcEntry 6 }

vpceShutdownOnDaemonQuiesce OBJECT-TYPE
    SYNTAX          TruthValue
    ACCESS          read-only
    STATUS          mandatory
    DESCRIPTION     
            "Whether the virtual process will be shutdown
             (quiesced or killed) when the WatcherDaemon quiesces."
    ::= { vpcEntry 7 }

vpcePingTimeoutMs OBJECT-TYPE
    SYNTAX          INTEGER
    ACCESS          read-only
    STATUS          mandatory
    DESCRIPTION     
            "The ping timeout in milliseconds."
    ::= { vpcEntry 8 }

vpcePingTimeoutDelayMs OBJECT-TYPE
    SYNTAX          INTEGER
    ACCESS          read-only
    STATUS          mandatory
    DESCRIPTION     
            "The ping timeout delay in milliseconds."
    ::= { vpcEntry 9 }

vpceMaxMissedPings OBJECT-TYPE
    SYNTAX          INTEGER
    ACCESS          read-only
    STATUS          mandatory
    DESCRIPTION     
            "The number of max missed pings."
    ::= { vpcEntry 10 }

vpceQuiesceTimeoutMs OBJECT-TYPE
    SYNTAX          INTEGER
    ACCESS          read-only
    STATUS          mandatory
    DESCRIPTION     
            "The quiesce timeout in milliseconds, or the time
             the WatcherDaemon will wait for a quiesce before
             the virtual process is automatically killed.  A
             value of 0 indicates the process will never be
             automatically killed."
    ::= { vpcEntry 11 }

vpceFailureQuiesceTimeoutMs OBJECT-TYPE
    SYNTAX          INTEGER
    ACCESS          read-only
    STATUS          mandatory
    DESCRIPTION     
            "The failure quiesce timeout in milliseconds, or the
             time the WatcherDaemon will wait for a quiesce before
             the virtual process is automatically killed, when the
             quiesce is triggered by a virtual process failure."
    ::= { vpcEntry 12 }

vpceProcessType OBJECT-TYPE
    SYNTAX          NString
    ACCESS          read-only
    STATUS          mandatory
    DESCRIPTION     
            "The process type of this virtual process."
    ::= { vpcEntry 13 }

vpceArgc OBJECT-TYPE
    SYNTAX          INTEGER
    ACCESS          read-only
    STATUS          mandatory
    DESCRIPTION     
            "The number of arguments of this virtual process."
    ::= { vpcEntry 14 }

vpceArgv OBJECT-TYPE
    SYNTAX          NString
    ACCESS          read-only
    STATUS          mandatory
    DESCRIPTION     
            "The arguments of this virtual process."
    ::= { vpcEntry 15 }

vpceTotalStarts OBJECT-TYPE
    SYNTAX          INTEGER
    ACCESS          read-only
    STATUS          mandatory
    DESCRIPTION     
            "The total number of starts for this virtual process."
    ::= { vpcEntry 16 }

vpceStartedTime OBJECT-TYPE
    SYNTAX          NTimeVal
    ACCESS          read-only
    STATUS          mandatory
    DESCRIPTION     
            "The started time of the virtual process."
    ::= { vpcEntry 17 }

vpcePid OBJECT-TYPE
    SYNTAX          INTEGER
    ACCESS          read-only
    STATUS          mandatory
    DESCRIPTION     
            "The operating system pid (process id)."
    ::= { vpcEntry 18 }

vpceWPid OBJECT-TYPE
    SYNTAX          INTEGER
    ACCESS          read-only
    STATUS          mandatory
    DESCRIPTION     
            "The watcher pid (process id)."
    ::= { vpcEntry 19 }

vpceConsecutivePingsMissed OBJECT-TYPE
    SYNTAX          INTEGER
    ACCESS          read-only
    STATUS          mandatory
    DESCRIPTION     
            "The number of consecutive pings that have been missed."
    ::= { vpcEntry 20 }

vpceTotalPingsMissed OBJECT-TYPE
    SYNTAX          INTEGER
    ACCESS          read-only
    STATUS          mandatory
    DESCRIPTION     
            "The total number of pings that have been missed."
    ::= { vpcEntry 21 }

vpcePingedTime OBJECT-TYPE
    SYNTAX          NTimeVal
    ACCESS          read-only
    STATUS          mandatory
    DESCRIPTION     
            "The pinged time of the virtual process."
    ::= { vpcEntry 22 }

vpceIsConnected OBJECT-TYPE
    SYNTAX          TruthValue
    ACCESS          read-only
    STATUS          mandatory
    DESCRIPTION     
            "Whether the virtual process is connected."
    ::= { vpcEntry 23 }

vpceStreamRemotePort OBJECT-TYPE
    SYNTAX          Gauge
    ACCESS          read-only
    STATUS          mandatory
    DESCRIPTION     
            "The remote TCP stream port."
    ::= { vpcEntry 24 }

vpceRestartAttemptedTime OBJECT-TYPE
    SYNTAX          NTimeVal
    ACCESS          read-only
    STATUS          mandatory
    DESCRIPTION     
            "The restart attempted time of the virtual process."
    ::= { vpcEntry 25 }

vpceQuiesceAttemptedTime OBJECT-TYPE
    SYNTAX          NTimeVal
    ACCESS          read-only
    STATUS          mandatory
    DESCRIPTION     
            "The quiesce attempted time of the virtual process."
    ::= { vpcEntry 26 }

vpceQuiescedTime OBJECT-TYPE
    SYNTAX          NTimeVal
    ACCESS          read-only
    STATUS          mandatory
    DESCRIPTION     
            "The quiesced time of the virtual process."
    ::= { vpcEntry 27 }

vpceKillAttemptedTime OBJECT-TYPE
    SYNTAX          NTimeVal
    ACCESS          read-only
    STATUS          mandatory
    DESCRIPTION     
            "The kill attempted time of the virtual process."
    ::= { vpcEntry 28 }

vpceDiedTime OBJECT-TYPE
    SYNTAX          NTimeVal
    ACCESS          read-only
    STATUS          mandatory
    DESCRIPTION     
            "The died time of the virtual process."
    ::= { vpcEntry 29 }

vpceReleasedTime OBJECT-TYPE
    SYNTAX          NTimeVal
    ACCESS          read-only
    STATUS          mandatory
    DESCRIPTION     
            "The released time of the virtual process."
    ::= { vpcEntry 30 }

vprInfo OBJECT IDENTIFIER
    ::= { wdVpSet 3 }

vpriCount OBJECT-TYPE
    SYNTAX          INTEGER
    ACCESS          not-accessible
    STATUS          mandatory
    DESCRIPTION     
            "The number of released virtual processes."
    ::= { vprInfo 1 }

vpriList OBJECT-TYPE
    SYNTAX          NString
    ACCESS          not-accessible
    STATUS          mandatory
    DESCRIPTION     
            "A space delimited list of the vpids of the
             released virtual processes."
    ::= { vprInfo 2 }

wvpDefaultParams OBJECT IDENTIFIER
    ::= { wdVpSet 4 }

wvpdpCount OBJECT-TYPE
    SYNTAX          INTEGER
    ACCESS          read-only
    STATUS          mandatory
    DESCRIPTION     
            "The number of watchable virtual processes running
             on this machine."
    ::= { wvpDefaultParams 1 }

wvpdpList OBJECT-TYPE
    SYNTAX          NString
    ACCESS          read-only
    STATUS          mandatory
    DESCRIPTION     
            "A space delimited list of the vpids of the watchable
             virtual processes running on this machine."
    ::= { wvpDefaultParams 2 }

wvpdpTable OBJECT-TYPE
    SYNTAX          SEQUENCE OF WvpdpEntry
    ACCESS          not-accessible
    STATUS          mandatory
    DESCRIPTION     
            "Table of watchable virtual process default parameters."
    ::= { wvpDefaultParams 3 }

wvpdpEntry OBJECT-TYPE
    SYNTAX          WvpdpEntry
    ACCESS          not-accessible
    STATUS          mandatory
    DESCRIPTION     
            "Default parameters for a particular watchable
             virtual process.  This table is indexed by
             wvpdpeProcessVpid (not consecutive), and the
              total number of conceptual rows in this table
              is wvpdpCount.  The vpids represented in this
              table are listed in wvpdpList."
    INDEX           { wvpdpeProcessVpid }
    ::= { wvpdpTable 1 }

WvpdpEntry ::=
    SEQUENCE {
        wvpdpeProcessVpid               Gauge,
        wvpdpeProcessBuildEnv           NString,
        wvpdpeProcessBuildName          NString,
        wvpdpeProcessBuildTime          NString,
        wvpdpeProcessCpuBusyPercentage  INTEGER,
        wvpdpeProcessCpuBusySecs        INTEGER,
        wvpdpeProcessCpuTotalSecs       INTEGER,
        wvpdpeProcessCwd                NString,
        wvpdpeProcessLoggingLevel       NString,
        wvpdpeProcessKBytes             INTEGER,
        wvpdpeProcessStartTime          NString,
        wvpdpeProcessVersionName        NString,
        wvpdpeProcessVersionNum         INTEGER
    }

wvpdpeProcessVpid OBJECT-TYPE
    SYNTAX          Gauge
    ACCESS          read-only
    STATUS          mandatory
    DESCRIPTION     
            "The process virtual process id."
    ::= { wvpdpEntry 1 }

wvpdpeProcessBuildEnv OBJECT-TYPE
    SYNTAX          NString
    ACCESS          read-only
    STATUS          mandatory
    DESCRIPTION     
            "The process build environment."
    ::= { wvpdpEntry 2 }

wvpdpeProcessBuildName OBJECT-TYPE
    SYNTAX          NString
    ACCESS          read-only
    STATUS          mandatory
    DESCRIPTION     
            "The process build name."
    ::= { wvpdpEntry 3 }

wvpdpeProcessBuildTime OBJECT-TYPE
    SYNTAX          NString
    ACCESS          read-only
    STATUS          mandatory
    DESCRIPTION     
            "The process build time."
    ::= { wvpdpEntry 4 }

wvpdpeProcessCpuBusyPercentage OBJECT-TYPE
    SYNTAX          INTEGER
    ACCESS          read-only
    STATUS          mandatory
    DESCRIPTION     
            "The process CPU busy percentage, calculated using
             deltas of wvpdpeProcessCpuBusySecs and
             wvpdpeProcessTotalSecs over a five second interval."
    ::= { wvpdpEntry 5 }

wvpdpeProcessCpuBusySecs OBJECT-TYPE
    SYNTAX          INTEGER
    ACCESS          read-only
    STATUS          mandatory
    DESCRIPTION     
            "The process CPU busy seconds."
    ::= { wvpdpEntry 6 }

wvpdpeProcessCpuTotalSecs OBJECT-TYPE
    SYNTAX          INTEGER
    ACCESS          read-only
    STATUS          mandatory
    DESCRIPTION     
            "The process CPU total seconds."
    ::= { wvpdpEntry 7 }

wvpdpeProcessCwd OBJECT-TYPE
    SYNTAX          NString
    ACCESS          read-only
    STATUS          mandatory
    DESCRIPTION     
            "The process current working directory."
    ::= { wvpdpEntry 8 }

wvpdpeProcessLoggingLevel OBJECT-TYPE
    SYNTAX          NString
    ACCESS          read-write
    STATUS          mandatory
    DESCRIPTION     
            "The process logging level."
    ::= { wvpdpEntry 9 }

wvpdpeProcessKBytes OBJECT-TYPE
    SYNTAX          INTEGER
    ACCESS          read-only
    STATUS          mandatory
    DESCRIPTION     
            "The process memory size in kilobytes."
    ::= { wvpdpEntry 10 }

wvpdpeProcessStartTime OBJECT-TYPE
    SYNTAX          NString
    ACCESS          read-only
    STATUS          mandatory
    DESCRIPTION     
            "The process start time."
    ::= { wvpdpEntry 11 }

wvpdpeProcessVersionName OBJECT-TYPE
    SYNTAX          NString
    ACCESS          read-only
    STATUS          mandatory
    DESCRIPTION     
            "The process version name."
    ::= { wvpdpEntry 12 }

wvpdpeProcessVersionNum OBJECT-TYPE
    SYNTAX          INTEGER
    ACCESS          read-only
    STATUS          mandatory
    DESCRIPTION     
            "The process version number."
    ::= { wvpdpEntry 13 }

wvpExtraParams OBJECT IDENTIFIER
    ::= { wdVpSet 5 }

watcherDaemon OBJECT IDENTIFIER
    ::= { wvpExtraParams 1 }

wdepCount OBJECT-TYPE
    SYNTAX          INTEGER
    ACCESS          read-only
    STATUS          mandatory
    DESCRIPTION     
            "The number of watcherDaemon virtual processes
             running on this machine."
    ::= { watcherDaemon 1 }

wdepList OBJECT-TYPE
    SYNTAX          NString
    ACCESS          read-only
    STATUS          mandatory
    DESCRIPTION     
            "A space delimited list of the vpids of the
             watcherDaemon virtual processes running on this
             machine."
    ::= { watcherDaemon 2 }

wdepTable OBJECT-TYPE
    SYNTAX          SEQUENCE OF WdepEntry
    ACCESS          not-accessible
    STATUS          mandatory
    DESCRIPTION     
            "Table of watcherDaemon virtual process extra
             parameters."
    ::= { watcherDaemon 3 }

wdepEntry OBJECT-TYPE
    SYNTAX          WdepEntry
    ACCESS          not-accessible
    STATUS          mandatory
    DESCRIPTION     
            "Extra parameters for a particular watcherDaemon
             virtual process.  This table is indexed by
             wvpdpeProcessVpid (from wvpdpTable), and the
             total number of conceptual rows in this table is
             wdepCount.  The vpids represented in this table are
             listed in wdepList."
    INDEX           { wvpdpeProcessVpid }
    ::= { wdepTable 1 }

WdepEntry ::=
    SEQUENCE {
        wdepeSystemCpuIdlePercentage    INTEGER,
        wdepeSystemCpuKernelPercentage  INTEGER,
        wdepeSystemCpuUserPercentage    INTEGER,
        wdepeSystemCpuWaitPercentage    INTEGER,
        wdepeSystemCpuQueueLength       INTEGER,
        wdepeSystemMemoryPhysicalFreeKBytes   INTEGER,
        wdepeSystemMemoryPhysicalTotalKBytes    INTEGER,
        wdepeSystemMemoryVirtualFreeKBytes  INTEGER,
        wdepeSystemMemoryVirtualTotalKBytes   INTEGER,
        wdepeSystemNumCpus              INTEGER,
        wdepeSystemNumCpusOnline        INTEGER
    }

wdepeSystemCpuIdlePercentage OBJECT-TYPE
    SYNTAX          INTEGER
    ACCESS          read-only
    STATUS          mandatory
    DESCRIPTION     
            "The idle CPU percentage for this system."
    ::= { wdepEntry 1 }

wdepeSystemCpuKernelPercentage OBJECT-TYPE
    SYNTAX          INTEGER
    ACCESS          read-only
    STATUS          mandatory
    DESCRIPTION     
            "The kernel CPU percentage for this system."
    ::= { wdepEntry 2 }

wdepeSystemCpuUserPercentage OBJECT-TYPE
    SYNTAX          INTEGER
    ACCESS          read-only
    STATUS          mandatory
    DESCRIPTION     
            "The user CPU percentage for this system."
    ::= { wdepEntry 3 }

wdepeSystemCpuWaitPercentage OBJECT-TYPE
    SYNTAX          INTEGER
    ACCESS          read-only
    STATUS          mandatory
    DESCRIPTION     
            "The wait CPU percentage for this system."
    ::= { wdepEntry 4 }

wdepeSystemCpuQueueLength OBJECT-TYPE
    SYNTAX          INTEGER
    ACCESS          read-only
    STATUS          mandatory
    DESCRIPTION     
            "The CPU queue length for this system."
    ::= { wdepEntry 5 }

wdepeSystemMemoryPhysicalFreeKBytes OBJECT-TYPE
    SYNTAX          INTEGER
    ACCESS          read-only
    STATUS          mandatory
    DESCRIPTION     
            "The free physical memory in kilobytes for
             this system."
    ::= { wdepEntry 6 }

wdepeSystemMemoryPhysicalTotalKBytes OBJECT-TYPE
    SYNTAX          INTEGER
    ACCESS          read-only
    STATUS          mandatory
    DESCRIPTION     
            "The total physical memory in kilobytes for
             this system."
    ::= { wdepEntry 7 }

wdepeSystemMemoryVirtualFreeKBytes OBJECT-TYPE
    SYNTAX          INTEGER
    ACCESS          read-only
    STATUS          mandatory
    DESCRIPTION     
            "The free virtual memory in kilobytes for
             this system."
    ::= { wdepEntry 8 }

wdepeSystemMemoryVirtualTotalKBytes OBJECT-TYPE
    SYNTAX          INTEGER
    ACCESS          read-only
    STATUS          mandatory
    DESCRIPTION     
            "The total virtual memory in kilobytes for
             this system."
    ::= { wdepEntry 9 }

wdepeSystemNumCpus OBJECT-TYPE
    SYNTAX          INTEGER
    ACCESS          read-only
    STATUS          mandatory
    DESCRIPTION     
            "The number of CPUs in this system."
    ::= { wdepEntry 10 }

wdepeSystemNumCpusOnline OBJECT-TYPE
    SYNTAX          INTEGER
    ACCESS          read-only
    STATUS          mandatory
    DESCRIPTION     
            "The number of CPUs online in this system."
    ::= { wdepEntry 11 }

wdWmSet OBJECT IDENTIFIER
    ::= { watcherDaemonMib 3 }

wmSetControl OBJECT IDENTIFIER
    ::= { wdWmSet 1 }

startWmArgs OBJECT-TYPE
    SYNTAX          NString
    ACCESS          read-write
    STATUS          mandatory
    DESCRIPTION     
            "The full command line of the module to start."
    ::= { wmSetControl 1 }

startWmState OBJECT-TYPE
    SYNTAX          INTEGER { nullState(1), doneState(2), goStart(100), 
                        goReset(200) }
    ACCESS          read-write
    STATUS          mandatory
    DESCRIPTION     
            "Control starting a watcher module.  The only valid
             set values are goStart and goReset.  Set to
             goStart to start a module (based on arguments
             supplied in startWmArgs).  After starting and
             the state is doneState, startWmStatus can be
             checked for the status of the start, and
             startWmModuleId can be checked for the module id of the
             module that was started.  Set to goReset to reset
             the startWmStatus and startWmModuleId, and reset the
             state back to the nullState."
    ::= { wmSetControl 2 }

startWmStatus OBJECT-TYPE
    SYNTAX          NString
    ACCESS          read-only
    STATUS          mandatory
    DESCRIPTION     
            "The status of the last attempted start."
    ::= { wmSetControl 3 }

startWmModuleId OBJECT-TYPE
    SYNTAX          Gauge
    ACCESS          read-only
    STATUS          mandatory
    DESCRIPTION     
            "The module id of the last attempted start."
    ::= { wmSetControl 4 }

wmControl OBJECT IDENTIFIER
    ::= { wdWmSet 2 }

wmcCount OBJECT-TYPE
    SYNTAX          INTEGER
    ACCESS          read-only
    STATUS          mandatory
    DESCRIPTION     
            "The number of modules running in the watcher-daemon."
    ::= { wmControl 1 }

wmcList OBJECT-TYPE
    SYNTAX          NString
    ACCESS          read-only
    STATUS          mandatory
    DESCRIPTION     
            "A space delimited list of the module ids of the
             modules running on this machine."
    ::= { wmControl 2 }

wmcTable OBJECT-TYPE
    SYNTAX          SEQUENCE OF WmcEntry
    ACCESS          not-accessible
    STATUS          mandatory
    DESCRIPTION     
            "Table of module information."
    ::= { wmControl 3 }

wmcEntry OBJECT-TYPE
    SYNTAX          WmcEntry
    ACCESS          not-accessible
    STATUS          mandatory
    DESCRIPTION     
            "Information and control for a particular
             module.  This table is indexed by wmceModuleId
             (not consecutive), and the total number of conceptual
             rows in this table is wmcCount.  The module ids
             represented in this table are listed in wmcList."
    INDEX           { wmceModuleId }
    ::= { wmcTable 1 }

WmcEntry ::=
    SEQUENCE {
        wmceModuleId                    Gauge,
        wmceModuleState                 INTEGER,
        wmceName                        NString,
        wmceArgc                        INTEGER,
        wmceArgv                        NString,
        wmceQuiesceTimeoutMs            INTEGER,
        wmceAssignedTime                NTimeVal,
        wmcePort                        INTEGER,
        wmceQuiesceAttemptedTime        NTimeVal,
        wmceDiedTime                    NTimeVal,
        wmceReleasedTime                NTimeVal
    }

wmceModuleId OBJECT-TYPE
    SYNTAX          Gauge
    ACCESS          read-only
    STATUS          mandatory
    DESCRIPTION     
            "The module id."
    ::= { wmcEntry 1 }

wmceModuleState OBJECT-TYPE
    SYNTAX          INTEGER { nullState(1), startingState(2), 
                        readyState(3), quiescingState(4), 
                        terminatingState(5), releasingState(6), 
                        goQuiesce(100) }
    ACCESS          read-write
    STATUS          mandatory
    DESCRIPTION     
            "The module state.  The only valid set value
             is goQuiesce.  Set to quiesce the module, and
             check wmrieQuiesceAttemptedTime to make sure the
             action was attempted."
    ::= { wmcEntry 2 }

wmceName OBJECT-TYPE
    SYNTAX          NString
    ACCESS          read-only
    STATUS          mandatory
    DESCRIPTION     
            "The name for the module."
    ::= { wmcEntry 3 }

wmceArgc OBJECT-TYPE
    SYNTAX          INTEGER
    ACCESS          read-only
    STATUS          mandatory
    DESCRIPTION     
            "The number of arguments for the module."
    ::= { wmcEntry 4 }

wmceArgv OBJECT-TYPE
    SYNTAX          NString
    ACCESS          read-only
    STATUS          mandatory
    DESCRIPTION     
            "The arguments for the module."
    ::= { wmcEntry 5 }

wmceQuiesceTimeoutMs OBJECT-TYPE
    SYNTAX          INTEGER
    ACCESS          read-only
    STATUS          mandatory
    DESCRIPTION     
            "The quiesce timeout in milliseconds, or the time
             the WatcherDaemon will wait for a quiesce before
             the module is automatically killed."
    ::= { wmcEntry 6 }

wmceAssignedTime OBJECT-TYPE
    SYNTAX          NTimeVal
    ACCESS          read-only
    STATUS          mandatory
    DESCRIPTION     
            "The assigned time of the module."
    ::= { wmcEntry 7 }

wmcePort OBJECT-TYPE
    SYNTAX          INTEGER
    ACCESS          read-only
    STATUS          mandatory
    DESCRIPTION     
            "The port the module is listening on."
    ::= { wmcEntry 8 }

wmceQuiesceAttemptedTime OBJECT-TYPE
    SYNTAX          NTimeVal
    ACCESS          read-only
    STATUS          mandatory
    DESCRIPTION     
            "The quiesce attempted time of the module."
    ::= { wmcEntry 9 }

wmceDiedTime OBJECT-TYPE
    SYNTAX          NTimeVal
    ACCESS          read-only
    STATUS          mandatory
    DESCRIPTION     
            "The died time of the module."
    ::= { wmcEntry 10 }

wmceReleasedTime OBJECT-TYPE
    SYNTAX          NTimeVal
    ACCESS          read-only
    STATUS          mandatory
    DESCRIPTION     
            "The released time of the module."
    ::= { wmcEntry 11 }

wmrInfo OBJECT IDENTIFIER
    ::= { wdWmSet 3 }

wmriCount OBJECT-TYPE
    SYNTAX          INTEGER
    ACCESS          not-accessible
    STATUS          mandatory
    DESCRIPTION     
            "The number of released modules."
    ::= { wmrInfo 1 }

wmriList OBJECT-TYPE
    SYNTAX          NString
    ACCESS          not-accessible
    STATUS          mandatory
    DESCRIPTION     
            "A space delimited list of the module ids of the
             released modules."
    ::= { wmrInfo 2 }

wdNotifications OBJECT IDENTIFIER
    ::= { watcherDaemonMib 100 }

wdNotificationPrefix OBJECT IDENTIFIER
    ::= { wdNotifications 0 }

wdNotificationObjects OBJECT IDENTIFIER
    ::= { wdNotifications 1 }

wdnoClapiSeverity OBJECT-TYPE
    SYNTAX          INTEGER { criticalAlarm(1), majorAlarm(2), 
                        minorAlarm(4), fatal(8), error(16), warning(32), 
                        userError(64), userWarning(128), status(256), 
                        info(1024), detailedInfo(4096), 
                        veryDetailedInfo(16384) }
    ACCESS          read-only
    STATUS          mandatory
    DESCRIPTION     
            "The severity of the clapi notification."
    ::= { wdNotificationObjects 1 }

wdnoClapiMessageId OBJECT-TYPE
    SYNTAX          NString
    ACCESS          read-only
    STATUS          mandatory
    DESCRIPTION     
            "The message ID of the clapi notification."
    ::= { wdNotificationObjects 2 }

wdnoClapiMessage OBJECT-TYPE
    SYNTAX          NString
    ACCESS          read-only
    STATUS          mandatory
    DESCRIPTION     
            "The message of the clapi notification."
    ::= { wdNotificationObjects 3 }

wdnoClapiHostName OBJECT-TYPE
    SYNTAX          NString
    ACCESS          read-only
    STATUS          mandatory
    DESCRIPTION     
            "The host name of the clapi notification."
    ::= { wdNotificationObjects 4 }

wdnoClapiServiceName OBJECT-TYPE
    SYNTAX          NString
    ACCESS          read-only
    STATUS          mandatory
    DESCRIPTION     
            "The service name of the clapi notification."
    ::= { wdNotificationObjects 5 }

wdStartNotification TRAP-TYPE
    ENTERPRISE      wdNotifications
--     STATUS          mandatory
    DESCRIPTION     
            "This notification is generated when the snmp-watcher-
             module is loaded and initialized."
    ::= 1

wdDaemonQuiesceNotification TRAP-TYPE
    ENTERPRISE      wdNotifications
--     STATUS          mandatory
    DESCRIPTION     
            "This notification is generated when the watcher-daemon
             starts quiescing."
    ::= 2

wdClapiNotification TRAP-TYPE
    ENTERPRISE      wdNotifications
    VARIABLES       { wdnoClapiSeverity, wdnoClapiMessageId, 
                      wdnoClapiMessage, wdnoClapiHostName, 
                      wdnoClapiServiceName }
--     STATUS          mandatory
    DESCRIPTION     
            "This notification is generated on clapi events."
    ::= 3

END -- end of module NUANCE-MIB.
