--  =====================================================================
-- No. 1/196 03-CXC 172 6153/2                 MANAGEMENT INFORMATION BASE
-- =====================================================================
-- Prepared:  TEI/XMX/ TEIMOGL                Revision  M
-- =====================================================================
-- Copyright
-- +++++++++
-- 
-- (c) Ericsson AS 2006. All rights reserved. No part of this document 
-- may be reproduced in any form without the written permission of the 
-- copyright holder.
-- 
-- Information
-- +++++++++++
-- 
-- This document is mainly intended for internal development and contains 
-- references to other documents. This document might however, after 
-- agreement with Ericsson, be delivered to customers to serve as 
-- information for design.
-- All referenced documents are however Ericsson internal and are not 
-- intended for customers or end users and will thus not be delivered 
-- externally.
--  
-- Disclaimer
-- ++++++++++
-- The content of this document is subject to revision without notice 
-- due to continued progress in methodology, design, and manufacturing. 
-- Ericsson shall have no liability for any error or damage of any kind 
-- resulting from the use of this document. 
-- 
-- =====================================================================
-- 

XF-CN-MIB DEFINITIONS ::= BEGIN

		IMPORTS
			entPhysicalIndex 
				FROM ENTITY-MIB
        		xfLicenseFeatureEntry	
        			FROM XF-LICENSE-MIB						
			OBJECT-GROUP, MODULE-COMPLIANCE			
				FROM SNMPv2-CONF			
			dsx1ConfigEntry
				FROM DS1-MIB
			Integer32, IpAddress, OBJECT-TYPE, MODULE-IDENTITY			
				FROM SNMPv2-SMI	
			DateAndTime, TEXTUAL-CONVENTION			
				FROM SNMPv2-TC
			SnmpAdminString
				FROM SNMP-FRAMEWORK-MIB
			ifIndex
				FROM IF-MIB              
			xfCN500 
				FROM XF-TOP-MIB;	
				
		-- 1.3.6.1.4.1.193.81.7.1
		xfCNMIB MODULE-IDENTITY
			LAST-UPDATED "201109280900Z"		-- Sept 28, 2011 at 09:00 GMT
			ORGANIZATION 
				"Ericsson Italy Milano"
			CONTACT-INFO 
				"Ericsson Italy Milano"				
			DESCRIPTION 
				"The MIB for specific CN500 objects in CN500."
			REVISION "201109280900Z"		-- Sept 28, 2011 at 09:00 GMT			
			DESCRIPTION 
				"Rev. O				
				Added objects: xfCNSiteLANMIBObjects, xfCNSiteLANCapability."
				
			REVISION "201104280900Z"		-- April 28, 2011 at 09:00 GMT			

			DESCRIPTION 
				"Rev. N				
				Extended XfCNEthernetEntry."				
			REVISION "201104280800Z"		-- April 28, 2011 at 08:00 GMT
			DESCRIPTION 
				"Rev. M				
				Added xfCNSyncEAlarmsStatus."				
			REVISION "201101251100Z"		-- November 25, 2010 at 11:00 GMT
			DESCRIPTION 
				"Rev. L				
				Made xfCNSyncEConfig and xfCNSyncEQLDomain read-write."				
			REVISION "201011251100Z"		-- November 25, 2010 at 11:00 GMT			
			DESCRIPTION 
				"Rev. K				
				Added objects: xfCNSyncQualityCapability."				
			REVISION "201011151100Z"		-- November 15, 2010 at 11:00 GMT			
			DESCRIPTION 
				"Rev. J				
				Added objects: xfCNSyncEConfig and xfCNSyncEQLDomain."
			REVISION "201011011100Z"		-- November 1, 2010 at 11:00 GMT			
			DESCRIPTION 
				"Rev. H				
				Added objects in xfCNSFPTable for diagnostic monotoring according to SFF-8472.
				Removed LaserMode."
			REVISION "201010011100Z"		-- October 1, 2010 at 11:00 GMT			
			DESCRIPTION 
				"Rev. G				
				Added objects: xfCNPacketTestTable for PT2010"				
			REVISION "201009291100Z"		-- September 29, 2010 at 11:00 GMT			
			DESCRIPTION 
				"Rev. F				
				Added objects: xfCNLicenseFeatureRMM, xfCNLicenseFingerPrintTable"				   
			REVISION "201006231600Z"		-- June 23, 2010 at 16:00 GMT
				DESCRIPTION 
					"Rev. E
					Added table xfCNEthernet and xfCNSfp"        
			REVISION "201006011600Z"		-- June 1, 2010 at 16:00 GMT
				DESCRIPTION 
					"Rev. D
					Modified the definition of xfCNSyncBoardCapability"
			REVISION "201004301600Z"		-- April 30, 2010 at 16:00 GMT
				DESCRIPTION 
					"Rev. C
					Updated description of xfCNInstallationModeInfoIndex"				       
			REVISION "201004281600Z"		-- April 28, 2010 at 16:00 GMT
				DESCRIPTION 
					"Rev. B
					Changed type for MO xfCNInstallationModeProductNumber: SnmpAdminString"          
			REVISION "201004191200Z"		-- April 19, 2010 at 12:00 GMT
				DESCRIPTION 
					"Rev. A"
			
			::= {  xfCN500 1}
			
--
-- Node definitions
--			

		-- 1.3.6.1.4.1.193.81.7.1.1
		xfCNMIBObjects OBJECT IDENTIFIER ::= { xfCNMIB 1}
		

		-- 1.3.6.1.4.1.193.81.7.1.1.1
		xfCNDs1MIBXObjects OBJECT IDENTIFIER ::= { xfCNMIBObjects 1 }

		-- 1.3.6.1.4.1.193.81.7.1.1.1.1		
		xfCNDsx1ConfigXTable OBJECT-TYPE
			SYNTAX SEQUENCE OF XfCNDsx1ConfigXEntry
			MAX-ACCESS not-accessible
			STATUS current
			DESCRIPTION
				" This table is an extension of the dsx1ConfigTable.
				"
			::= { xfCNDs1MIBXObjects 1 }

		-- 1.3.6.1.4.1.193.81.7.1.1.1.1.1
		xfCNDsx1ConfigXEntry OBJECT-TYPE
			SYNTAX XfCNDsx1ConfigXEntry
			MAX-ACCESS not-accessible
			STATUS current
			DESCRIPTION
				"Additional information about the configuration of a E1 
				interface."
			AUGMENTS { dsx1ConfigEntry }
			::= { xfCNDsx1ConfigXTable 1 }

		
		XfCNDsx1ConfigXEntry ::=
			SEQUENCE { 
				xfCNDsx1Mode INTEGER

     			}
		
		-- 1.3.6.1.4.1.193.81.7.1.1.1.1.1.1	
 		xfCNDsx1Mode OBJECT-TYPE
          		SYNTAX  INTEGER {
                    pdhTraffic (1),
					syncIn2MHz (2),
					syncIn2Mbps (3),
					syncOut2MHz (4),
					syncOut2Mbps (5)
                     
                 		}
          		MAX-ACCESS  read-write
          		STATUS  current
          		DESCRIPTION

                "xfCNDsx1Mode is used to configure the E1 physical port as SI:
                either input or output and its format, either 2Mbps or 2MHz.
                When SI is configured the interface is used to transport the synchronization signal over the hop.

				When xfCNDsx1Mode is set to pdhTraffic the interface is dedicated for PDH traffic.
				
				This MO is applicable only for the interface instances relative to the 14th, 15th and 16th E1 ports.
				The MO for 16th E1 port is always settable to syncIn2MHz/2Mbps or syncOut2MHz/2Mbps.
				The MO for 15th E1 port is settable to syncOut2MHz/2Mbps only if MO for 16th E1 port has been set to output SI.
				The MO for 14th E1 port is settable to or syncOut2MHz/2Mbps only if MO for 15th E1 port has been set to output SI."
			DEFVAL { pdhTraffic }
                 		
          		::= { xfCNDsx1ConfigXEntry 1 }

		-- 1.3.6.1.4.1.193.81.7.1.1.2
		xfCNSyncMIBObjects OBJECT IDENTIFIER ::= { xfCNMIBObjects 2 }


		-- 1.3.6.1.4.1.193.81.7.1.1.2.1
		xfCNSyncBoardCapability OBJECT-TYPE
			SYNTAX BITS
				{
				twoMbps(0),
				twoMHz(1)			
				}
			MAX-ACCESS read-only
			STATUS current
			DESCRIPTION
				"Capability bits for Synchronization signal transport of a CN500 board.
                		0	twoMbps		2048kbps synch signal transport
				1	twoMHz		2048kHz synch signal transport
				
				Note: they are not mutually exclusive. 
				The different values are:
				0000.0000 means no sync
				1000.0000 means 2048kbps
				0100.0000 means 2048kHz
				1100.0000 means 2048kbps and 2048kHz
				"
			::= { xfCNSyncMIBObjects 1 }
			
		-- 1.3.6.1.4.1.193.81.7.1.1.2.2
		xfCNSyncEConfig OBJECT-TYPE
			SYNTAX INTEGER {
				other (1),
				syncEDisabled (2),
				syncERingEthernet (3),
				syncERingRadio (4),
				syncEChainEthernet (5),
				syncEChainRadio (6)
          	}
			MAX-ACCESS read-write
			STATUS current
			DESCRIPTION
				"Use case based configuration of SyncE.
				
				SyncEDisabled (2),
				SyncERingEthernet (3),
				SyncERingRadio (4),
				SyncEChainEthernet (5),
				SyncEChainRadio (6).
				
				Select one of the SyncE configurations.
				Other MOs will be affected."
			::= { xfCNSyncMIBObjects 2 }

		-- 1.3.6.1.4.1.193.81.7.1.1.2.3
		xfCNSyncEQLDomain OBJECT-TYPE
			SYNTAX INTEGER {
				other (1),
				syncEANSI (2),
				syncEETSI (3)
          	}
			MAX-ACCESS read-write
			STATUS current
			DESCRIPTION
				"Selects the domain of the QL values.
				Other(1),
				ANSI (2),
				ETSI (3)"
			::= { xfCNSyncMIBObjects 3 }  
			
			
		-- 1.3.6.1.4.1.193.81.7.1.1.2.4
		xfCNSyncQualityCapability OBJECT-TYPE
			SYNTAX BITS {
				synchQualCap (0)
			}
			MAX-ACCESS read-only
			STATUS current
			DESCRIPTION
				"Capability MO stating if the CN500 SW supports notAssigned as default values for the Quality Level when input SI is configured.
	 
				Bits 0:
					 0	not supported 
					 1 	supported 
				"
			::= { xfCNSyncMIBObjects 4 }

				-- 1.3.6.1.4.1.193.81.7.1.1.2.4
		xfCNSyncEAlarmStatus OBJECT-TYPE
			SYNTAX BITS {
		  loesmc0(0),
		  loesmc1(1),
		  loesmc2(2),
		  invalidQLEthernet0(3),
		  invalidQLEthernet1(4),
		  invalidQLEthernet2(5),
		  invalidQLRL0(6),
		  invalidQLRL1(7),
		  invalidQLRL2(8)
			}
			MAX-ACCESS read-only
			STATUS current
			DESCRIPTION
				"The alarms for SyncE:
				
          loesmc      - Critical: Loss of ESMC. No ESMC PDU for the last five seconds. QL-DNU is reported on the interface.
          invalidQLEthernet - Critical: The ESMC QL values from the Ethernet port has invalid values. 
          							    Probably due to wrong QL domain[ANSI, ETSI]. QL-INV is reported on the interface.
          invalidQLRL    - Critical: The SSM QL values from the hop has invalid values. 
                                     Probably due to wrong QL domain[ANSI, ETSI]. QL-INV is reported on the interface.
 
				"
			::= { xfCNSyncMIBObjects 5 }

		-- 1.3.6.1.4.1.193.81.7.1.1.3
		xfCNRestoreConfigMIBObjects OBJECT IDENTIFIER ::= { xfCNMIBObjects 3 }

		-- 1.3.6.1.4.1.193.81.7.1.1.3.1
		xfCNInstallationModeInfoTable OBJECT-TYPE
			SYNTAX SEQUENCE OF XfCNInstallationModeInfoEntry
			MAX-ACCESS not-accessible
			STATUS current
			DESCRIPTION
				"This table contains the main parameters of configuration file stored
				in RMM and Flash. This info will be shown to the operator as preview data
				of configuration file."
				
			::= { xfCNRestoreConfigMIBObjects 1 }

		
		-- 1.3.6.1.4.1.193.81.7.1.1.3.1.1
		xfCNInstallationModeInfoEntry OBJECT-TYPE
			SYNTAX XfCNInstallationModeInfoEntry
			MAX-ACCESS not-accessible
			STATUS current
			DESCRIPTION
				"An Entry for the configuration file stored in RMM and in Flash."
				
			INDEX{     xfCNInstallationModeInfoIndex    }
			::= { xfCNInstallationModeInfoTable 1 }

		
		XfCNInstallationModeInfoEntry ::=
			SEQUENCE {
 				xfCNInstallationModeInfoIndex		Integer32,
				xfCNInstallationModeConfigFileTime 	DateAndTime,
				xfCNInstallationModeDCNIP		IpAddress, 
				xfCNInstallationModeDCNSubNet		IpAddress, 
				xfCNInstallationModeProductNumber 	SnmpAdminString
				
     			}

		-- 1.3.6.1.4.1.193.81.7.1.1.3.1.1.1
		xfCNInstallationModeInfoIndex    OBJECT-TYPE
			SYNTAX Integer32 (1..2)
			MAX-ACCESS read-only
			STATUS current
			DESCRIPTION
				"Index to the table. It indexes two entries, one row for RMM and one row for CN flash.
				The association between index and memory support is:
				1   -> RMM
				2   -> FLASH
				"
			::= { xfCNInstallationModeInfoEntry 1 }

		-- 1.3.6.1.4.1.193.81.7.1.1.3.1.1.2
		xfCNInstallationModeConfigFileTime OBJECT-TYPE
			SYNTAX DateAndTime
			MAX-ACCESS read-only
			STATUS current
			DESCRIPTION
				"Date and time of creation of configuration file. Format: yyyy-mm-dd-hh-mm-ss."
			::= { xfCNInstallationModeInfoEntry 2 }

		-- 1.3.6.1.4.1.193.81.7.1.1.3.1.1.3
		xfCNInstallationModeDCNIP OBJECT-TYPE
			SYNTAX IpAddress
			MAX-ACCESS read-only
			STATUS current
			DESCRIPTION
				"DCN IP address."
			::= { xfCNInstallationModeInfoEntry 3 }

		-- 1.3.6.1.4.1.193.81.7.1.1.3.1.1.4
		xfCNInstallationModeDCNSubNet OBJECT-TYPE
			SYNTAX IpAddress
			MAX-ACCESS read-only
			STATUS current
			DESCRIPTION
				"DCN subnet mask."
			::= { xfCNInstallationModeInfoEntry 4 }

		-- 1.3.6.1.4.1.193.81.7.1.1.3.1.1.5
		xfCNInstallationModeProductNumber OBJECT-TYPE
			SYNTAX SnmpAdminString
			MAX-ACCESS read-only
			STATUS current
			DESCRIPTION
				"CN (MMU2 XS) product number."
			::= { xfCNInstallationModeInfoEntry 5 }
			
		-- 1.3.6.1.4.1.193.81.7.1.1.4
		xfCNEthernetMIBObjects OBJECT IDENTIFIER ::= { xfCNMIBObjects 4 }

		-- 1.3.6.1.4.1.193.81.7.1.1.4.1
		xfCNEthernetTable OBJECT-TYPE
			SYNTAX SEQUENCE OF XfCNEthernetEntry
			MAX-ACCESS not-accessible
			STATUS current
			DESCRIPTION
				"Ethernet table"
				
			::= { xfCNEthernetMIBObjects 1 }

		
		-- 1.3.6.1.4.1.193.81.7.1.1.4.1.1
		xfCNEthernetEntry OBJECT-TYPE
			SYNTAX XfCNEthernetEntry
			MAX-ACCESS not-accessible
			STATUS current
			DESCRIPTION
				"Ethernet entry"
				
			INDEX{     ifIndex    }
			::= { xfCNEthernetTable 1 }

		
		XfCNEthernetEntry ::=
			SEQUENCE {
				xfCNVlanId  				Integer32,
				xfCNEthernetLoop 		INTEGER,
				xfCNVlanTPId				INTEGER,
				xfCNVlanPcp					Integer32,
				xfCNIpDscp					Integer32				
			}

		-- 1.3.6.1.4.1.193.81.7.1.1.4.1.1.1
		xfCNVlanId OBJECT-TYPE
			SYNTAX Integer32
			MAX-ACCESS read-write
			STATUS current
			DESCRIPTION
				"VLAN ID for the in-band management.
				A number between 0 - 4094"
			::= { xfCNEthernetEntry 1 }

		-- 1.3.6.1.4.1.193.81.7.1.1.4.1.1.2
		xfCNEthernetLoop OBJECT-TYPE
			SYNTAX INTEGER {
					other (1),
					enable (2),
					disable (3)          
      }
			MAX-ACCESS read-write
			STATUS current
			DESCRIPTION
				"Ethernet loop"
			DEFVAL { disable }
			::= { xfCNEthernetEntry 2 }      

    -- 1.3.6.1.4.1.193.81.7.1.1.4.1.1.3
    	xfCNVlanTPId OBJECT-TYPE
			SYNTAX INTEGER {
					other (1),
					etherType0x8100 (2),
					etherType0x88a8 (3)          
      }	
      MAX-ACCESS read-write
			STATUS current
			DESCRIPTION
				"VLAN Tag Protocol Identifier for the in-band management over LAN and WAN"
			DEFVAL { etherType0x8100 }
			::= { xfCNEthernetEntry 3 }			

    -- 1.3.6.1.4.1.193.81.7.1.1.4.1.1.4
    	xfCNVlanPcp OBJECT-TYPE
			SYNTAX Integer32 
			MAX-ACCESS read-write
			STATUS current
			DESCRIPTION
				"
					Priority Code Point
					It indicates the frame priority level. Values are from 0 (best effort) to 7 (highest); User Priority 1 represents the lowest value in IEEE 802.1 Q and therefore shall be send to TC0.
					PCP	Network priority	Traffic characteristics
					1          	0        	(lowest)	Background 
					0          	1        	Best Effort
					2          	2        	Excellent Effort (Default Value)
					3          	3        	Critical Applications
					4          	4        	Video, < 100 ms latency
					5          	5        	Voice, < 10 ms latency
					6          	6        	Internetwork Control
					7          	7        	(highest)	Network Control
				"
			DEFVAL { 2 }
			::= { xfCNEthernetEntry 4 }

    -- 1.3.6.1.4.1.193.81.7.1.1.4.1.1.5
    	xfCNIpDscp OBJECT-TYPE
			SYNTAX Integer32 	
			MAX-ACCESS read-write
			STATUS current
			DESCRIPTION
				"
				Differentiated Services Code Point (DSCP) field in the header of DCN IP packets coming from the internal management port used for packet classification purposes northbound from the PT1.
				DSCP allowed values between 0-63.
				"
			DEFVAL { 0 }	
			::= { xfCNEthernetEntry 5 }			
			

		-- 1.3.6.1.4.1.193.81.7.1.1.5
		xfCNSfpObjects OBJECT IDENTIFIER ::= { xfCNMIBObjects 5 }

		-- 1.3.6.1.4.1.193.81.7.1.1.5.1
		xfCNSfpTable OBJECT-TYPE
			SYNTAX SEQUENCE OF XfCNSfpEntry
			MAX-ACCESS not-accessible
			STATUS current
			DESCRIPTION
				"This table contains objects mainly for diagnostic monitoring according to
				diagnostic monitoring according to SFF-8472."
				
			::= { xfCNSfpObjects 1 }

		
		-- 1.3.6.1.4.1.193.81.7.1.1.5.1.1
		xfCNSfpEntry OBJECT-TYPE
			SYNTAX XfCNSfpEntry
			MAX-ACCESS not-accessible
			STATUS current
			DESCRIPTION
				"Sfp entry"
				
			INDEX{     entPhysicalIndex    }
			::= { xfCNSfpTable 1 }

		
		XfCNSfpEntry ::=
			SEQUENCE {
 				xfCNSfpReceivedPower				Integer32,
 				xfCNSfpTransmittedPower				Integer32,
 				xfCNSfpReceivedPowerThreshold		Integer32,
 				xfCNSfpTransmittedPowerThreshold	Integer32,
 				xfCNSfpTemperature					Integer32,
 				xfCNSfpBiasCurrent					Integer32,
 				xfCNSfpSupplyVoltage				Integer32,
				xfCNSfpAlarmStatus					BITS				
			}
		-- 1.3.6.1.4.1.193.81.7.1.1.5.1.1.1
		xfCNSfpReceivedPower OBJECT-TYPE
			SYNTAX Integer32
			MAX-ACCESS read-only
			STATUS current
			DESCRIPTION
				"Received power on the SFP in dBm. Typical values range from -22 to 3,6 dBm."
			::= { xfCNSfpEntry 1 }

		-- 1.3.6.1.4.1.193.81.7.1.1.5.1.1.2
		xfCNSfpTransmittedPower OBJECT-TYPE
			SYNTAX Integer32
			MAX-ACCESS read-only
			STATUS current
			DESCRIPTION
				"Transmitted power on the SFP in dBm. Typical values range from -9,5 to 3,6 dBm."
			::= { xfCNSfpEntry 2 }

		-- 1.3.6.1.4.1.193.81.7.1.1.5.1.1.3
		xfCNSfpReceivedPowerThreshold OBJECT-TYPE
			SYNTAX Integer32
			MAX-ACCESS read-write
			STATUS current
			DESCRIPTION
				"Threshold for SFP received power alarm."
			::= { xfCNSfpEntry 3 }
					
		-- 1.3.6.1.4.1.193.81.7.1.1.5.1.1.4
		xfCNSfpTransmittedPowerThreshold OBJECT-TYPE
			SYNTAX Integer32
			MAX-ACCESS read-write
			STATUS current
			DESCRIPTION
				"Threshold for SFP transmitted power alarm."
			::= { xfCNSfpEntry 4 }

		-- 1.3.6.1.4.1.193.81.7.1.1.5.1.1.5
		xfCNSfpTemperature OBJECT-TYPE
			SYNTAX Integer32
			MAX-ACCESS read-only
			STATUS current
			DESCRIPTION
				"SFP temperature in degrees Celsius, typical values range from -40 to +85."
			::= { xfCNSfpEntry 5 } 
			
		-- 1.3.6.1.4.1.193.81.7.1.1.5.1.1.6
		xfCNSfpBiasCurrent OBJECT-TYPE
			SYNTAX Integer32
			MAX-ACCESS read-only
			STATUS current
			DESCRIPTION
				"SFP bias current in mA, typical value is 300 mA."
			::= { xfCNSfpEntry 6 }
			
		-- 1.3.6.1.4.1.193.81.7.1.1.5.1.1.7
		xfCNSfpSupplyVoltage OBJECT-TYPE
			SYNTAX Integer32
			MAX-ACCESS read-only
			STATUS current
			DESCRIPTION
				"SFP supply voltage in tenths of volt, typical value is 3,6."
			::= { xfCNSfpEntry 7 }
			
		-- 1.3.6.1.4.1.193.81.7.1.1.5.1.1.8
		xfCNSfpAlarmStatus OBJECT-TYPE
            SYNTAX BITS
                {
                sfpReceivedPower0(0),
                sfpReceivedPower1(1),
                sfpReceivedPower2(2),
                sfpTransmittedPower1(3),
                sfpTransmittedPower2(4),
                sfpTransmittedPower3(5)
                }
            MAX-ACCESS read-only
            STATUS current
            DESCRIPTION
                "Indicates active alarm status of the PT2010 SFP functionality:
                
                SfpReceivedPower      

                  major    SFP received power is lower that the configured threshold.

                
                SfpTransmittedPower  
                  major    SFP transmitted power is lower that the configured threshold.
                
                
                Severity is indicated by 3 bits per status:
                bits 012
                     000   clear
                     001   undetermined
                     010   warning
                     011   minor
                     100   major
                     101   critical
                "
            ::= { xfCNSfpEntry 8 }


			
		-- 1.3.6.1.4.1.193.81.7.1.1.6
		xfCNLicenseMIBObjects OBJECT IDENTIFIER ::= { xfCNMIBObjects 6 }
		
		-- 1.3.6.1.4.1.193.81.7.1.1.6.1			
		xfCNLicenseFeatureXObjects OBJECT IDENTIFIER ::= { xfCNLicenseMIBObjects 1 }			
			
		-- 1.3.6.1.4.1.193.81.7.1.1.6.1.1		
		xfCNLicenseFeatureXTable OBJECT-TYPE
			SYNTAX SEQUENCE OF XfCNLicenseFeatureXEntry
			MAX-ACCESS not-accessible
			STATUS current
			DESCRIPTION
				" This table is an extension of the xfLicenseFeatureTable.
				"
			::= { xfCNLicenseFeatureXObjects 1 }

		-- 1.3.6.1.4.1.193.81.7.1.1.6.1.1.1
		xfCNLicenseFeatureXEntry OBJECT-TYPE
			SYNTAX XfCNLicenseFeatureXEntry
			MAX-ACCESS not-accessible
			STATUS current
			DESCRIPTION
				"This object specifies the CN500 RMM where the license, for a specific licensed feature, is stored.
				"
				
			AUGMENTS { xfLicenseFeatureEntry }
			::= { xfCNLicenseFeatureXTable 1 }

		
		XfCNLicenseFeatureXEntry ::=
			SEQUENCE { 
				xfCNLicenseFeatureRMM BITS
     			}
		
		-- 1.3.6.1.4.1.193.81.7.1.1.6.1.1.1.1	
 		xfCNLicenseFeatureRMM OBJECT-TYPE
          		SYNTAX BITS {
                     			masterRMM (0),
					slaveRMM (1)	                   
                 		}
          		MAX-ACCESS read-only
          		STATUS  current
          		DESCRIPTION
				"This object specifies the CN500 RMM (either Master or Slave or both) where the license,
				 for a specific licensed feature, is stored.
				
			bits 01:
			     00 Supported by the node SW but not present on any RMM;
			     10 Only present on either the Master RMM or the RMM in 1+0; 
			     01 Only present on Slave RMM;
			     11 Present on both Master and Slave RMM. "
			             		
          		::= { xfCNLicenseFeatureXEntry 1 }		


		-- 1.3.6.1.4.1.193.81.7.1.1.6.2			
		xfCNLicenseFingerPrintObjects OBJECT IDENTIFIER ::= { xfCNLicenseMIBObjects 2 }

	
		-- 1.3.6.1.4.1.193.81.7.1.1.6.2.1
		xfCNLicenseFingerPrintTable  OBJECT-TYPE
			SYNTAX SEQUENCE OF XfCNLicenseFingerPrintEntry
			MAX-ACCESS not-accessible
			STATUS current
			DESCRIPTION
				"This table contains the fingerprint of installed RMM both for 1+0 and 1+1 configurations.
				The table is indexed with entPhysicalIndex of the modem (CN500)"	
			::= { xfCNLicenseFingerPrintObjects 1 }

		-- 1.3.6.1.4.1.193.81.7.1.1.6.2.1.1
		xfCNLicenseFingerPrintEntry OBJECT-TYPE
			SYNTAX XfCNLicenseFingerPrintEntry
			MAX-ACCESS not-accessible
			STATUS current
			DESCRIPTION
				"An entry of a FingerPrint."
			INDEX { entPhysicalIndex }
			::= { xfCNLicenseFingerPrintTable 1 }
			

		XfCNLicenseFingerPrintEntry ::=
			SEQUENCE { 
				xfCNLicenseFingerPrint
					OCTET STRING
				}
						

		-- 1.3.6.1.4.1.193.81.7.1.1.6.2.1.1.1
		xfCNLicenseFingerPrint OBJECT-TYPE
			SYNTAX OCTET STRING
			MAX-ACCESS read-only
			STATUS current
			DESCRIPTION
				"The fingerprint of the RMM."
			::= { xfCNLicenseFingerPrintEntry 1 }
			

		-- 1.3.6.1.4.1.193.81.7.1.1.7
		xfCNPacketTestObjects OBJECT IDENTIFIER ::= { xfCNMIBObjects 7 }
				
		-- 1.3.6.1.4.1.193.81.7.1.1.7.1
		xfCNPacketTestTable OBJECT-TYPE
			SYNTAX SEQUENCE OF XfCNPacketTestEntry
			MAX-ACCESS not-accessible
			STATUS current
			DESCRIPTION
				"MOs for testing packet. It is a indexed table (by entPhysicalIndex)."
			::= { xfCNPacketTestObjects 1 }
		
		-- 1.3.6.1.4.1.193.81.7.1.1.7.1.1
		xfCNPacketTestEntry OBJECT-TYPE
			SYNTAX XfCNPacketTestEntry
			MAX-ACCESS not-accessible
			STATUS current
			DESCRIPTION
				"Packet test entry.
				The table is indexed with entPhysicalIndex of the modem (CN500)"
			INDEX { entPhysicalIndex }
			::=	{ xfCNPacketTestTable 1}			
		
		XfCNPacketTestEntry ::=
			SEQUENCE {
				xfCNTestNearEnd  	INTEGER,
				xfCNNearEndTestResult SnmpAdminString
				}
				
		-- 1.3.6.1.4.1.193.81.7.1.1.7.1.1.1
		xfCNTestNearEnd OBJECT-TYPE
			SYNTAX INTEGER {
					other (1),
					start  (2),
					pending  (3),
					finished (4)
          
      }
			MAX-ACCESS read-write
			STATUS current
			DESCRIPTION
				"Start,
				pending (read-only),
				finished (read-only).
				Start actuates the test, pending is during the test, finished then the result can be read."
			DEFVAL { other }	
			::= { xfCNPacketTestEntry 1 }
		
		-- 1.3.6.1.4.1.193.81.7.1.1.7.1.1.2			 
		xfCNNearEndTestResult OBJECT-TYPE
			SYNTAX SnmpAdminString
			MAX-ACCESS read-only
			STATUS current
			DESCRIPTION
				"TestOk
				ErrorTBD1,
				ErrorTBD2.
				Result can be read 30 seconds after the actuation and will be presented in the GUI as is. 
				That means that more test results can be added without updating the Craft."	
			::= { xfCNPacketTestEntry 2 }
		
		
		-- 1.3.6.1.4.1.193.81.7.1.1.8
		xfCNSiteLANMIBObjects OBJECT IDENTIFIER ::= { xfCNMIBObjects 8 }
				
		-- 1.3.6.1.4.1.193.81.7.1.1.8.1
		xfCNSiteLANCapability OBJECT-TYPE
		   SYNTAX BITS {
                                siteLANAlarmDisableNotSupported(0),
                                siteLANAlarmDisableSupported(1)
                                }
                   MAX-ACCESS read-only
                   STATUS current
                   DESCRIPTION
                       "This bit reports if CN500 unit supports the possibility to disable SiteLAN alarm  or not.
                       The different values are:
                       0    means disabling of SiteLAN alarm is Not Supported
                       1    means disabling of SiteLAN alarm is Supported"
                       ::= { xfCNSiteLANMIBObjects 1 }	
		
		
		
		-- 1.3.6.1.4.1.193.81.7.1.2
		xfCNConformance OBJECT IDENTIFIER ::= { xfCNMIB 2 }
		
		-- 1.3.6.1.4.1.193.81.7.1.2.1
		xfCNCompliances OBJECT IDENTIFIER ::= { xfCNConformance 1 }

		
		-- 1.3.6.1.4.1.193.81.7.1.2.1.1
		xfCNCompliance MODULE-COMPLIANCE
			STATUS current
			DESCRIPTION 
				"Description."
			MODULE -- this module
				MANDATORY-GROUPS { xfCNObjectGroup }
			::= { xfCNCompliances 1 }

		
		-- 1.3.6.1.4.1.193.81.7.1.2.2
		xfCNObjectGroups OBJECT IDENTIFIER ::= { xfCNConformance 2 }
 		
		-- 1.3.6.1.4.1.193.81.7.1.2.2.1
		xfCNObjectGroup OBJECT-GROUP
			OBJECTS { xfCNDsx1Mode, xfCNSyncBoardCapability, xfCNSyncEConfig, xfCNSyncEQLDomain, xfCNSyncQualityCapability,
				xfCNSyncEAlarmStatus,xfCNInstallationModeInfoIndex, xfCNInstallationModeConfigFileTime, xfCNInstallationModeDCNIP, 
				xfCNInstallationModeDCNSubNet, xfCNInstallationModeProductNumber, xfCNVlanId,  xfCNEthernetLoop, xfCNVlanTPId, 
				xfCNVlanPcp, xfCNIpDscp, xfCNSfpReceivedPower, xfCNSfpTransmittedPower, xfCNSfpReceivedPowerThreshold, 
				xfCNSfpTransmittedPowerThreshold, xfCNSfpTemperature, xfCNSfpBiasCurrent,	xfCNSfpSupplyVoltage, xfCNSfpAlarmStatus, 
				xfCNLicenseFeatureRMM, xfCNLicenseFingerPrint, xfCNTestNearEnd, xfCNNearEndTestResult, xfCNSiteLANCapability }
			STATUS current
			DESCRIPTION 
				"All objects in this MIB."
			::= { xfCNObjectGroups 1 }
			
			END
