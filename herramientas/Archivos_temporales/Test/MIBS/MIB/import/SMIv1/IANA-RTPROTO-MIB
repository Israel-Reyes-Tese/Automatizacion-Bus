--
-- This SMIv1 module has been generated by smidump 0.2-cvs. Do not edit.
--

IANA-RTPROTO-MIB DEFINITIONS ::= BEGIN

IMPORTS
    mib-2
        FROM RFC1213-MIB;

ianaRtProtoMIB OBJECT IDENTIFIER
    ::= { mib-2 84 }

-- ianaRtProtoMIB MODULE-IDENTITY
--     LAST-UPDATED    "200009260000Z"
--     ORGANIZATION    
--             "IANA"
--     CONTACT-INFO    
--             " Internet Assigned Numbers Authority
--              Internet Corporation for Assigned Names and Numbers
--              4676 Admiralty Way, Suite 330
--              Marina del Rey, CA 90292-6601
--              
--              Phone: +1 310 823 9358
--              EMail: iana@iana.org"
--     DESCRIPTION     
--             "This MIB module defines the IANAipRouteProtocol and
--              IANAipMRouteProtocol textual conventions for use in MIBs
--              which need to identify unicast or multicast routing
--              mechanisms.
--              
--              Any additions or changes to the contents of this MIB module
--              require either publication of an RFC, or Designated Expert
--              Review as defined in RFC 2434, Guidelines for Writing an
--              IANA Considerations Section in RFCs.  The Designated Expert 
--              will be selected by the IESG Area Director(s) of the Routing
--              Area."
--     REVISION        "200009260000Z"
--     DESCRIPTION     
--             "Original version, published in coordination
--              with RFC 2932."
--     ::= { mib-2 84 }


IANAipRouteProtocol ::=
    INTEGER { other(1), local(2), netmgmt(3), icmp(4), egp(5), ggp(6), 
                        hello(7), rip(8), isIs(9), esIs(10), 
                        ciscoIgrp(11), bbnSpfIgp(12), ospf(13), bgp(14), 
                        idpr(15), ciscoEigrp(16), dvmrp(17) }

-- IANAipRouteProtocol ::= TEXTUAL-CONVENTION
--     STATUS          mandatory
--     DESCRIPTION     
--             "A mechanism for learning routes.  Inclusion of values for
--              routing protocols is not intended to imply that those
--              protocols need be supported."
--     SYNTAX          INTEGER
--                       { other(1), local(2), netmgmt(3), icmp(4), 
--                         egp(5), ggp(6), hello(7), rip(8), isIs(9), 
--                         esIs(10), ciscoIgrp(11), bbnSpfIgp(12), 
--                         ospf(13), bgp(14), idpr(15), ciscoEigrp(16), 
--                         dvmrp(17) }

IANAipMRouteProtocol ::=
    INTEGER { other(1), local(2), netmgmt(3), dvmrp(4), mospf(5), 
                        pimSparseDense(6), cbt(7), pimSparseMode(8), 
                        pimDenseMode(9), igmpOnly(10), bgmp(11), 
                        msdp(12) }

-- IANAipMRouteProtocol ::= TEXTUAL-CONVENTION
--     STATUS          mandatory
--     DESCRIPTION     
--             "The multicast routing protocol.  Inclusion of values for
--              multicast routing protocols is not intended to imply that
--              those protocols need be supported."
--     SYNTAX          INTEGER
--                       { other(1), local(2), netmgmt(3), dvmrp(4), 
--                         mospf(5), pimSparseDense(6), cbt(7), 
--                         pimSparseMode(8), pimDenseMode(9), 
--                         igmpOnly(10), bgmp(11), msdp(12) }

END -- end of module IANA-RTPROTO-MIB.
