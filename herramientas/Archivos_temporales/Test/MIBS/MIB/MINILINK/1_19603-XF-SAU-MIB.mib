XF-SAU-MIB DEFINITIONS ::= BEGIN
	IMPORTS
		OBJECT-GROUP, MODULE-COMPLIANCE
		FROM SNMPv2-CONF
		Gauge32, Integer32, OBJECT-TYPE, MODULE-IDENTITY
			FROM SNMPv2-SMI
		TruthValue, RowStatus
			FROM SNMPv2-TC
		InterfaceIndex
			FROM IF-MIB
		xfIpSau
			FROM XF-TOP-MIB;

		xfSauMIB MODULE-IDENTITY
			LAST-UPDATED "200808140000Z"
			ORGANIZATION
				"Ericsson GmbH"
			CONTACT-INFO
				"Hansjoerg Hofmann
				Ericsson GmbH
				Gerberstr. 33
				71522 Backnang
				Germany
				+497191133377
				hansjoerg.hofmann@ericsson.com"
			DESCRIPTION
				"This MIB contains information on settings
				for the SAU that are not covered by Ericsson MIBs.
				Currently the following
				services are configured:
				Misc configuration items for ports
				"
			REVISION "200808140000Z"    -- 2008-08-14
			DESCRIPTION
				"PA4: added xfSauRowStatus"
			REVISION "200801280000Z"    -- 2008-01-28
			DESCRIPTION
				"PB3: extended values for xfSauIfMode (xfSauTerminalServer replaced by xfSauTerminalServerTunneling and xfSauTerminalServerMleAccess, comment for loops: added text"
			REVISION "200801230000Z"    -- 2008-01-25
			DESCRIPTION
				"PB2: renamed xfSauIfTable, xfSauIfEntry to xfSauTable, xfSauEntry. Added MO xfSauPortType carrying IANA-types for mirrowing to MO ifType"
			REVISION "200712091000Z"    -- 2007-12-09
			DESCRIPTION
				"PB1: renamed xfSauIfType to xfSauIfMode, removed xfSauPortType, changed Syntax of xfSauPortSpeed to Gauge32, renamed entry for xfSauIfMode from xfSauAuxOff to xfSauAuxNotConfigured"
			REVISION "200712090900Z"    -- 2007-12-09
			DESCRIPTION
				"A: set to revision"
			REVISION "200712090800Z"    -- 2007-12-09
			DESCRIPTION
				"PA4: xfSauIfTypes for TS reduced to one and xfSauOff changed to xfSauAuxOff, ifTypes changed to v11, rs232 ans g703at64k, descriptions extended"
			REVISION "200712070000Z"    -- 2007-12-07
			DESCRIPTION
				"PA3: fix oid numbers, new ifTypes added, ifDescr removed"
			REVISION "200710040000Z"
			DESCRIPTION
				"PA2"
			REVISION "200707040000Z"
			DESCRIPTION
				"PA1"
			::= { xfIpSau 1}

--
-- Textual conventions
--

--
-- Node definitions
--

		xfSauObjects OBJECT IDENTIFIER ::= { xfSauMIB 1 }

-- External objects

-- Miscellaneous Interface Objects

		xfSauTable OBJECT-TYPE
			SYNTAX SEQUENCE OF XfSauEntry
			MAX-ACCESS not-accessible
			STATUS current
			DESCRIPTION
			"A table containing options for the SAU AUX interfaces."
			::= { xfSauObjects 2 }

		xfSauEntry OBJECT-TYPE
			SYNTAX XfSauEntry
			MAX-ACCESS not-accessible
			STATUS current
			DESCRIPTION
			"SAU misc If configuration."
			INDEX{ xfSauIfIndex }
			::= { xfSauTable 1 }

		XfSauEntry ::=
			SEQUENCE {
			xfSauIfIndex				-- 1, The table index
			InterfaceIndex,
			xfSauIfMode					-- 2, Determines the mode of the interface {PPP, TSC, TS MLEaccess, TS tunneling, AuxOff}.
			INTEGER,
			xfSauPortType				-- 3, Determines the physical mode of a port using IANA-types: v11(64), rs232(33), g703at64k(66).
			INTEGER,
			xfSauPortSpeed				-- 4, Determines the speed of an interface.
			Gauge32,
			xfSauPortEdgeMode			-- 5, Determines if the positive or negative edge is used for the clocking.
			INTEGER,
			xfSauPortOctetSync			-- 6, Determines if octet synch. is to be generated in G.703 mode.
			TruthValue,
			xfSauPortSynchMode			-- 7, Indicates if the port is configured to synchrounous ar asynchronous timing (rs232{Sync,Async}PortTable).
			INTEGER,
			xfSauPortLineLoop			-- 8, Indicates if the line loop (the external signal coming in via the port/connector is looped back to the port/connector going out) of a port is enabled or disabled.
			TruthValue,
			xfSauPortLocalLoop			-- 9, Indicates if the local loop (the internal signal comming from the NAB/backplane is looped back to the NAB/backplane) of a port is enabled or disabled.
			TruthValue,
			xfSauPortAlarms				-- 10, This object is not used and not implemented!
			BITS,
			xfSauAlarmEnablePossible	-- 11, This object is not used and not implemented!
			BITS,
            xfSauRowStatus              -- 12, This object indicates the row status.
            RowStatus
			}

		xfSauIfIndex OBJECT-TYPE
			SYNTAX InterfaceIndex
			MAX-ACCESS not-accessible
			STATUS current
			DESCRIPTION
			"The value of ifIndex for the port."
			::= { xfSauEntry 1 }

		xfSauIfMode OBJECT-TYPE
			SYNTAX INTEGER{
			xfSauPpp(1),
			xfSauTransparentServiceChannel(2),
			xfSauTerminalServerTunneling(3),
			xfSauTerminalServerMleAccess(4),
			xfSauAuxNotConfigured(5)
			}
			MAX-ACCESS read-write
			STATUS current
			DESCRIPTION
			"Determines the mode of the interface {xfSauPpp, xfSauTransparentServiceChannel, xfSauTerminalServerTunneling, xfSauTerminalServerMleAccess, xfSauAuxOff}."
			DEFVAL{xfSauAuxNotConfigured}
			::= { xfSauEntry 2 }

		xfSauPortType OBJECT-TYPE
			SYNTAX INTEGER{
			v11(64),
			rs232(33),
			g703at64k(66)
			}
			MAX-ACCESS read-write
			STATUS current
			DESCRIPTION
			"Determines the physical mode of a port using IANA-types: v11(64), rs232(33), g703at64k(66)."
			DEFVAL{v11}
			::= { xfSauEntry 3 }

		xfSauPortSpeed OBJECT-TYPE
			SYNTAX Gauge32
			MAX-ACCESS read-write
			STATUS current
			DESCRIPTION
			"The speed of the port in bps {1200, 2400, 4800, 9600, 14400, 19200, 38400, 57600, 64000}."
			::= { xfSauEntry 4 }

		xfSauPortEdgeMode OBJECT-TYPE
			SYNTAX INTEGER{
			positive(1),
			negative(2)
			}
			MAX-ACCESS read-write
			STATUS current
			DESCRIPTION
			"Determines which edge is used for the clocking {positive, negative}."
			DEFVAL{positive}
			::= { xfSauEntry 5 }

		xfSauPortOctetSync OBJECT-TYPE
			SYNTAX TruthValue
			MAX-ACCESS read-write
			STATUS current
			DESCRIPTION
			"Determines if octet synch. is to be generated in G.703 mode {true, false}."
			DEFVAL { true }
			::= { xfSauEntry 6 }

		xfSauPortSynchMode OBJECT-TYPE
			SYNTAX INTEGER{
			synchronous(1),
			asynchronous(2)
			}
			MAX-ACCESS read-write
			STATUS current
			DESCRIPTION
			"Port configuration of the timing mode {synchronous, asynchronous}.
			Depending on the entry, a row in the rs232SyncPortTable or a row in the rs232AsyncPortTable exists for the port."
			DEFVAL{synchronous}
			::= { xfSauEntry 7 }

		xfSauPortLineLoop OBJECT-TYPE
			SYNTAX TruthValue
			MAX-ACCESS read-write
			STATUS current
			DESCRIPTION
			"Determines if line loop is enabled for the port {true, false}. Line loop: The external signal coming in via the port/connector is looped back to the port/connector going out"
			DEFVAL{ false }
			::= { xfSauEntry 8 }

		xfSauPortLocalLoop OBJECT-TYPE
			SYNTAX TruthValue
			MAX-ACCESS read-write
			STATUS current
			DESCRIPTION
			"Determines if local loop is enabled for the port {true, false}. Local loop: The internal signal comming from the NAB/backplane is looped back to the NAB/backplane"
			DEFVAL{ false }
			::= { xfSauEntry 9 }

		xfSauPortAlarms OBJECT-TYPE
			SYNTAX BITS{
			xfSauLos0(0),
			xfSauLos1(1),
			xfSauLos2(2)
			}
			MAX-ACCESS read-only
			STATUS current
			DESCRIPTION
			"Gives information on the alarm status of the port.
			Severity is indicated by three bits per alarm:
			bits 012
				 000	clear
				 001	undetermined
				 010	warning
				 011	minor
				 100	major
				 101	critical"
			::= { xfSauEntry 10 }

		xfSauAlarmEnablePossible OBJECT-TYPE
			SYNTAX BITS{
			xfSauLos(0)			}
			MAX-ACCESS read-write
			STATUS current
			DESCRIPTION
			"This object indicates which bits/alarms in the xfSauPortAlarms are enabled for a specific port.
				0 not enabled
				1 enabled"
			::= { xfSauEntry 11 }

        xfSauRowStatus OBJECT-TYPE
            SYNTAX RowStatus
            -- SYNTAX INTEGER{
            -- active(1),
            -- notInService(2),
            -- createAndGo(4)
            -- }
            MAX-ACCESS read-write
            STATUS current
            DESCRIPTION
            "This object represents the RowStatus, but only 'active'(1),
            'notInService'(2) and 'createAndGo'(4) are implemented.
            The MIB rows are always present, and cannot be created or
            destroyed.
            NOTE that 'createAndGo'(4) is used in a different way as described
                 in the SNMPv2-TC !
                 Here, setting 'createAndGo'(4) while in 'notInService'(2)
                 discards all changes made to the objects of this XfSauIfEntry
                 and resets them to the previous values and the xfSauRowStatus
                 was is set to 'active'(1). 
            Setting any of the other (writable) objects is only possible
            if the xfSauRowStatus is set to 'notInService'(2), and any
            changes will have no effect until the xfSauRowStatus is set
            to 'active'(1).
            Is Set to 'active'(1) at initialization, so the default
            values of the row's objects can be used."
            DEFVAL{ active }
            ::= { xfSauEntry 12 }
        
-- conformance information

		xfSauConformance OBJECT IDENTIFIER ::= { xfSauMIB 6 }

		xfSauGroups OBJECT IDENTIFIER ::= { xfSauConformance 1 }
		xfSauCompliances OBJECT IDENTIFIER ::= { xfSauConformance 2 }

-- compliance statements

		xfSauCompliance MODULE-COMPLIANCE
			STATUS current
			DESCRIPTION
				"The compliance statement for SNMP entities which
				have Sau like interfaces."
			MODULE -- this module
				MANDATORY-GROUPS { xfSauGroups }

			GROUP	xfSauGroup
			DESCRIPTION
				"The If group is mandatory only for those SNMP
				entities which have serial interfaces."

			::= { xfSauCompliances 1 }

-- units of conformance

		xfSauGroup OBJECT-GROUP
			OBJECTS { xfSauIfMode, xfSauPortType, xfSauPortSpeed,
					xfSauPortEdgeMode, xfSauPortOctetSync,
					xfSauPortSynchMode, xfSauPortLineLoop, xfSauPortLocalLoop,
					xfSauRowStatus
						}
			STATUS current
			DESCRIPTION
				"numbering objects in the MIB"
			::= { xfSauGroups 2 }

	END

--
--
