--
-- This SMIv1 module has been generated by smidump 0.2-cvs. Do not edit.
--

FOUNDRY-SN-TRAP-MIB DEFINITIONS ::= BEGIN

IMPORTS
    snAgGblTrapMessage, snAgentBrdIndex, snChasFanDescription, 
    snChasFanIndex, snChasPwrSupplyDescription, snChasPwrSupplyIndex, 
    snChasPwrSupplyStatus
        FROM FOUNDRY-SN-AGENT-MIB
    snOspfConfigErrorType, snOspfExtLsdbLimit, snOspfIfStatusIpAddress, 
    snOspfIfStatusState, snOspfLsdbAreaId, snOspfLsdbLsId, 
    snOspfLsdbRouterId, snOspfLsdbType, snOspfNbrIpAddr, snOspfNbrRtrId, 
    snOspfNbrState, snOspfPacketSrc, snOspfPacketType, snOspfRouterId, 
    snOspfVirtIfStatusAreaID, snOspfVirtIfStatusNeighbor, 
    snOspfVirtIfStatusState, snOspfVirtNbrArea, snOspfVirtNbrRtrId, 
    snOspfVirtNbrState
        FROM FOUNDRY-SN-OSPF-GROUP-MIB
    foundry
        FROM FOUNDRY-SN-ROOT-MIB
    snL4MaxSessionLimit, snL4TcpSynLimit, 
    snL4TrapRealServerCurConnections, snL4TrapRealServerIP, 
    snL4TrapRealServerName, snL4TrapRealServerPort
        FROM FOUNDRY-SN-SW-L4-SWITCH-GROUP-MIB
    snSwViolatorMacAddress, snSwViolatorPortNumber
        FROM FOUNDRY-SN-SWITCH-GROUP-MIB
    TRAP-TYPE
        FROM RFC-1215;

snTrapChasPwrSupply TRAP-TYPE
    ENTERPRISE      foundry
    VARIABLES       { snChasPwrSupplyStatus }
--     STATUS          mandatory
    DESCRIPTION     
            "The SNMP trap that is generated when a power supply fails
             to operate normally."
    ::= 1

snTrapLockedAddressViolation TRAP-TYPE
    ENTERPRISE      foundry
    VARIABLES       { snSwViolatorPortNumber, snSwViolatorMacAddress }
--     STATUS          mandatory
    DESCRIPTION     
            "The SNMP trap that is generated when more source MAC addresses
             are received from a port than the maximum number of addresses
             configured to that port."
    ::= 2

snTrapOspfIfStateChange TRAP-TYPE
    ENTERPRISE      foundry
    VARIABLES       { snOspfRouterId, snOspfIfStatusIpAddress, 
                      snOspfIfStatusState }
--     STATUS          mandatory
    DESCRIPTION     
            "An ospfIfStateChange trap signifies that there
             has been a change in the state of a non-virtual
             OSPF interface. This trap should  be  generated
             when  the interface state regresses (e.g., goes
             from Dr to Down) or progresses  to  a  terminal
             state  (i.e.,  Point-to-Point, DR Other, Dr, or
             Backup)."
    ::= 3

snTrapOspfVirtIfStateChange TRAP-TYPE
    ENTERPRISE      foundry
    VARIABLES       { snOspfRouterId, snOspfVirtIfStatusAreaID, 
                      snOspfVirtIfStatusNeighbor, 
                      snOspfVirtIfStatusState }
--     STATUS          mandatory
    DESCRIPTION     
            "An ospfIfStateChange trap signifies that there
             has  been a change in the state of an OSPF vir-
             tual interface.
             This trap should be generated when  the  inter-
             face  state  regresses  (e.g., goes from Point-
             to-Point to Down) or progresses to  a  terminal
             state (i.e., Point-to-Point)."
    ::= 4

snOspfNbrStateChange TRAP-TYPE
    ENTERPRISE      foundry
    VARIABLES       { snOspfRouterId, snOspfNbrIpAddr, snOspfNbrRtrId, 
                      snOspfNbrState }
--     STATUS          mandatory
    DESCRIPTION     
            "An  ospfNbrStateChange  trap  signifies   that
             there  has been a change in the state of a non-
             virtual OSPF neighbor.   This  trap  should  be
             generated  when  the  neighbor  state regresses
             (e.g., goes from Attempt or Full  to  1-Way  or
             Down)  or progresses to a terminal state (e.g.,
             2-Way or Full).  When an  neighbor  transitions
             from  or  to Full on non-broadcast multi-access
             and broadcast networks, the trap should be gen-
             erated  by the designated router.  A designated
             router transitioning to Down will be  noted  by
             ospfIfStateChange."
    ::= 5

snOspfVirtNbrStateChange TRAP-TYPE
    ENTERPRISE      foundry
    VARIABLES       { snOspfRouterId, snOspfVirtNbrArea, 
                      snOspfVirtNbrRtrId, snOspfVirtNbrState }
--     STATUS          mandatory
    DESCRIPTION     
            "An ospfIfStateChange trap signifies that there
             has  been a change in the state of an OSPF vir-
             tual neighbor.  This trap should  be  generated
             when  the  neighbor state regresses (e.g., goes
             from Attempt or  Full  to  1-Way  or  Down)  or
             progresses to a terminal state (e.g., Full)."
    ::= 6

snOspfIfConfigError TRAP-TYPE
    ENTERPRISE      foundry
    VARIABLES       { snOspfRouterId, snOspfIfStatusIpAddress, 
                      snOspfPacketSrc, snOspfConfigErrorType, 
                      snOspfPacketType }
--     STATUS          mandatory
    DESCRIPTION     
            "An ospfIfConfigError  trap  signifies  that  a
             packet  has  been received on a non-virtual in-
             terface  from  a  router  whose   configuration
             parameters  conflict  with this router's confi-
             guration parameters.  Note that the  event  op-
             tionMismatch  should  cause  a  trap only if it
             prevents an adjacency from forming."
    ::= 7

snOspfVirtIfConfigError TRAP-TYPE
    ENTERPRISE      foundry
    VARIABLES       { snOspfRouterId, snOspfVirtIfStatusAreaID, 
                      snOspfVirtIfStatusNeighbor, snOspfConfigErrorType, 
                      snOspfPacketType }
--     STATUS          mandatory
    DESCRIPTION     
            "An ospfConfigError trap signifies that a pack-
             et  has  been  received  on a virtual interface
             from a router  whose  configuration  parameters
             conflict   with   this  router's  configuration
             parameters.  Note that the event optionMismatch
             should  cause a trap only if it prevents an ad-
             jacency from forming."
    ::= 8

snOspfIfAuthFailure TRAP-TYPE
    ENTERPRISE      foundry
    VARIABLES       { snOspfRouterId, snOspfIfStatusIpAddress, 
                      snOspfPacketSrc, snOspfConfigErrorType, 
                      snOspfPacketType }
--     STATUS          mandatory
    DESCRIPTION     
            "An ospfIfAuthFailure  trap  signifies  that  a
             packet  has  been received on a non-virtual in-
             terface from a router whose authentication  key
             or  authentication  type  conflicts  with  this
             router's authentication key  or  authentication
             type."
    ::= 9

snOspfVirtIfAuthFailure TRAP-TYPE
    ENTERPRISE      foundry
    VARIABLES       { snOspfRouterId, snOspfVirtIfStatusAreaID, 
                      snOspfVirtIfStatusNeighbor, snOspfConfigErrorType, 
                      snOspfPacketType }
--     STATUS          mandatory
    DESCRIPTION     
            "An ospfVirtIfAuthFailure trap signifies that a
             packet has been received on a virtual interface
             from a router whose authentication key  or  au-
             thentication  type conflicts with this router's
             authentication key or authentication type."
    ::= 10

snOspfIfRxBadPacket TRAP-TYPE
    ENTERPRISE      foundry
    VARIABLES       { snOspfRouterId, snOspfIfStatusIpAddress, 
                      snOspfPacketSrc, snOspfPacketType }
--     STATUS          mandatory
    DESCRIPTION     
            "An ospfIfRxBadPacket trap  signifies  that  an
             OSPF  packet has been received on a non-virtual
             interface that cannot be parsed."
    ::= 11

snOspfVirtIfRxBadPacket TRAP-TYPE
    ENTERPRISE      foundry
    VARIABLES       { snOspfRouterId, snOspfVirtIfStatusAreaID, 
                      snOspfVirtIfStatusNeighbor, snOspfPacketType }
--     STATUS          mandatory
    DESCRIPTION     
            "An ospfRxBadPacket trap signifies that an OSPF
             packet has been received on a virtual interface
             that cannot be parsed."
    ::= 12

snOspfTxRetransmit TRAP-TYPE
    ENTERPRISE      foundry
    VARIABLES       { snOspfRouterId, snOspfIfStatusIpAddress, 
                      snOspfNbrRtrId, snOspfPacketType, snOspfLsdbType, 
                      snOspfLsdbLsId, snOspfLsdbRouterId }
--     STATUS          mandatory
    DESCRIPTION     
            "An ospfTxRetransmit  trap  signifies  than  an
             OSPF  packet  has  been retransmitted on a non-
             virtual interface.  All packets that may be re-
             transmitted  are associated with an LSDB entry.
             The LS type, LS ID, and Router ID are  used  to
             identify the LSDB entry."
    ::= 13

ospfVirtIfTxRetransmit TRAP-TYPE
    ENTERPRISE      foundry
    VARIABLES       { snOspfRouterId, snOspfVirtIfStatusAreaID, 
                      snOspfVirtIfStatusNeighbor, snOspfPacketType, 
                      snOspfLsdbType, snOspfLsdbLsId, snOspfLsdbRouterId }
--     STATUS          mandatory
    DESCRIPTION     
            "An ospfTxRetransmit  trap  signifies  than  an
             OSPF packet has been retransmitted on a virtual
             interface.  All packets that may be retransmit-
             ted  are  associated with an LSDB entry. The LS
             type, LS ID, and Router ID are used to identify
             the LSDB entry."
    ::= 14

snOspfOriginateLsa TRAP-TYPE
    ENTERPRISE      foundry
    VARIABLES       { snOspfRouterId, snOspfLsdbAreaId, snOspfLsdbType, 
                      snOspfLsdbLsId, snOspfLsdbRouterId }
--     STATUS          mandatory
    DESCRIPTION     
            "An ospfOriginateLsa trap signifies that a  new
             LSA  has  been originated by this router.  This
             trap should not be invoked for simple refreshes
             of  LSAs  (which happesn every 30 minutes), but
             instead will only be invoked  when  an  LSA  is
             (re)originated due to a topology change.  Addi-
             tionally, this trap does not include LSAs  that
             are  being  flushed  because  they have reached
             MaxAge."
    ::= 15

snOspfMaxAgeLsa TRAP-TYPE
    ENTERPRISE      foundry
    VARIABLES       { snOspfRouterId, snOspfLsdbAreaId, snOspfLsdbType, 
                      snOspfLsdbLsId, snOspfLsdbRouterId }
--     STATUS          mandatory
    DESCRIPTION     
            "An ospfMaxAgeLsa trap signifies  that  one  of
             the LSA in the router's link-state database has
             aged to MaxAge."
    ::= 16

snOspfLsdbOverflow TRAP-TYPE
    ENTERPRISE      foundry
    VARIABLES       { snOspfRouterId, snOspfExtLsdbLimit }
--     STATUS          mandatory
    DESCRIPTION     
            "An ospfLsdbOverflow trap  signifies  that  the
             number of LSAs in the router's link-state data-
             base has exceeded ospfExtLsdbLimit."
    ::= 17

snOspfLsdbApproachingOverflow TRAP-TYPE
    ENTERPRISE      foundry
    VARIABLES       { snOspfRouterId, snOspfExtLsdbLimit }
--     STATUS          mandatory
    DESCRIPTION     
            "An ospfLsdbApproachingOverflow trap  signifies
             that  the  number of LSAs in the router's link-
             state database has exceeded ninety  percent  of
             ospfExtLsdbLimit."
    ::= 18

snTrapL4MaxSessionLimitReached TRAP-TYPE
    ENTERPRISE      foundry
    VARIABLES       { snL4MaxSessionLimit }
--     STATUS          mandatory
    DESCRIPTION     
            "The SNMP trap that is generated when the maximum number
             of connections reached."
    ::= 19

snTrapL4TcpSynLimitReached TRAP-TYPE
    ENTERPRISE      foundry
    VARIABLES       { snL4TcpSynLimit }
--     STATUS          mandatory
    DESCRIPTION     
            "The SNMP trap that is generated when the number of TCP
             SYN limits reached."
    ::= 20

snTrapL4RealServerUp TRAP-TYPE
    ENTERPRISE      foundry
    VARIABLES       { snL4TrapRealServerIP, snL4TrapRealServerName }
--     STATUS          mandatory
    DESCRIPTION     
            "The SNMP trap that is generated when the load balancing
             real server is up."
    ::= 21

snTrapL4RealServerDown TRAP-TYPE
    ENTERPRISE      foundry
    VARIABLES       { snL4TrapRealServerIP, snL4TrapRealServerName }
--     STATUS          mandatory
    DESCRIPTION     
            "The SNMP trap that is generated when the load balancing
             real server is down."
    ::= 22

snTrapL4RealServerPortUp TRAP-TYPE
    ENTERPRISE      foundry
    VARIABLES       { snL4TrapRealServerIP, snL4TrapRealServerName, 
                      snL4TrapRealServerPort }
--     STATUS          mandatory
    DESCRIPTION     
            "The SNMP trap that is generated when the load balancing
             real server TCP port is up."
    ::= 23

snTrapL4RealServerPortDown TRAP-TYPE
    ENTERPRISE      foundry
    VARIABLES       { snL4TrapRealServerIP, snL4TrapRealServerName, 
                      snL4TrapRealServerPort }
--     STATUS          mandatory
    DESCRIPTION     
            "The SNMP trap that is generated when the load balancing
             real server TCP port is down."
    ::= 24

snTrapL4RealServerMaxConnectionLimitReached TRAP-TYPE
    ENTERPRISE      foundry
    VARIABLES       { snL4TrapRealServerIP, snL4TrapRealServerName, 
                      snL4TrapRealServerCurConnections }
--     STATUS          mandatory
    DESCRIPTION     
            "The SNMP trap that is generated when the real server reaches
             maximum number of connections."
    ::= 25

snTrapL4BecomeStandby TRAP-TYPE
    ENTERPRISE      foundry
--     STATUS          mandatory
    DESCRIPTION     
            "The SNMP trap that is generated when the server load
             balancing switch changes state from active to standby."
    ::= 26

snTrapL4BecomeActive TRAP-TYPE
    ENTERPRISE      foundry
--     STATUS          mandatory
    DESCRIPTION     
            "The SNMP trap that is generated when the server load
             balancing switch changes state from standby to active."
    ::= 27

snTrapModuleInserted TRAP-TYPE
    ENTERPRISE      foundry
    VARIABLES       { snAgentBrdIndex }
--     STATUS          mandatory
    DESCRIPTION     
            "The SNMP trap that is generated when a module was inserted
             to the chassis during system running."
    ::= 28

snTrapModuleRemoved TRAP-TYPE
    ENTERPRISE      foundry
    VARIABLES       { snAgentBrdIndex }
--     STATUS          mandatory
    DESCRIPTION     
            "The SNMP trap that is generated when a module was removed
             from the chassis during system running."
    ::= 29

snTrapChasPwrSupplyFailed TRAP-TYPE
    ENTERPRISE      foundry
    VARIABLES       { snChasPwrSupplyIndex, snChasPwrSupplyDescription }
--     STATUS          mandatory
    DESCRIPTION     
            "The SNMP trap that is generated when a power supply fails
             to operate normally."
    ::= 30

snTrapChasFanFailed TRAP-TYPE
    ENTERPRISE      foundry
    VARIABLES       { snChasFanIndex, snChasFanDescription }
--     STATUS          mandatory
    DESCRIPTION     
            "The SNMP trap that is generated when a fan fails
             to operate normally."
    ::= 31

snTrapLockedAddressViolation2 TRAP-TYPE
    ENTERPRISE      foundry
    VARIABLES       { snAgGblTrapMessage }
--     STATUS          mandatory
    DESCRIPTION     
            "The SNMP trap that is generated when more source MAC addresses
             are received from a port than the maximum number of addresses
             configured to that port."
    ::= 32

snTrapFsrpIfStateChange TRAP-TYPE
    ENTERPRISE      foundry
    VARIABLES       { snAgGblTrapMessage }
--     STATUS          mandatory
    DESCRIPTION     
            "The SNMP trap that is generated when a FSRP routing device
             changed state from active to standby or vice-versa."
    ::= 33

snTrapVrrpIfStateChange TRAP-TYPE
    ENTERPRISE      foundry
    VARIABLES       { snAgGblTrapMessage }
--     STATUS          mandatory
    DESCRIPTION     
            "The SNMP trap that is generated when a VRRP routing device
             changed state from master to backup or vice-versa."
    ::= 34

snTrapMgmtModuleRedunStateChange TRAP-TYPE
    ENTERPRISE      foundry
    VARIABLES       { snAgGblTrapMessage }
--     STATUS          mandatory
    DESCRIPTION     
            "The SNMP trap that is generated when the management module
             changes redundancy state."
    ::= 35

snTrapTemperatureWarning TRAP-TYPE
    ENTERPRISE      foundry
    VARIABLES       { snAgGblTrapMessage }
--     STATUS          mandatory
    DESCRIPTION     
            "The SNMP trap that is generated when the actual temperature
             reading is above the warning temperature threshold."
    ::= 36

snTrapAccessListDeny TRAP-TYPE
    ENTERPRISE      foundry
    VARIABLES       { snAgGblTrapMessage }
--     STATUS          mandatory
    DESCRIPTION     
            "The SNMP trap that is generated when a packet was denied
             by an access list."
    ::= 37

snTrapMacFilterDeny TRAP-TYPE
    ENTERPRISE      foundry
    VARIABLES       { snAgGblTrapMessage }
--     STATUS          mandatory
    DESCRIPTION     
            "The SNMP trap that is generated when a packet was denied
             by a MAC address filter."
    ::= 38

snTrapL4GslbRemoteUp TRAP-TYPE
    ENTERPRISE      foundry
    VARIABLES       { snAgGblTrapMessage }
--     STATUS          mandatory
    DESCRIPTION     
            "The SNMP trap that is generated when the connection to the remote SI is established."
    ::= 39

snTrapL4GslbRemoteDown TRAP-TYPE
    ENTERPRISE      foundry
    VARIABLES       { snAgGblTrapMessage }
--     STATUS          mandatory
    DESCRIPTION     
            "The SNMP trap that is generated when the connection to the remote SI is down."
    ::= 40

snTrapL4GslbRemoteControllerUp TRAP-TYPE
    ENTERPRISE      foundry
    VARIABLES       { snAgGblTrapMessage }
--     STATUS          mandatory
    DESCRIPTION     
            "The SNMP trap that is generated when the connection to the GSLB SI is established."
    ::= 41

snTrapL4GslbRemoteControllerDown TRAP-TYPE
    ENTERPRISE      foundry
    VARIABLES       { snAgGblTrapMessage }
--     STATUS          mandatory
    DESCRIPTION     
            "The SNMP trap that is generated when the connection to the GSLB SI is down."
    ::= 42

snTrapL4GslbHealthCheckIpUp TRAP-TYPE
    ENTERPRISE      foundry
    VARIABLES       { snAgGblTrapMessage }
--     STATUS          mandatory
    DESCRIPTION     
            "The SNMP trap that is generated when GSLB health check for an address transitions
             from down to active state."
    ::= 43

snTrapL4GslbHealthCheckIpDown TRAP-TYPE
    ENTERPRISE      foundry
    VARIABLES       { snAgGblTrapMessage }
--     STATUS          mandatory
    DESCRIPTION     
            "The SNMP trap that is generated when GSLB health check for an address transitions
             from active to down state."
    ::= 44

snTrapL4GslbHealthCheckIpPortUp TRAP-TYPE
    ENTERPRISE      foundry
    VARIABLES       { snAgGblTrapMessage }
--     STATUS          mandatory
    DESCRIPTION     
            "The SNMP trap that is generated when a given port for a health check address is up."
    ::= 45

snTrapL4GslbHealthCheckIpPortDown TRAP-TYPE
    ENTERPRISE      foundry
    VARIABLES       { snAgGblTrapMessage }
--     STATUS          mandatory
    DESCRIPTION     
            "The SNMP trap that is generated when a given port for a health check address is down."
    ::= 46

snTrapL4FirewallBecomeStandby TRAP-TYPE
    ENTERPRISE      foundry
--     STATUS          mandatory
    DESCRIPTION     
            "The SNMP trap that is generated when the server load
             balancing switch Firewall changes state from active to standby."
    ::= 47

snTrapL4FirewallBecomeActive TRAP-TYPE
    ENTERPRISE      foundry
--     STATUS          mandatory
    DESCRIPTION     
            "The SNMP trap that is generated when the server load
             balancing switch Firewall changes state from standby to active."
    ::= 48

snTrapL4FirewallPathUp TRAP-TYPE
    ENTERPRISE      foundry
--     STATUS          mandatory
    DESCRIPTION     
            "The SNMP trap that is generated when the server load
             balancing switch Firewall path is up."
    ::= 49

snTrapL4FirewallPathDown TRAP-TYPE
    ENTERPRISE      foundry
--     STATUS          mandatory
    DESCRIPTION     
            "The SNMP trap that is generated when the server load
             balancing switch Firewall path is down."
    ::= 50

snTrapIcmpLocalExceedBurst TRAP-TYPE
    ENTERPRISE      foundry
    VARIABLES       { snAgGblTrapMessage }
--     STATUS          mandatory
    DESCRIPTION     
            "The SNMP trap that is generated when incoming ICMP exceeds burst-MAX."
    ::= 51

snTrapIcmpTransitExceedBurst TRAP-TYPE
    ENTERPRISE      foundry
    VARIABLES       { snAgGblTrapMessage }
--     STATUS          mandatory
    DESCRIPTION     
            "The SNMP trap that is generated when transit ICMP exceeds burst-MAX."
    ::= 52

snTrapTcpLocalExceedBurst TRAP-TYPE
    ENTERPRISE      foundry
    VARIABLES       { snAgGblTrapMessage }
--     STATUS          mandatory
    DESCRIPTION     
            "The SNMP trap that is generated when incoming TCP SYN exceeds burst-MAX."
    ::= 53

snTrapTcpTransitExceedBurst TRAP-TYPE
    ENTERPRISE      foundry
    VARIABLES       { snAgGblTrapMessage }
--     STATUS          mandatory
    DESCRIPTION     
            "The SNMP trap that is generated when transit TCP exceeds burst-MAX."
    ::= 54

snTrapL4ContentVerification TRAP-TYPE
    ENTERPRISE      foundry
--     STATUS          mandatory
    DESCRIPTION     
            "The SNMP trap that is generated when the HTTP match-list pattern
             is found."
    ::= 55

snTrapDuplicateIp TRAP-TYPE
    ENTERPRISE      foundry
--     STATUS          mandatory
    DESCRIPTION     
            "Duplicate IP address detected."
    ::= 56

END -- end of module FOUNDRY-SN-TRAP-MIB.
