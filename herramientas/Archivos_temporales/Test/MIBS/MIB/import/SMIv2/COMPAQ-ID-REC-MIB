--
-- This SMIv2 module has been generated by smidump 0.2-cvs. Do not edit.
--

COMPAQ-ID-REC-MIB DEFINITIONS ::= BEGIN

IMPORTS
    enterprises
        FROM SNMPv2-SMI;

compaq OBJECT IDENTIFIER
    ::= { enterprises 232 }

compaq-proLiantBLeClassCG-proLiantBLpClassGbE OBJECT IDENTIFIER
    ::= { enterprises 232 161 }

compaq-products OBJECT IDENTIFIER
    ::= { compaq-proLiantBLeClassCG-proLiantBLpClassGbE 1 }

compaq-ProLiantBLeClassCGSeriesProd OBJECT IDENTIFIER
    ::= { compaq-products 36 }

compaq-ProLiantBLeClassCGProd OBJECT IDENTIFIER
    ::= { compaq-ProLiantBLeClassCGSeriesProd 1 }

proLiantBLeClassCGDevRegistration OBJECT IDENTIFIER
    ::= { compaq-ProLiantBLeClassCGProd 2 }

proLiantBLeClassCGDevice OBJECT IDENTIFIER
    ::= { proLiantBLeClassCGDevRegistration 1 }

proLiantBLeClassCGUnitRegistration OBJECT IDENTIFIER
    ::= { compaq-ProLiantBLeClassCGProd 3 }

proLiantBLeClassCGUnit OBJECT IDENTIFIER
    ::= { proLiantBLeClassCGUnitRegistration 1 }

proLiantBLeClassCGModuleRegistration OBJECT IDENTIFIER
    ::= { compaq-ProLiantBLeClassCGProd 4 }

proLiantBLeClassCG-Module-Mainboard-26Port OBJECT IDENTIFIER
    ::= { proLiantBLeClassCGModuleRegistration 1 }

proLiantBLeClassCGPortRegistration OBJECT IDENTIFIER
    ::= { compaq-ProLiantBLeClassCGProd 5 }

proLiantBLeClassCG-Port-10-100-TX OBJECT IDENTIFIER
    ::= { proLiantBLeClassCGPortRegistration 1 }

proLiantBLeClassCG-Port-1000-TX OBJECT IDENTIFIER
    ::= { proLiantBLeClassCGPortRegistration 2 }

compaq-ProLiantBLpClassGbESeriesProd OBJECT IDENTIFIER
    ::= { compaq-products 37 }

compaq-ProLiantBLpClassGbEProd OBJECT IDENTIFIER
    ::= { compaq-ProLiantBLpClassGbESeriesProd 1 }

proLiantBLpClassGbEDevRegistration OBJECT IDENTIFIER
    ::= { compaq-ProLiantBLpClassGbEProd 2 }

proLiantBLpClassGbEDevice OBJECT IDENTIFIER
    ::= { proLiantBLpClassGbEDevRegistration 1 }

proLiantBLpClassGbEUnitRegistration OBJECT IDENTIFIER
    ::= { compaq-ProLiantBLpClassGbEProd 3 }

proLiantBLpClassGbEUnit OBJECT IDENTIFIER
    ::= { proLiantBLpClassGbEUnitRegistration 1 }

proLiantBLpClassGbEModuleRegistration OBJECT IDENTIFIER
    ::= { compaq-ProLiantBLpClassGbEProd 4 }

proLiantBLpClassGbE-Module-Mainboard-24Port OBJECT IDENTIFIER
    ::= { proLiantBLpClassGbEModuleRegistration 1 }

proLiantBLpClassGbEPortRegistration OBJECT IDENTIFIER
    ::= { compaq-ProLiantBLpClassGbEProd 5 }

proLiantBLpClassGbE-Port-10-100-TX OBJECT IDENTIFIER
    ::= { proLiantBLpClassGbEPortRegistration 1 }

proLiantBLpClassGbE-Port-1000-TX OBJECT IDENTIFIER
    ::= { proLiantBLpClassGbEPortRegistration 2 }

proLiantBLpClassGbE-Port-1000-SX OBJECT IDENTIFIER
    ::= { proLiantBLpClassGbEPortRegistration 3 }

compaq-mgmt OBJECT IDENTIFIER
    ::= { compaq-proLiantBLeClassCG-proLiantBLpClassGbE 2 }

compaq-common-mgmt OBJECT IDENTIFIER
    ::= { compaq-proLiantBLeClassCG-proLiantBLpClassGbE 3 }

END -- end of module COMPAQ-ID-REC-MIB.
