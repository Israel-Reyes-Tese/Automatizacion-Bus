--
-- This SMIv2 module has been generated by smidump 0.2-cvs. Do not edit.
--

SONUS-SBX-POLICY-SERVER-TRAP-MIB DEFINITIONS ::= BEGIN

IMPORTS
    Counter32, IpAddress, MODULE-IDENTITY, NOTIFICATION-TYPE, 
    OBJECT-TYPE, Unsigned32
        FROM SNMPv2-SMI
    DisplayString
        FROM SNMPv2-TC
    SonusName
        FROM SONUS-COMMON-TC
    sonusAlarmDescription, sonusAlarmLevel, sonusAlarmNodeID, 
    sonusAlarmSequenceId, sonusAlarmTime
        FROM SONUS-COMMON-TRAP-MIB
    sonusSBX5000NotificationMIBs
        FROM SONUS-SMI;

sonusSbxPolicyServerTrapsMIB MODULE-IDENTITY
    LAST-UPDATED    "201003120000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for SoftSwitch Policy Execution Server Management."
    ::= { sonusSBX5000NotificationMIBs 2 }


sonusPolicyServerTraps OBJECT IDENTIFIER
    ::= { sonusSbxPolicyServerTrapsMIB 1 }

sonusPolicyServerNotifications OBJECT IDENTIFIER
    ::= { sonusPolicyServerTraps 1 }

sonusPolicyServerNotificationPrefix OBJECT IDENTIFIER
    ::= { sonusPolicyServerNotifications 0 }

sonusPolicyServerNotificationObjects OBJECT IDENTIFIER
    ::= { sonusPolicyServerNotifications 1 }

sonusPolicyServerRegisterReason OBJECT-TYPE
    SYNTAX          INTEGER { new(1) }
    MAX-ACCESS      read-only
    STATUS          current
    DESCRIPTION     
            "Register operation reason."
    ::= { sonusPolicyServerNotificationObjects 1 }

sonusPolicyServerUnregisterReason OBJECT-TYPE
    SYNTAX          INTEGER { threshold(1), unknown(2), duplicate(3), 
                        lostConnection(4), clientUnregistered(5), 
                        unknownGateway(6), maxClientsExceeded(7) }
    MAX-ACCESS      read-only
    STATUS          current
    DESCRIPTION     
            "Unregister operation reason."
    ::= { sonusPolicyServerNotificationObjects 2 }

sonusPolicyServerCongestionLevel OBJECT-TYPE
    SYNTAX          Unsigned32
    MAX-ACCESS      read-only
    STATUS          current
    DESCRIPTION     
            "Congestion level to which the PSX is transitioning."
    ::= { sonusPolicyServerNotificationObjects 3 }

sonusPolicyServerPipeErrorCode OBJECT-TYPE
    SYNTAX          Unsigned32
    MAX-ACCESS      read-only
    STATUS          current
    DESCRIPTION     
            "The unix error code, if any, will be available in this field."
    ::= { sonusPolicyServerNotificationObjects 4 }

sonusPolicyServerPipeMwiQueueLevel OBJECT-TYPE
    SYNTAX          INTEGER { mwiQueueSafe(0), mwiQueueLevelMinor(1), 
                        mwiQueueLevelMajor(2), mwiQueueLevelCritical(3) }
    MAX-ACCESS      read-only
    STATUS          current
    DESCRIPTION     
            "This field contains the MWI queue level information."
    ::= { sonusPolicyServerNotificationObjects 5 }

sonusPolicyServerDbOperationFailureReason OBJECT-TYPE
    SYNTAX          INTEGER { connection(1), update(2) }
    MAX-ACCESS      read-only
    STATUS          current
    DESCRIPTION     
            "DB operation failure reason."
    ::= { sonusPolicyServerNotificationObjects 6 }

sonusPolicyServerTMIdentifier1 OBJECT-TYPE
    SYNTAX          DisplayString
    MAX-ACCESS      read-only
    STATUS          current
    DESCRIPTION     
            "Identifies the control. For Destination and Origination element type 
             this is the national number. For Trunkgroup type, it is the trunkgroup 
             identifier"
    ::= { sonusPolicyServerNotificationObjects 7 }

sonusPolicyServerTMIdentifier2 OBJECT-TYPE
    SYNTAX          DisplayString
    MAX-ACCESS      read-only
    STATUS          current
    DESCRIPTION     
            "Identifies the control.  For Destination and Origination element type 
             this is the country code. For Trunkgroup type it is the gateway identifier."
    ::= { sonusPolicyServerNotificationObjects 8 }

sonusPolicyServerTMElementType OBJECT-TYPE
    SYNTAX          INTEGER { destination(1), trunkgroup(2), 
                        origination(3), routingLabel(4) }
    MAX-ACCESS      read-only
    STATUS          current
    DESCRIPTION     
            "Type of element on which this traffic management control operates."
    ::= { sonusPolicyServerNotificationObjects 9 }

sonusPolicyServerTMProvControlType OBJECT-TYPE
    SYNTAX          INTEGER { unknown(0), canf(1), cantdr(2), skipdr(3), 
                        skipar(4), dialeddestination(5), 
                        translateddestination(6), cantar(7), strdr(8), 
                        strar(9), irrdr(10), sirrdr(11), orrdr(12), 
                        sorrdr(13), rralternate(14), irrar(15), 
                        sirrar(16), orrar(17), sorrar(18), 
                        origination(19), finalCallingNumber(20), 
                        finalDestination(21), 
                        contractorBasedOrigination(22), 
                        cdDNBasedDestination(23) }
    MAX-ACCESS      read-only
    STATUS          current
    DESCRIPTION     
            "Type of control provisioned."
    ::= { sonusPolicyServerNotificationObjects 10 }

sonusPolicyServerTMAppliedControlType OBJECT-TYPE
    SYNTAX          INTEGER { dialeddestination(1), 
                        translateddestination(2), origination(3), 
                        finalCallingNumber(4), finalDestination(5), 
                        contractorBasedOrigination(6), 
                        cdDNBasedDestination(7) }
    MAX-ACCESS      read-only
    STATUS          current
    DESCRIPTION     
            "Type of control applied."
    ::= { sonusPolicyServerNotificationObjects 11 }

sonusPolicyServerTMAddressNature OBJECT-TYPE
    SYNTAX          INTEGER { unknown(0), national(1), international(2), 
                        nochange(3), subscriber(4), networkspecific(5), 
                        natureunknown(6), subscriberoperator(7), 
                        nationaloperator(8), internationaloperator(9), 
                        testcode(10), nonumberoprequested(11), 
                        nonumbercutthrough(12), nature950(13), 
                        anicallingpartysubscriber(14), 
                        aninotavailable(15), anicallingpartynational(16), 
                        anicalledpartysubscriber(17), 
                        anicalledpartynonumber(18), 
                        anicalledpartynational(19), ss7reserved(20), 
                        nationalnotrestricted(21), 
                        nationalrestricted(22), 
                        internationalnotrestricted(23), 
                        internationalrestricted(24), 
                        partialcallinglineid(126), all(255) }
    MAX-ACCESS      read-only
    STATUS          current
    DESCRIPTION     
            "Specifies whether the call was national,international or any other type 
             like network specific."
    ::= { sonusPolicyServerNotificationObjects 12 }

sonusPolicyServerClientName OBJECT-TYPE
    SYNTAX          SonusName
    MAX-ACCESS      read-only
    STATUS          current
    DESCRIPTION     
            "Name of the PolicyServer client, usually a gateway."
    ::= { sonusPolicyServerNotificationObjects 13 }

sonusPolicyServerLWRESDBlacklisted OBJECT-TYPE
    SYNTAX          DisplayString
    MAX-ACCESS      read-only
    STATUS          current
    DESCRIPTION     
            "Specifies the DNS Server ip."
    ::= { sonusPolicyServerNotificationObjects 14 }

sonusPolicyServerLWRESDWhitelisted OBJECT-TYPE
    SYNTAX          DisplayString
    MAX-ACCESS      read-only
    STATUS          current
    DESCRIPTION     
            "Specifies the DNS Server ip."
    ::= { sonusPolicyServerNotificationObjects 15 }

sonusPolicyServerADServerSyncFailed OBJECT-TYPE
    SYNTAX          DisplayString
    MAX-ACCESS      read-only
    STATUS          current
    DESCRIPTION     
            "Specifies the AD Server sync status."
    ::= { sonusPolicyServerNotificationObjects 16 }

sonusPolicyServerADServerSyncSuccess OBJECT-TYPE
    SYNTAX          DisplayString
    MAX-ACCESS      read-only
    STATUS          current
    DESCRIPTION     
            "Specifies the AD Server sync status."
    ::= { sonusPolicyServerNotificationObjects 17 }

sonusPolicyServerDbOperationFailureNotification NOTIFICATION-TYPE
    OBJECTS         { sonusAlarmNodeID, sonusAlarmLevel, 
                      sonusAlarmSequenceId, sonusAlarmTime, 
                      sonusAlarmDescription, 
                      sonusPolicyServerDbOperationFailureReason }
    STATUS          current
    DESCRIPTION     
            "DB operation failed. Look at the failure reason."
    ::= { sonusPolicyServerNotificationPrefix 1 }

sonusPolicyServerRegisterNotification NOTIFICATION-TYPE
    OBJECTS         { sonusAlarmNodeID, sonusAlarmLevel, 
                      sonusAlarmSequenceId, sonusAlarmTime, 
                      sonusAlarmDescription, sonusPolicyServerClientName, 
                      sonusPolicyServerRegisterReason }
    STATUS          current
    DESCRIPTION     
            "Register operation. Look at register reason."
    ::= { sonusPolicyServerNotificationPrefix 2 }

sonusPolicyServerUnregisterNotification NOTIFICATION-TYPE
    OBJECTS         { sonusAlarmNodeID, sonusAlarmLevel, 
                      sonusAlarmSequenceId, sonusAlarmTime, 
                      sonusAlarmDescription, sonusPolicyServerClientName, 
                      sonusPolicyServerUnregisterReason }
    STATUS          current
    DESCRIPTION     
            "Unregister operation. Look at unregister reason."
    ::= { sonusPolicyServerNotificationPrefix 3 }

sonusPolicyServerScpCommunicationUpNotification NOTIFICATION-TYPE
    OBJECTS         { sonusAlarmNodeID, sonusAlarmLevel, 
                      sonusAlarmSequenceId, sonusAlarmTime, 
                      sonusAlarmDescription }
    STATUS          current
    DESCRIPTION     
            "Communication to SCP is UP."
    ::= { sonusPolicyServerNotificationPrefix 4 }

sonusPolicyServerScpCommunicationDownNotification NOTIFICATION-TYPE
    OBJECTS         { sonusAlarmNodeID, sonusAlarmLevel, 
                      sonusAlarmSequenceId, sonusAlarmTime, 
                      sonusAlarmDescription }
    STATUS          current
    DESCRIPTION     
            "Communication to SCP is DOWN."
    ::= { sonusPolicyServerNotificationPrefix 5 }

sonusPolicyServerCallProcessTimeHighThresholdNotification NOTIFICATION-TYPE
    OBJECTS         { sonusAlarmNodeID, sonusAlarmLevel, 
                      sonusAlarmSequenceId, sonusAlarmTime, 
                      sonusAlarmDescription }
    STATUS          current
    DESCRIPTION     
            "PSX overload condition set."
    ::= { sonusPolicyServerNotificationPrefix 6 }

sonusPolicyServerCallProcessTimeLowThresholdNotification NOTIFICATION-TYPE
    OBJECTS         { sonusAlarmNodeID, sonusAlarmLevel, 
                      sonusAlarmSequenceId, sonusAlarmTime, 
                      sonusAlarmDescription }
    STATUS          current
    DESCRIPTION     
            "PSX overload condition cleared."
    ::= { sonusPolicyServerNotificationPrefix 7 }

sonusPolicyServerScpTimeoutNotification NOTIFICATION-TYPE
    OBJECTS         { sonusAlarmNodeID, sonusAlarmLevel, 
                      sonusAlarmSequenceId, sonusAlarmTime, 
                      sonusAlarmDescription }
    STATUS          current
    DESCRIPTION     
            "SCP queries timing out."
    ::= { sonusPolicyServerNotificationPrefix 8 }

sonusPolicyServerNoRouteFoundNotification NOTIFICATION-TYPE
    OBJECTS         { sonusAlarmNodeID, sonusAlarmLevel, 
                      sonusAlarmSequenceId, sonusAlarmTime, 
                      sonusAlarmDescription }
    STATUS          current
    DESCRIPTION     
            "No route found for Pes request"
    ::= { sonusPolicyServerNotificationPrefix 9 }

sonusPolicyServerTMControlAppliedNotification NOTIFICATION-TYPE
    OBJECTS         { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMAppliedControlType, 
                      sonusPolicyServerTMAddressNature }
    STATUS          current
    DESCRIPTION     
            "A traffic control has been applied."
    ::= { sonusPolicyServerNotificationPrefix 10 }

sonusPolicyServerCongestionNotification NOTIFICATION-TYPE
    OBJECTS         { sonusAlarmNodeID, sonusAlarmLevel, 
                      sonusAlarmSequenceId, sonusAlarmTime, 
                      sonusAlarmDescription, 
                      sonusPolicyServerCongestionLevel }
    STATUS          current
    DESCRIPTION     
            "The PSX congestion control level is changed"
    ::= { sonusPolicyServerNotificationPrefix 11 }

sonusPolicyServerDbConnSuccessNotification NOTIFICATION-TYPE
    OBJECTS         { sonusAlarmNodeID, sonusAlarmLevel, 
                      sonusAlarmSequenceId, sonusAlarmTime, 
                      sonusAlarmDescription }
    STATUS          current
    DESCRIPTION     
            "The 'pes' process establishes connection to the PSX DB."
    ::= { sonusPolicyServerNotificationPrefix 12 }

sonusPolicyServerPipeCommunicationDownNotification NOTIFICATION-TYPE
    OBJECTS         { sonusAlarmNodeID, sonusAlarmLevel, 
                      sonusAlarmSequenceId, sonusAlarmTime, 
                      sonusAlarmDescription, 
                      sonusPolicyServerPipeErrorCode }
    STATUS          current
    DESCRIPTION     
            "'pes' process was unable to establish connection with master 'pipe' process."
    ::= { sonusPolicyServerNotificationPrefix 13 }

sonusPolicyServerPipeRegistrationFailureNotification NOTIFICATION-TYPE
    OBJECTS         { sonusAlarmNodeID, sonusAlarmLevel, 
                      sonusAlarmSequenceId, sonusAlarmTime, 
                      sonusAlarmDescription, 
                      sonusPolicyServerPipeErrorCode }
    STATUS          current
    DESCRIPTION     
            "'pes' process was unable to register with master 'pipe' process."
    ::= { sonusPolicyServerNotificationPrefix 14 }

sonusPolicyServerPipeIOErrorNotification NOTIFICATION-TYPE
    OBJECTS         { sonusAlarmNodeID, sonusAlarmLevel, 
                      sonusAlarmSequenceId, sonusAlarmTime, 
                      sonusAlarmDescription, 
                      sonusPolicyServerPipeErrorCode }
    STATUS          current
    DESCRIPTION     
            "'pes' process was unable to send/receive an update to 'pipe' process."
    ::= { sonusPolicyServerNotificationPrefix 15 }

sonusPolicyServerPipeMWIQueueLevelChanged NOTIFICATION-TYPE
    OBJECTS         { sonusAlarmNodeID, sonusAlarmLevel, 
                      sonusAlarmSequenceId, sonusAlarmTime, 
                      sonusAlarmDescription, 
                      sonusPolicyServerPipeMwiQueueLevel }
    STATUS          current
    DESCRIPTION     
            "The MWI queue level changed. There is a safe level, followed by yellow, 
             orange and red levels. If the incoming message rate is far higher than 
             the consumption rate (updating the database), then the queue builds up 
             and crosses levels. Once the red level is reached, incoming messages 
             will be floored (not put in the queue)."
    ::= { sonusPolicyServerNotificationPrefix 16 }

sonusPolicyServerPipeCommunicationUpNotification NOTIFICATION-TYPE
    OBJECTS         { sonusAlarmNodeID, sonusAlarmLevel, 
                      sonusAlarmSequenceId, sonusAlarmTime, 
                      sonusAlarmDescription }
    STATUS          current
    DESCRIPTION     
            "'pes' process establishes connection with master 'pipe' process."
    ::= { sonusPolicyServerNotificationPrefix 17 }

sonusPolicyServerPipeRegistrationSuccessNotification NOTIFICATION-TYPE
    OBJECTS         { sonusAlarmNodeID, sonusAlarmLevel, 
                      sonusAlarmSequenceId, sonusAlarmTime, 
                      sonusAlarmDescription }
    STATUS          current
    DESCRIPTION     
            "'pes' process registers with master 'pipe' process."
    ::= { sonusPolicyServerNotificationPrefix 18 }

sonusPolicyServerLwresdCommunicationUpNotification NOTIFICATION-TYPE
    OBJECTS         { sonusAlarmNodeID, sonusAlarmLevel, 
                      sonusAlarmSequenceId, sonusAlarmTime, 
                      sonusAlarmDescription }
    STATUS          current
    DESCRIPTION     
            "Communication to LWRESD is UP."
    ::= { sonusPolicyServerNotificationPrefix 19 }

sonusPolicyServerLwresdCommunicationDownNotification NOTIFICATION-TYPE
    OBJECTS         { sonusAlarmNodeID, sonusAlarmLevel, 
                      sonusAlarmSequenceId, sonusAlarmTime, 
                      sonusAlarmDescription }
    STATUS          current
    DESCRIPTION     
            "Communication to LWRESD is DOWN."
    ::= { sonusPolicyServerNotificationPrefix 20 }

sonusPolicyServerSqlErrorHighThresholdNotification NOTIFICATION-TYPE
    OBJECTS         { sonusAlarmNodeID, sonusAlarmLevel, 
                      sonusAlarmSequenceId, sonusAlarmTime, 
                      sonusAlarmDescription }
    STATUS          current
    DESCRIPTION     
            "PES communication ports closed due to excessive failures."
    ::= { sonusPolicyServerNotificationPrefix 21 }

sonusPolicyServerInternalErrorHighThresholdNotification NOTIFICATION-TYPE
    OBJECTS         { sonusAlarmNodeID, sonusAlarmLevel, 
                      sonusAlarmSequenceId, sonusAlarmTime, 
                      sonusAlarmDescription }
    STATUS          current
    DESCRIPTION     
            "PSX excessive Internal communication failure crossed configured threshold."
    ::= { sonusPolicyServerNotificationPrefix 22 }

sonusPolicyServerExternalErrorHighThresholdNotification NOTIFICATION-TYPE
    OBJECTS         { sonusAlarmNodeID, sonusAlarmLevel, 
                      sonusAlarmSequenceId, sonusAlarmTime, 
                      sonusAlarmDescription }
    STATUS          current
    DESCRIPTION     
            "PSX excessive External communication failure crossed configured threshold."
    ::= { sonusPolicyServerNotificationPrefix 23 }

sonusPolicyServerInternalErrorLowThresholdNotification NOTIFICATION-TYPE
    OBJECTS         { sonusAlarmNodeID, sonusAlarmLevel, 
                      sonusAlarmSequenceId, sonusAlarmTime, 
                      sonusAlarmDescription }
    STATUS          current
    DESCRIPTION     
            "PSX excessive Internal communication failure cleared."
    ::= { sonusPolicyServerNotificationPrefix 24 }

sonusPolicyServerExternalErrorLowThresholdNotification NOTIFICATION-TYPE
    OBJECTS         { sonusAlarmNodeID, sonusAlarmLevel, 
                      sonusAlarmSequenceId, sonusAlarmTime, 
                      sonusAlarmDescription }
    STATUS          current
    DESCRIPTION     
            "PSX excessive External communication failure cleared."
    ::= { sonusPolicyServerNotificationPrefix 25 }

sonusPipeTMControlProvisionedNotification NOTIFICATION-TYPE
    OBJECTS         { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
    STATUS          current
    DESCRIPTION     
            "A traffic control has been provisioned."
    ::= { sonusPolicyServerNotificationPrefix 26 }

sonusPipeTMControlRemovedNotification NOTIFICATION-TYPE
    OBJECTS         { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
    STATUS          current
    DESCRIPTION     
            "A traffic control has been removed."
    ::= { sonusPolicyServerNotificationPrefix 27 }

sonusPipeTMControlModifiedNotification NOTIFICATION-TYPE
    OBJECTS         { sonusAlarmNodeID, sonusAlarmLevel, 
                      sonusAlarmSequenceId, sonusAlarmTime, 
                      sonusAlarmDescription, 
                      sonusPolicyServerTMElementType, 
                      sonusPolicyServerTMIdentifier1, 
                      sonusPolicyServerTMIdentifier2, 
                      sonusPolicyServerTMProvControlType, 
                      sonusPolicyServerTMAddressNature }
    STATUS          current
    DESCRIPTION     
            "A traffic control has been modified."
    ::= { sonusPolicyServerNotificationPrefix 28 }

sonusPolicyServerLWRESDDNSServerBlacklistedNotification NOTIFICATION-TYPE
    OBJECTS         { sonusAlarmNodeID, sonusAlarmLevel, 
                      sonusAlarmSequenceId, sonusAlarmTime, 
                      sonusAlarmDescription, 
                      sonusPolicyServerLWRESDBlacklisted }
    STATUS          current
    DESCRIPTION     
            "ENUM Server is Blacklisted."
    ::= { sonusPolicyServerNotificationPrefix 29 }

sonusPolicyServerLWRESDDNSServerRecoveredNotification NOTIFICATION-TYPE
    OBJECTS         { sonusAlarmNodeID, sonusAlarmLevel, 
                      sonusAlarmSequenceId, sonusAlarmTime, 
                      sonusAlarmDescription, 
                      sonusPolicyServerLWRESDWhitelisted }
    STATUS          current
    DESCRIPTION     
            "ENUM Server is Whitelisted."
    ::= { sonusPolicyServerNotificationPrefix 30 }

sonusPolicyServerLWRESDENUMServerBlacklistedNotification NOTIFICATION-TYPE
    OBJECTS         { sonusAlarmNodeID, sonusAlarmLevel, 
                      sonusAlarmSequenceId, sonusAlarmTime, 
                      sonusAlarmDescription, 
                      sonusPolicyServerLWRESDBlacklisted }
    STATUS          current
    DESCRIPTION     
            "ENUM Server is Blacklisted."
    ::= { sonusPolicyServerNotificationPrefix 31 }

sonusPolicyServerLWRESDENUMServerRecoveredNotification NOTIFICATION-TYPE
    OBJECTS         { sonusAlarmNodeID, sonusAlarmLevel, 
                      sonusAlarmSequenceId, sonusAlarmTime, 
                      sonusAlarmDescription, 
                      sonusPolicyServerLWRESDWhitelisted }
    STATUS          current
    DESCRIPTION     
            "ENUM Server is Whitelisted."
    ::= { sonusPolicyServerNotificationPrefix 32 }

sonusPolicyServerADServerSyncFailedNotification NOTIFICATION-TYPE
    OBJECTS         { sonusAlarmNodeID, sonusAlarmLevel, 
                      sonusAlarmSequenceId, sonusAlarmTime, 
                      sonusAlarmDescription, 
                      sonusPolicyServerADServerSyncFailed }
    STATUS          current
    DESCRIPTION     
            "AD Server sync failed."
    ::= { sonusPolicyServerNotificationPrefix 33 }

sonusPolicyServerADServerSyncSuccessNotification NOTIFICATION-TYPE
    OBJECTS         { sonusAlarmNodeID, sonusAlarmLevel, 
                      sonusAlarmSequenceId, sonusAlarmTime, 
                      sonusAlarmDescription, 
                      sonusPolicyServerADServerSyncSuccess }
    STATUS          current
    DESCRIPTION     
            "Ad Server sync up and syncing."
    ::= { sonusPolicyServerNotificationPrefix 34 }

END -- end of module SONUS-SBX-POLICY-SERVER-TRAP-MIB.
