ZTE-ALARM-IRP-MIB DEFINITIONS ::= BEGIN

IMPORTS
        MODULE-IDENTITY, OBJECT-TYPE, NOTIFICATION-TYPE,
        enterprises, Integer32
                FROM SNMPv2-SMI
        TEXTUAL-CONVENTION, DisplayString, DateAndTime,RowStatus
                FROM SNMPv2-TC
        OBJECT-GROUP, NOTIFICATION-GROUP, MODULE-COMPLIANCE
                FROM SNMPv2-CONF
        alarm
        	FROM ZTE-IRP-MIB;


alarmIRP                  OBJECT IDENTIFIER ::= { alarm 1 }
alarmIRPInfo			  OBJECT IDENTIFIER ::= { alarmIRP 1 }
alarmCount		  		  OBJECT IDENTIFIER ::= { alarmIRP 2 }	
alarmNotifications        OBJECT IDENTIFIER ::= { alarmIRP 4 }
alarmNotificationProfile  OBJECT IDENTIFIER ::= { alarmNotifications 1 }
alarmConformance          OBJECT IDENTIFIER ::= { alarmIRP 5 }
alarmFilter               OBJECT IDENTIFIER ::= { alarmIRP 6 }
alarmOperation            OBJECT IDENTIFIER ::= { alarmIRP 7 }

--======================================================================
-- TEXTUAL CONVENTIONS
--======================================================================
ManagedObjectInstance ::= TEXTUAL-CONVENTION
        STATUS current
        DESCRIPTION
                "the unique name of one object instance."
        SYNTAX OCTET STRING (SIZE (0..512))

AdditionalText   ::= TEXTUAL-CONVENTION
        STATUS      current
        DESCRIPTION
                "This object represents some arbitrary additional 
                 information of the alarm."
        SYNTAX      OCTET STRING (SIZE (0..1000))

TypeOfEvent ::= TEXTUAL-CONVENTION
        STATUS current
        DESCRIPTION
                "Event type specified in ITU recommendations 
                 X.733 and X736."
        SYNTAX INTEGER {
                communicationsAlarm(1),
                processingErrorAlarm(2),
                environmentalAlarm(3),
                qualityOfServiceAlarm(4),
                equipmentAlarm(5),
                integrityViolation(6),
                operationalViolation(7),
                physicalViolation(8),
                securityServiceViolation(9),
                timeDomainViolation(10),
                omcAlarm(11)          
        }

PerceivedSeverity ::= TEXTUAL-CONVENTION
        STATUS current
        DESCRIPTION        
                "the alarm level including 
                Critical, Major, Minor, Warning, and Indeterminate."
        SYNTAX INTEGER {
                indeterminate(1),
                critical(2),
                major(3),
                minor(4),
                warning(5),
                cleared(6)
        }

SeverityFilter ::=   TEXTUAL-CONVENTION
        STATUS current
        DESCRIPTION        
                "the alarm level filter including 
                Critical, Major, Minor, Warning, and Indeterminate."
        SYNTAX INTEGER {
                noFilter(0),
                indeterminate(1),
                critical(2),
                major(3),
                minor(4),
                warning(5),
                cleared(6)
        }    
TypeFilter ::=   TEXTUAL-CONVENTION
        STATUS current
        DESCRIPTION        
                "Event type specified in ITU recommendations 
                 X.733 and X736."
        SYNTAX INTEGER {      
                noFilter(0),
                communicationsAlarm(1),
                processingErrorAlarm(2),
                environmentalAlarm(3),
                qualityOfServiceAlarm(4),
                equipmentAlarm(5),
                integrityViolation(6),
                operationalViolation(7),
                physicalViolation(8),
                securityService(9),
                timeDomainViolation(10),
                omcAlarm(11)     
        }            
        
AckStatus ::=   TEXTUAL-CONVENTION
        STATUS current
        DESCRIPTION        
                "the alarm ack status including ACKNOWLEDGED and UNACKNOWLEDGED"
        SYNTAX INTEGER {      
                acknowledged(1),
                unAcKnowledged(2)
        }    
        
ProbableCause ::= TEXTUAL-CONVENTION
        STATUS current
        DESCRIPTION        
                "The possible alarm causes are more detailed than
                 the alarmType. "
        SYNTAX INTEGER {
                -- The following values are defined in M.3100 (1995)
                indeterminate(0),
                alarmIndicationSignal(1),
                callSetupFailure(2),
                degradedSignal(3),
                farEndReceiverFailure(4),
                framingError(5),
                lossOfFrame(6),
                lossOfPointer(7),
                lossOfSignal(8),
                payloadTypeMismatch(9),
                m3100TransmissionError(10),
                remoteAlarmInterface(11),
                excessiveBitErrorRate(12),
                pathTraceMismatch(13),
                unavailable(14),
                signalLabelMismatch(15),
                lossOfMultiFrame(16),
                communicationsReceiveFailure(17),
                communicationsTransmitFailure(18),
                modulationFailure(19),
                demodulationFailure(20),

                backPlaneFailure(51),
                dataSetProblem(52),
                equipmentIdentifierDuplication(53),
                externalIfDeviceProblem(54),
                lineCardProblem(55),
                multiplexerProblem(56),
                neIdentifierDuplication(57),
                powerProblem(58),
                processorProblem(59),
                protectionPathFailure(60),
                receiverFailure(61),
                replaceableUnitMissing(62),
                replaceableUnitTypeMismatch(63),
                synchronisationSourceMismatch(64),
                terminalProblem(65),
                timingProblem(66),
                transmitterFailure(67),
                trunkCardProblem(68),
                replaceableUnitProblem(69),
                realTimeClockFailure(70),
                airCompressorFailure(101),
                airConditioningFailure(102),
                airDryerFailure(103),
                batteryDischarging(104),
                batteryFailure(105),
                commercialPowerFailure(106),
                coolingFanFailure(107),
                engineFailure(108),
                fireDetectorFailure(109),
                fuseFailure(110),
                generatorFailure(111),
                lowBatteryThreshold(112),
                pumpFailure(113),
                rectifierFailure(114),
                rectifierHighVoltage(115),
                rectifierLowVoltage(116),
                ventilationSystemFailure(117),
                enclosureDoorOpen(118),
                explosiveGas(119),
                fire(120),
                flood(121),
                highHumidity(122),
                highTemperature(123),
                highWind(124),
                iceBuildUp(125),
                -- IntrusionDetection (use X.736 value)
                lowFuel(127),
                lowHumidity(128),
                lowCablePressure(129),
                lowTemperature(130),
                lowWater(131),
                smoke(132),
                toxicGas(133),
                storageCapacityProblem(151),
                memoryMismatch(152),
                corruptData(153),
                outOfCPUCycles(154),
                softwareEnvironmentProblem(155),
                softwareDownloadFailure(156),
                lossOfRealTime(157),
                --
                -- The following values are defined in X.733 (1992)
                adapterError(301),
                applicationSubsystemFailure(302),
                bandwidthReduced(303),
                -- CallEstablishmentError (use M.3100 value)
                communicationsProtocolError(305),
                communicationsSubsystemFailure(306),
                configurationOrCustomizationError(307),
                congestion(308),
                -- CorruptData (use M.3100 value)
                cpuCyclesLimitExceeded(310),
                dataSetOrModemError(311),
                -- DegradedSignal (use M.3100 value)
                dtedceInterfaceError(313),
                -- EnclosureDoorOpen (use M.3100 value)
                equipmentMalfunction(315),
                excessiveVibration(316),
                fileError(317),
                -- FireDetected (use M.3100 value)
                -- FloodDetected (use M.3100 value)
                -- FramingError  (use M.3100 value)
                heatingOrVentilationOrCoolingSystemProblem(321),
                humidityUnacceptable(322),
                inputOutputDeviceError(323),
                inputDeviceError(324),
                lanError(325),
                leakDetected(326),
                localNodeTransmissionError(327),
                -- LossOfFrame (use M.3100 value)
                -- LossOfSignal (use M.3100 value)
                materialSupplyExhausted(330),
                -- MultiplexerProblem (use M.3100 value)
                outOfMemory(332),
                ouputDeviceError(333),
                performanceDegraded(334),
                -- PowerProblem (use M.3100 value)
                pressureUnacceptable(336),
                -- ProcessorProblem (use M.3100 value)
                -- PumpFailure (use M.3100 value)
                queueSizeExceeded(339),
                receiveFailure(340),
                -- ReceiverFailure (use M.3100 value)
                remoteNodeTransmissionError(342),
                resourceAtOrNearingCapacity(343),
                responseTimeExcessive(344),
                retransmissionRateExcessive(345),
                softwareError(346),
                softwareProgramAbnormallyTerminated(347),
                softwareProgramError(348),
                -- StorageCapacityProblem (use M.3100 value)
                temperatureUnacceptable(350),
                thresholdCrossed(351),
                -- TimingProblem (use M.3100 value)
                toxicLeakDetected(353),
                transmitFailure(354),
                -- TransmitterFailure (use M.3100 value)
                underlyingResourceUnavailable(356),
                versionMismatch(357),
                --
            
                -- The following values are defined in GSM 12.11 (1999)
                abisToBTSInterfaceFailure(501),
                abisToTRXInterfaceFailure(502),
                antennaProblem(503),
                batteryBreakdown(504),
                batteryChargingFault(505),
                clockSynchronisationProblem(506),
                combinerProblem(507),
                diskProblem(508),
                -- EquipmentFailure (use X.733 value)
                excessiveReceiverTemperature(510),
                excessiveTransmitterOutputPower(511),
                excessiveTransmitterTemperature(512),
                frequencyHoppingDegraded(513),
                frequencyHoppingFailure(514),
                frequencyRedefinitionFailed(515),
                lineInterfaceFailure(516),
                linkFailure(517),
                lossOfSynchronisation(518),
                lostRedundancy(519),
                mainsBreakdownWithBatteryBackUp(520),
                mainsBreakdownWithoutBatteryBackUp(521),
                powerSupplyFailure(522),
                receiverAntennaFault(523),
                -- ReceiverFailure (use M.3100 value)
                receiverMulticouplerFailure(525),
                reducedTransmitterOutputPower(526),
                signalQualityEvaluationFault(527),
                timeslotHardwareFailure(528),
                transceiverProblem(529),
                transcoderProblem(530),
                transcoderOrRateAdapterProblem(531),
                transmitterAntennaFailure(532),
                transmitterAntennaNotAdjusted(533),
                -- TransmitterFailure (use M.3100 value)
                transmitterLowVoltageOrCurrent(535),
                transmitterOffFrequency(536),
                databaseInconsistency(537),
                fileSystemCallUnsuccessful(538),
                inputParameterOutOfRange(539),
                invalidParameter(540),
                invalidPointer(541),
                messageNotExpected(542),
                messageNotInitialised(543),
                messageOutOfSequence(544),
                systemCallUnsuccessful(545),
                timeoutExpired(546),
                variableOutOfRange(547),
                watchDogTimerExpired(548),
                coolingSystemFailure(549),
                externalEquipmentFailure(550),
                externalPowerSupplyFailure(551),
                externalTransmissionDeviceFailure(552),
                -- FanFailure (use M.3100 value)
                -- HighHumidity (use M.3100 value)
                -- HighTemperature (use M.3100 value)
                -- IntrusionDetected (use X.736 value)
                -- LowHumidity (use M.3100 value)
                -- LowTemperature (use M.3100 value)
                -- SmokeDetected (use M.3100 value)
                -- ExcessiveErrorRate (use M.3100 value)
                reducedAlarmReporting(561),
                reducedEventReporting(562),
                reducedLoggingCapability(563),
                systemResourcesOverload(564),
                broadcastChannelFailure(565),
                connectionEstablishmentError(566),
                invalidMessageReceived(567),
                invalidMSUReceived(568),
                lapdLinkProtocolFailure(569),
                localAlarmIndication(570),
                remoteAlarmIndication(571),
                routingFailure(572),
                ss7ProtocolFailure(573),
                gsm1211TransmissionError(574),
                
                
                -- The following values are defined in X.736 (1992)
                authenticationFailure(701),
                breachOfConfidentiality(702),
                cableTamper(703),
                delayedInformation(704),
                denialOfService(705),
                duplicateInformation(706),
                informationMissing(707),
                informationModificationDetected(708),
                informationOutOfSequence(709),
                intrusionDetection(710),
                keyExpired(711),
                nonRepudiationFailure(712),
                outOfHoursActivity(713),
                outOfService(714),
                proceduralError(715),
                unauthorizedAccessAttempt(716),
                unexpectedInformation(717),
                unspecifiedReason(718),
                protectionMechanismFailure(81),
                protectionResourceFailure(82),
                intrusionDetection(126),
                externalPointFailure(136),
				reinitialized(158),
				excessiveErrorRate(203),
				equipmentOutOfService(999)
				--
                -- The following UMTS specific values are defined:
	-- <UMTS specific values to be inserted here>
        }        
        

--======================================================================
-- IRP VERSION INFORMATION
--======================================================================

alarmIrpVersion OBJECT-TYPE
        SYNTAX      DisplayString (SIZE (0..20))
        MAX-ACCESS  read-only
        STATUS      current
        DESCRIPTION
                "This object represents the version of the Alarm IRP
                 SNMPv2 Solution Set supported by the agent."
        ::= { alarmIRPInfo 1 }


--======================================================================
-- GENERIC EVENT ATTRIBUTES SPECIFIED BY NOTIFICATION IRP
--======================================================================

sendNotificationId OBJECT-TYPE
        SYNTAX      Integer32
        MAX-ACCESS  accessible-for-notify
        STATUS      current
        DESCRIPTION
                "This object represent the notification identifier
                of current send notification ( AlarmNew,AlarmCleared,AlarmAckChange,AlarmCommentChange,AlarmSync)
                
                The agent shall store the notification identifier
                of the last send FM notification in this object
                immediately after sending the notification.
                
                The manager can retrieve the current value of this
                object to detect lost notifications. This mechanism
                can be used by the manager when no notification
                is received for a certain time (e.g. 10 minutes)
                to evaluate whether a synchronization should be performed. "
        ::= { alarmIRPInfo 2 }


systemDN OBJECT-TYPE
        SYNTAX      ManagedObjectInstance
        MAX-ACCESS  read-only
        STATUS      current
        DESCRIPTION
                "This object carries the Distinguished Name (DN) of the system 
                 which generates the Notification.
                 The combination of notificationId and systemDN uniquely 
                 identifies each notification."
        ::= { alarmIRPInfo 3 }
        
lastSendNotificationId OBJECT-TYPE
        SYNTAX      Integer32
        MAX-ACCESS  accessible-for-notify
        STATUS      current
        DESCRIPTION
                "This object represent the notification identifier
                of last send notification ( AlarmNew, AlarmCleared,AlarmAckChange,AlarmCommentChange)
                
                The agent shall store the notification identifier
                of the last send FM notification in this object
                immediately after sending the notification.
                
                The manager can retrieve the current value of this
                object to detect lost notifications. This mechanism
                can be used by the manager when no notification
                is received for a certain time (e.g. 10 minutes)
                to evaluate whether a synchronization should be performed. "
        ::= { alarmIRPInfo 4 }
        
        
messageCode OBJECT-TYPE
        SYNTAX      Integer32
        MAX-ACCESS  accessible-for-notify
        STATUS      current
        DESCRIPTION        
                "the ems error code."
       ::= { alarmIRPInfo 5 }

syncUniqueId OBJECT-TYPE
        SYNTAX      Integer32
        MAX-ACCESS  accessible-for-notify
        STATUS      current
        DESCRIPTION        
                "This object represent the sync identifier of the same alarm sync operation. "
       ::= { alarmIRPInfo 6 }

--======================================================================
-- NUMBER OF ALARMS
--======================================================================

alarmIndeterminateNumber OBJECT-TYPE
        SYNTAX      Integer32
        MAX-ACCESS  read-only
        STATUS      current
        DESCRIPTION
                "This object determines the number of currently 
                 active alarms with perceived severity 'indeterminate'."
        ::= { alarmCount 1 }

alarmCriticalNumber OBJECT-TYPE
        SYNTAX      Integer32
        MAX-ACCESS  read-only
        STATUS      current
        DESCRIPTION
                "This object determines the number of currently 
                 active alarms with perceived severity 'critical'."
        ::= { alarmCount 2 }

alarmMajorNumber OBJECT-TYPE
        SYNTAX      Integer32
        MAX-ACCESS  read-only
        STATUS      current
        DESCRIPTION
                "This object determines the number of currently 
                 active alarms with perceived severity 'major'."
        ::= { alarmCount 3 }

alarmMinorNumber OBJECT-TYPE
        SYNTAX      Integer32
        MAX-ACCESS  read-only
        STATUS      current
        DESCRIPTION
                "This object determines the number of currently 
                 active alarms with perceived severity 'minor'."
        ::= { alarmCount 4 }

alarmWarningNumber OBJECT-TYPE
        SYNTAX      Integer32
        MAX-ACCESS  read-only
        STATUS      current
        DESCRIPTION
                "This object determines the number of currently 
                 active alarms with perceived severity 'warning'."
        ::= { alarmCount 5 }

alarmNumber OBJECT-TYPE
        SYNTAX      Integer32
        MAX-ACCESS  read-only
        STATUS      current
        DESCRIPTION
                "This object determines the total number of 
                 currently active alarms, i.e. the total number
                 of entries in the Active Alarm Table."
        ::= { alarmCount 6 }
        
--======================================================================
-- CURRENT ALARM TABLE
--======================================================================

currentAlarmTable OBJECT-TYPE
        SYNTAX      SEQUENCE OF AlarmEntry
        MAX-ACCESS  not-accessible
        STATUS      current
        DESCRIPTION
                "Table with information about the current alarms in the system."
        ::= { alarmIRP 3 }

currentAlarmEntry OBJECT-TYPE
        SYNTAX       AlarmEntry
        MAX-ACCESS   not-accessible
        STATUS       current
        DESCRIPTION
                "One entry in the table holds one current alarm."
        INDEX { alarmIndex }
::= { currentAlarmTable 1 }

--**************************
-- define report field
--*************************

AlarmEntry ::= SEQUENCE {
		alarmIndex		    		Integer32,
        alarmId                     DisplayString,
        alarmManagedObjectInstance  ManagedObjectInstance,
        alarmEventTime              DateAndTime,
        alarmEventType              TypeOfEvent,
        alarmProbableCause          ProbableCause,
        alarmPerceivedSeverity      PerceivedSeverity,
        alarmSpecificProblem        DisplayString,
        alarmAdditionalText         AdditionalText,
        alarmComment                DisplayString,
        alarmCode                   DisplayString,
        alarmNetype                 DisplayString,
        rowStatus                   RowStatus,
        alarmCodeName               DisplayString,
        alarmManagedObjectInstanceName  DisplayString,
        alarmSystemType     		DisplayString,
        alarmNeIP                   DisplayString,
        alarmAck                    AckStatus,
        cleiCode                    DisplayString,
        timeZoneID            	    DisplayString,
        timeZoneOffset          		Integer32,
        dSTSaving               		Integer32,
        aid                         DisplayString,
        id                          DisplayString,
        alarmOtherInfo              DisplayString,
        alarmMocObjectInstance   DisplayString
        }

alarmId OBJECT-TYPE
        SYNTAX      DisplayString (SIZE (0..255))
        MAX-ACCESS  read-only
        STATUS      current
        DESCRIPTION
                "This object represents an alarm in EMS using 
                the private format of vendor"
        ::= { currentAlarmEntry 1 }

alarmManagedObjectInstance OBJECT-TYPE
        SYNTAX      ManagedObjectInstance
        MAX-ACCESS  read-only
        STATUS      current
        DESCRIPTION
                "This object identifies the MO instance of 
                 network resource to which the alarm is 
                 related."
        ::= { currentAlarmEntry 2 }

alarmEventTime OBJECT-TYPE
        SYNTAX      DateAndTime
        MAX-ACCESS  read-only
        STATUS      current
        DESCRIPTION 
                "This object represents the event time of the subject alarm."
        ::= { currentAlarmEntry 3 }
        
alarmEventType OBJECT-TYPE
        SYNTAX      TypeOfEvent
        MAX-ACCESS  read-only
        STATUS      current
        DESCRIPTION
                "This object represents the type of event."
        ::= { currentAlarmEntry 4 }

alarmProbableCause OBJECT-TYPE
        SYNTAX      ProbableCause
        MAX-ACCESS  read-only
        STATUS      current
        DESCRIPTION
                "This object represents the probable cause 
                 of the current."
        ::= { currentAlarmEntry 5 }

alarmPerceivedSeverity OBJECT-TYPE
        SYNTAX      PerceivedSeverity
        MAX-ACCESS  read-write
        STATUS      current
        DESCRIPTION
                "This object represents the perceived severity of 
                 the alarm."
        ::= { currentAlarmEntry 6 }

alarmSpecificProblem OBJECT-TYPE
        SYNTAX      DisplayString (SIZE (0..255))
        MAX-ACCESS  read-only
        STATUS      current
        DESCRIPTION
                "This object represents the vendor specific problem 
                 ."
        ::= { currentAlarmEntry 7 }

alarmAdditionalText OBJECT-TYPE
        SYNTAX      AdditionalText
        MAX-ACCESS  read-only
        STATUS      current
        DESCRIPTION
                "This object represents some arbitrary additional 
                 information of the alarm."
        ::= { currentAlarmEntry 8 }

alarmIndex OBJECT-TYPE
        SYNTAX      Integer32(0..2147483647)
        MAX-ACCESS  read-only
        STATUS      current
        DESCRIPTION
                "This object uniquely identifies an entry in the 
                 Active Alarm Table. It increases every time a new alarm 
                 occurs. Due to cleared alarms the index will not be 
                 contiguous. When the maximum is reached of 
                 Integer32, the value of this object rolls over to 1. 
                 The actor must use 'alarmEventTime' to sort on 
                 chronological order.
                 
                 The alarmIndex object is read-only ,and it
                 is used as index in the Active Alarm Table. 
                 The alarmIndex facilities the way to extract 
                 the corresponding value from a notification where 
                 the object is included."
        ::= { currentAlarmEntry 9 }
    

alarmComment  OBJECT-TYPE
        SYNTAX      DisplayString (SIZE (0..255))
        MAX-ACCESS  read-write
        STATUS      current
        DESCRIPTION
                "This object represents alarm comment."
        ::= { currentAlarmEntry 10 }

alarmCode OBJECT-TYPE
        SYNTAX      DisplayString (SIZE (0..50))
        MAX-ACCESS  read-only
        STATUS      current
        DESCRIPTION
                "This object represents an alarm code"
        ::= { currentAlarmEntry 11 }
 
alarmNetype OBJECT-TYPE
        SYNTAX      DisplayString (SIZE (0..50))
        MAX-ACCESS  read-only
        STATUS      current
        DESCRIPTION
                "This object represents an alarm netype"
        ::= { currentAlarmEntry 12 }              
rowStatus OBJECT-TYPE
        SYNTAX      RowStatus
        MAX-ACCESS  not-accessible
        STATUS      current
        DESCRIPTION
                "TControls and reflects the  status  of  rows  in   this table "
        ::= { currentAlarmEntry 13 }  
        
alarmCodeName OBJECT-TYPE
        SYNTAX      DisplayString (SIZE (0..255))
        MAX-ACCESS  read-only
        STATUS      current
        DESCRIPTION
                "This object represents an alarm code name"
        ::= { currentAlarmEntry 14 }       
        
alarmManagedObjectInstanceName OBJECT-TYPE
        SYNTAX      DisplayString (SIZE (0..255))
        MAX-ACCESS  read-only
        STATUS      current
        DESCRIPTION
                "This object identifies the MO instance name of 
                 network resource to which the alarm is 
                 related."
        ::= { currentAlarmEntry 15 }
        
alarmSystemType OBJECT-TYPE
        SYNTAX      DisplayString (SIZE (0..5))
        MAX-ACCESS  read-only
        STATUS      current
        DESCRIPTION
                "This object represents systemtype."
        ::= { currentAlarmEntry 16 }
        
alarmNeIP OBJECT-TYPE
        SYNTAX      DisplayString (SIZE (0..60))
        MAX-ACCESS  read-only
        STATUS      current
        DESCRIPTION
                "This object identifies the IP of 
                 network resource to which the alarm is 
                 related."
        ::= { currentAlarmEntry 17 }  
        
        
alarmAck OBJECT-TYPE
        SYNTAX      AckStatus
        MAX-ACCESS  read-write
        STATUS      current
        DESCRIPTION
                "Ack AlarmData or UnAckAlarmData"
        ::= { currentAlarmEntry 18 }     
                        
cleiCode OBJECT-TYPE
        SYNTAX      DisplayString (SIZE (0..50))
        MAX-ACCESS  read-only
        STATUS      current
        DESCRIPTION
                "This object represents the CLEI Code of the MO instance of 
                 network resource. "
        ::= { currentAlarmEntry 19 }  
        
timeZoneID OBJECT-TYPE
        SYNTAX      DisplayString (SIZE (0..50))
        MAX-ACCESS  read-only
        STATUS      current
        DESCRIPTION
                "This object represents the NE's TimeZoneID. "
        ::= { currentAlarmEntry 20 }

timeZoneOffset OBJECT-TYPE
        SYNTAX      Integer32
        MAX-ACCESS  read-only
        STATUS      current
        DESCRIPTION
                "This object represents the NE's TimeZoneOffset. "
        ::= { currentAlarmEntry 21 }
                
dSTSaving OBJECT-TYPE
        SYNTAX      Integer32
        MAX-ACCESS  read-only
        STATUS      current
        DESCRIPTION
                "This object represents the NE's DSTSaving. "
        ::= { currentAlarmEntry 22 }  
        
aid OBJECT-TYPE
        SYNTAX      DisplayString (SIZE (0..255))
        MAX-ACCESS  read-only
        STATUS      current
        DESCRIPTION
                "This object represents an alarm AID"
        ::= { currentAlarmEntry 23 }                          
        
id OBJECT-TYPE
        SYNTAX      DisplayString (SIZE (0..50))
        MAX-ACCESS  read-only
        STATUS      current
        DESCRIPTION
                "This object represents the number id of the alarm. "
        ::= { currentAlarmEntry 24 }   
        
alarmOtherInfo OBJECT-TYPE
        SYNTAX      DisplayString (SIZE (0..255))
        MAX-ACCESS  read-only
        STATUS      current
        DESCRIPTION
                "This object represents the custom properity of the alarm. "
        ::= { currentAlarmEntry 25 }  
        
        
alarmMocObjectInstance OBJECT-TYPE
        SYNTAX      DisplayString (SIZE (0..255))
        MAX-ACCESS  read-only
        STATUS      current
        DESCRIPTION
               "This object identifies the SUB MO instance of 
                 network resource to which the alarm is 
                 related."
        ::= { currentAlarmEntry 26 }  
        
                                     
--======================================================================
-- ALARM FILTER
--======================================================================
alarmFilterEnable OBJECT-TYPE
        SYNTAX      Integer32
        MAX-ACCESS  read-write
        STATUS      current
        DESCRIPTION
                "Alarm Filter enable or false,0 means false,while 1 means true."
        ::= { alarmFilter 1 }
        
alarmFilterCondition  OBJECT IDENTIFIER ::= { alarmFilter 3}
--======================================================================
-- ALARM FILTER
--======================================================================
        
 
alarmTypeFilter OBJECT-TYPE
        SYNTAX      TypeFilter
        MAX-ACCESS  read-write
        STATUS      current
        DESCRIPTION
                "This object filters alarm according to the alarm type.The alarm of specifical type will be sent."                 
        ::= { alarmFilterCondition 4 }  
alarmSeverityFilter OBJECT-TYPE
        SYNTAX      SeverityFilter
        MAX-ACCESS  read-write
        STATUS      current
        DESCRIPTION
                "This object filters alarm according to the alarm severity.The alarm of specifical severity will be sent."                 
        ::= { alarmFilterCondition 5 }  
                                            

alarmCodesExcludeFilter OBJECT-TYPE
        SYNTAX     OCTET STRING (SIZE (0..512))
        MAX-ACCESS  read-write
        STATUS      current
        DESCRIPTION
                "This object filters alarm according to the alarm code.  uses ',' as splitter between alarm codes .for example: 10001,10002 means :The alarm of specifical  code of 10001 and 10002 will not be sent. "                 
        ::= { alarmFilterCondition 6 }  

alarmTypeExcludeFilter OBJECT-TYPE
        SYNTAX     OCTET STRING (SIZE (0..512))
        MAX-ACCESS  read-write
        STATUS      current
        DESCRIPTION
                "This object filters alarm according to the alarm type.  uses ',' as splitter between alarm types .for example: 1,2 means :The alarms of specifical type  of 1 and 2,those will not be sent. "                 
        ::= { alarmFilterCondition 7 }  

alarmServerityExcludeFilter OBJECT-TYPE
        SYNTAX     OCTET STRING (SIZE (0..512))
        MAX-ACCESS  read-write
        STATUS      current
        DESCRIPTION
                "This object filters alarm according to the alarm serverity.  uses ',' as splitter between alarm serverity .for example: 1,2 means : The alarms of specifical  serverity of 1 and 2 will not  be sent. "                 
        ::= { alarmFilterCondition 8 }  

alarmSystemTypeCodeExcludeFilter OBJECT-TYPE
        SYNTAX     OCTET STRING (SIZE (0..512))
        MAX-ACCESS  read-write
        STATUS      current
        DESCRIPTION
                "This object filters alarm according to the alarm system type and alarm code.  uses '[]' as splitter between alarm system type and alarm code .for example: [6,1000][11,1200] means : System type is 6 and the alarm code for 1000, system type 11 and alarm code of 1200 is not sent."                 
        ::= { alarmFilterCondition 9 }  

alarmPosition1OrPostion2ExcludeFilter OBJECT-TYPE
        SYNTAX     OCTET STRING (SIZE (0..1024))
        MAX-ACCESS  read-write
        STATUS      current
        DESCRIPTION
                "This object filters alarm according to the alarm position1 or position2.  uses ',' as splitter between alarm position1 or poistion2. for example: CommonTopoObject=107-1417765074750,CommonTopoObject=100-1416791386500 means : Position1 is CommonTopoObject=107-1417765074750 and the position2 for CommonTopoObject=100-1416791386500, position1 CommonTopoObject=107-1417765074750 or position2 of CommonTopoObject=100-1416791386500 is not sent."                 
        ::= { alarmFilterCondition 10 }  
   
alarmSystemTypeCauseExcludeFilter OBJECT-TYPE
        SYNTAX     OCTET STRING (SIZE (0..512))
        MAX-ACCESS  read-write
        STATUS      current
        DESCRIPTION
                "This object filters alarm according to the alarm system type and northbound alarm code.  uses '[]' as splitter between alarm system type and northbound alarm code .for example: [6,716][11,351] means : System type is 6 and the northbound alarm code for 716, system type 11 and northbound alarm code of 351 is not sent."                 
        ::= { alarmFilterCondition 11 }     
        
                        
syncAlarm OBJECT-TYPE
        SYNTAX OCTET STRING (SIZE (0..1024))
        MAX-ACCESS  read-write
        STATUS      current
        DESCRIPTION
                "This object sync alarm ,once successfully set,ems will send alarm.The format is :'position:a,c;', 'a' and 'c' is Moc's Id."             
              
        ::= {alarmOperation 1 }
        
alarmTableFilter OBJECT-TYPE
        SYNTAX OCTET STRING (SIZE (0..1024))
        MAX-ACCESS  read-write
        STATUS      current
        DESCRIPTION
                "This object filters alarm according to serverity,type,northbound alarm code, alarm code, systemtype, position. The format is : 'PerceivedSeverity:1,3; TypeOfEvent:1,2; ProbableCause:1001,1002;SystemTypeAndCause:[6,716];SystemTypeAndCode:[6,1000];Position1OrPostion2:COMM:EMS=0806164728805,CommonTopoObject=123;Position:COMM:EMS=0806164728805,CommonTopoObject=123'"             
              
        ::= {alarmOperation 2 }   
        
alarmTrapEnable  OBJECT-TYPE
         SYNTAX INTEGER {
         off(0),
         on(1),
         error(3)
        } 
        MAX-ACCESS  read-write
        STATUS      current
        DESCRIPTION
                "This object enable alarm trap.1 means enable alarm trap,while 0 means disable alarm trap."             
              
        ::= {alarmOperation 3 }

clearAlarm  OBJECT-TYPE
        SYNTAX OCTET STRING (SIZE (0..1024))
        MAX-ACCESS  read-write
        STATUS      current
        DESCRIPTION
                "This object clear alarm ,use alarm's alarmPerceivedSeverity and id. for example 'PerceivedSeverity:2;Id:123' or  'PerceivedSeverity:3,4;' "             
              
        ::= {alarmOperation 4 }          
                 
--======================================================================
-- ALARM RELATED NOTIFICATIONS
--======================================================================

alarmNew NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo
                     }
        STATUS      current
        DESCRIPTION 
                "This notification is sent when a new Alarm is 
                 generated and stored in the Active Alarm Table. 
                 Note that the notification does not include all
                 objects for the corresponding entry in the Alarm 
                 Table. The reason is that some environments may have 
                 problems with large PDUs. Thus, the notification 
                 receiver must get the missing objects from the
                 Active Alarm Table.
                 
                 The value 'cleared' for the PerceivedSeverity
                 is not allowed for an alarm notification."
        ::= { alarmNotificationProfile 1 }


alarmCleared NOTIFICATION-TYPE
        OBJECTS {   alarmEventTime,
                    sendNotificationId,
                    lastSendNotificationId,   
                    systemDN,                    
                    alarmCode,                    
                    alarmManagedObjectInstance,
                    alarmEventType,
                    alarmProbableCause,
                    alarmPerceivedSeverity,
                    alarmSpecificProblem,
                    alarmAdditionalText,     
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo
                    }
        STATUS      current
        DESCRIPTION 
                "This notification is generated when an alarm is 
                 cleared. A cleared alarm is removed from the 
                 Active Alarm Table and is no longer accessible.
                 
                 It's impossible to retrieve an cleared alarm from
                 Active Alarm Table any more."
        ::= { alarmNotificationProfile 2 }
        
alarmAckChange NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo
                    }
        STATUS      current
        DESCRIPTION 
                "This notification is sent when alarm's status was changed,acknowledged or unacknowledged."
        ::= { alarmNotificationProfile 3 }

alarmCommentChange NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo                
                    }
        STATUS      current
        DESCRIPTION 
                "This notification is sent when alarm's content of comment was changed."
        ::= { alarmNotificationProfile 4 }

        
alarmListRebuild NOTIFICATION-TYPE
        OBJECTS {   systemDN
                     }
        STATUS      current
        DESCRIPTION 
                "This notification is sent when ems re-establish the connection to nms."
        ::= { alarmNotificationProfile 5 }        

alarmSync NOTIFICATION-TYPE
        OBJECTS {    
                    alarmEventTime,
                    sendNotificationId,
                    lastSendNotificationId,
                    systemDN,            
                    alarmCode,                    
                    alarmManagedObjectInstance,
                    alarmEventType,
                    alarmProbableCause,
                    alarmPerceivedSeverity,
                    alarmSpecificProblem,
                    alarmAdditionalText,     
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo
                     }
        STATUS      current
        DESCRIPTION 
                "This notification is generated when set syncAlarm successfully. 
                 The alarmManagedObjectInstance of all alarms are in line with user setting."
        ::= { alarmNotificationProfile 6 }  
        
        
messageInfo NOTIFICATION-TYPE
        OBJECTS {   systemDN,
                    messageCode 
                     }
        STATUS      current
        DESCRIPTION 
                "This notification is sent when ems on an abnormal situation."
        ::= { alarmNotificationProfile 7 } 
        
alarmSeverityChange NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo                
                    }
        STATUS      current
        DESCRIPTION 
                "This notification is sent when alarm's severity was changed."
        ::= { alarmNotificationProfile 8 }

alarmManagedObjectInstanceNameChange NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo                
                    }
        STATUS      current
        DESCRIPTION 
                "This notification is sent when alarm's subname1 was changed."
        ::= { alarmNotificationProfile 9 }
        
alarmServiceChange NOTIFICATION-TYPE
        OBJECTS {   alarmEventTime,
                    sendNotificationId,
                    lastSendNotificationId,
                    systemDN,
                    alarmCode,
                    alarmManagedObjectInstance,
                    alarmEventType,
                    alarmProbableCause,
                    alarmPerceivedSeverity,
                    alarmSpecificProblem ,
                    alarmAdditionalText,                    
                    alarmNetype,
                    alarmIndex,
                    alarmId,
                    alarmCodeName,
                    alarmManagedObjectInstanceName,
                    alarmSystemType,
                    alarmNeIP,
                    alarmAck,
                    cleiCode,
                    timeZoneID,
                    timeZoneOffset,
                    dSTSaving,
                    aid,
                    id,
                    alarmMocObjectInstance,
                    alarmComment,
                    alarmOtherInfo                
                    }
        STATUS      current
        DESCRIPTION 
                "This notification is sent when alarm's path was changed."
        ::= { alarmNotificationProfile 10 }
		
alarmSyncStart NOTIFICATION-TYPE
        OBJECTS {   
        						systemDN,
								syncUniqueId
                     }
        STATUS      current
        DESCRIPTION 
                "This notification is sent before send alarmSync trap to nms."
        ::= { alarmNotificationProfile 11 }
        
alarmSyncEnd NOTIFICATION-TYPE
        OBJECTS {   
        						systemDN,
								syncUniqueId
                     }
        STATUS      current
        DESCRIPTION 
                "This notification is sent after send all alarmSync trap to nms."
        ::= { alarmNotificationProfile 12 }

--======================================================================
-- CONFORMANCE INFORMATION
--======================================================================

alarmCompliances OBJECT IDENTIFIER ::= { alarmConformance 1 }
alarmGroups      OBJECT IDENTIFIER ::= { alarmConformance 2 }


--======================================================================
-- COMPLIANCE STATEMENTS
--======================================================================

alarmCompliance MODULE-COMPLIANCE
        STATUS current
        DESCRIPTION 
                "A collection of objects that are required for
                 compliance to the ALARM-IRP."

        MODULE -- This module
           MANDATORY-GROUPS { alarmAdminMandatoryGroup,
                              alarmMandatoryGroup,
                              alarmNotificationMandatoryGroup
                               }

           GROUP alarmAdminOptionalGroup
           DESCRIPTION
                   "This group is not optional. A SNMP entity may 
                    support one or several of the objects in the group."
                    
           GROUP alarmNumberGroup
           DESCRIPTION
                   "This group is not optional."
           

        ::= { alarmCompliances 1 }


--======================================================================
-- GROUPS
--======================================================================

alarmAdminMandatoryGroup OBJECT-GROUP  
        OBJECTS {   alarmIrpVersion        			
        	}
        STATUS      current
        DESCRIPTION 
                "A collection of mandatory objects holding administrative
                information."
        ::= { alarmGroups 1 }

alarmAdminOptionalGroup OBJECT-GROUP  
        OBJECTS {  
        	 systemDN
        	 }
        STATUS      current
        DESCRIPTION 
                "A collection of optional objects holding administrative
                information."
        ::= { alarmGroups 2 }

alarmNumberGroup OBJECT-GROUP
        OBJECTS {   alarmNumber,
                    alarmIndeterminateNumber,
                    alarmCriticalNumber,
                    alarmMajorNumber,
                    alarmMinorNumber,
                    alarmWarningNumber }
        STATUS      current
        DESCRIPTION 
                "A collection of optional objects for retrieval of 
                 the number of currently active alarms."
        ::= { alarmGroups 3 }

alarmMandatoryGroup OBJECT-GROUP
        OBJECTS {   alarmIndex,
                    alarmId,
                    alarmManagedObjectInstance,
                    alarmEventTime,
                    alarmEventType,
                    alarmProbableCause,
                    alarmPerceivedSeverity,
                    alarmSpecificProblem,
                    alarmAdditionalText }
        STATUS      current
        DESCRIPTION 
                "A collection of objects that represents mandatory 
                 alarm attributes."
        ::= { alarmGroups 4 }

alarmNotificationMandatoryGroup NOTIFICATION-GROUP
        NOTIFICATIONS { alarmNew,
                        alarmCleared,
                        alarmAckChange,
                        alarmCommentChange,
                        alarmListRebuild,
                        alarmSync,
                        messageInfo,
                        alarmSeverityChange,
                        alarmManagedObjectInstanceNameChange,
                        alarmServiceChange,
                        alarmSyncStart,
                        alarmSyncEnd
                        }
        STATUS      current
        DESCRIPTION 
                "A collection of mandatory alarm notifications."
        ::= { alarmGroups 5 }

END
