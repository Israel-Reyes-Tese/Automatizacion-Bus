--
-- This SMIv1 module has been generated by smidump 0.2-cvs. Do not edit.
--

LOG-MIB DEFINITIONS ::= BEGIN

IMPORTS
    OBJECT-TYPE
        FROM RFC-1212
    TRAP-TYPE
        FROM RFC-1215
    snmpResearchMIBs
        FROM SNMP-RESEARCH-MIB
    enterprises
        FROM SNMPv2-SMI
    DisplayString, RowStatus, TruthValue
        FROM SNMPv2-TC;

siLog OBJECT IDENTIFIER
    ::= { enterprises 99 12 40 }

-- siLog MODULE-IDENTITY
--     LAST-UPDATED    "199603050000Z"
--     ORGANIZATION    
--             "SNMP Research"
--     CONTACT-INFO    
--             " Postal: SNMP Research
--              3001 Kimberlin Heights Road
--              Knoxville, TN  37920-9716
--              
--              Tel: +1 423 579 3311
--              Fax: +1 423 579 6565
--              
--              E-mail: info@int.snmp.com
--              WWW: http://www.int.snmp.com"
--     DESCRIPTION     
--             "A MIB module used to monitor log files and to 
--              forward traps when specified text strings
--              are matched above a certain tolerence level."
--     ::= { enterprises 99 12 40 }


siLogObjects OBJECT IDENTIFIER
    ::= { siLog 1 }

siLogGlobalPollInterval OBJECT-TYPE
    SYNTAX          INTEGER
    ACCESS          read-write
    STATUS          mandatory
    DESCRIPTION     
            "The period, in seconds, when the log files will be
             checked to see if there are any regular expression
             entry matches or if the log file size threshold has been
             exceeded."
    ::= { siLogObjects 1 }

siLogGlobalPollNow OBJECT-TYPE
    SYNTAX          TruthValue
    ACCESS          read-write
    STATUS          mandatory
    DESCRIPTION     
            "Setting this object to true (1) will cause all the
             log files entered in the siLogTable to be checked to see 
             if the file size threshold has been reached or if any 
             regular expression matching has occurred."
    DEFVAL          { false }
    ::= { siLogObjects 2 }

siLogTable OBJECT-TYPE
    SYNTAX          SEQUENCE OF SiLogEntry
    ACCESS          not-accessible
    STATUS          mandatory
    DESCRIPTION     
            "The table of log files."
    ::= { siLogObjects 3 }

siLogEntry OBJECT-TYPE
    SYNTAX          SiLogEntry
    ACCESS          not-accessible
    STATUS          mandatory
    DESCRIPTION     
            "The information about a log file."
    INDEX           { siLogTableIndex }
    ::= { siLogTable 1 }

SiLogEntry ::=
    SEQUENCE {
        siLogTableIndex                 INTEGER,
        siLogDescr                      DisplayString,
        siLogName                       DisplayString,
        siLogMatchPattern               DisplayString,
        siLogMatchAllExceptPattern      TruthValue,
        siLogStartPosition              INTEGER,
        siLogStopPosition               INTEGER,
        siLogMatches                    INTEGER,
        siLogCommandOnMatch             DisplayString,
        siLogTrapOnMatch                TruthValue,
        siLogSize                       INTEGER,
        siLogMaxSize                    INTEGER,
        siLogCommandOnMaxSize           DisplayString,
        siLogTrapOnMaxSize              TruthValue,
        siLogPollInterval               INTEGER,
        siLogPollNow                    TruthValue,
        siLogOwner                      DisplayString,
        siLogRowStatus                  RowStatus
    }

siLogTableIndex OBJECT-TYPE
    SYNTAX          INTEGER (1..2147483647)
    ACCESS          not-accessible
    STATUS          mandatory
    DESCRIPTION     
            "The index of the log file Table."
    ::= { siLogEntry 1 }

siLogDescr OBJECT-TYPE
    SYNTAX          DisplayString
    ACCESS          read-write
    STATUS          mandatory
    DESCRIPTION     
            "A textual description of the log file being
             monitored."
    ::= { siLogEntry 2 }

siLogName OBJECT-TYPE
    SYNTAX          DisplayString
    ACCESS          read-write
    STATUS          mandatory
    DESCRIPTION     
            "The textual name of the log file. This name must be
             present when a row is active."
    ::= { siLogEntry 3 }

siLogMatchPattern OBJECT-TYPE
    SYNTAX          DisplayString
    ACCESS          read-write
    STATUS          mandatory
    DESCRIPTION     
            "A regular expression against which to match
             log file entries."
    ::= { siLogEntry 4 }

siLogMatchAllExceptPattern OBJECT-TYPE
    SYNTAX          TruthValue
    ACCESS          read-write
    STATUS          mandatory
    DESCRIPTION     
            "An option that turns on matching for 
             all lines that do not contain the regular expression."
    DEFVAL          { false }
    ::= { siLogEntry 5 }

siLogStartPosition OBJECT-TYPE
    SYNTAX          INTEGER
    ACCESS          read-write
    STATUS          mandatory
    DESCRIPTION     
            "The character position, within a log file entry,
             where regular expression matching will begin."
    ::= { siLogEntry 7 }

siLogStopPosition OBJECT-TYPE
    SYNTAX          INTEGER
    ACCESS          read-write
    STATUS          mandatory
    DESCRIPTION     
            "The character position, within a log file entry,
             after which regular expression matching will
             not take place."
    ::= { siLogEntry 8 }

siLogMatches OBJECT-TYPE
    SYNTAX          INTEGER
    ACCESS          read-only
    STATUS          mandatory
    DESCRIPTION     
            "The number of lines within a log file,
             that match the given regular expression."
    ::= { siLogEntry 9 }

siLogCommandOnMatch OBJECT-TYPE
    SYNTAX          DisplayString
    ACCESS          read-write
    STATUS          mandatory
    DESCRIPTION     
            "A command-line argument to be executed
             when a regular expression match has occurred."
    ::= { siLogEntry 10 }

siLogTrapOnMatch OBJECT-TYPE
    SYNTAX          TruthValue
    ACCESS          read-write
    STATUS          mandatory
    DESCRIPTION     
            "This value indicates whether a trap should or 
             should not be sent when a regular expression
             match occurs.  If true (1) a trap should be sent.
             If false (2) a trap should not be sent."
    DEFVAL          { false }
    ::= { siLogEntry 11 }

siLogSize OBJECT-TYPE
    SYNTAX          INTEGER
    ACCESS          read-only
    STATUS          mandatory
    DESCRIPTION     
            "The size of the log file in bytes."
    ::= { siLogEntry 12 }

siLogMaxSize OBJECT-TYPE
    SYNTAX          INTEGER
    ACCESS          read-write
    STATUS          mandatory
    DESCRIPTION     
            "The maximum byte size threshold of the log file."
    ::= { siLogEntry 13 }

siLogCommandOnMaxSize OBJECT-TYPE
    SYNTAX          DisplayString
    ACCESS          read-write
    STATUS          mandatory
    DESCRIPTION     
            "A command-line argument to be executed when
             the maximum log file size threshold is reached."
    ::= { siLogEntry 14 }

siLogTrapOnMaxSize OBJECT-TYPE
    SYNTAX          TruthValue
    ACCESS          read-write
    STATUS          mandatory
    DESCRIPTION     
            "This value indicates whether a trap should or
             should not be sent when the maximum size threshold 
             is reached.  If true (1) a trap should be sent.
             If false (2) a trap should not be sent."
    DEFVAL          { false }
    ::= { siLogEntry 15 }

siLogPollInterval OBJECT-TYPE
    SYNTAX          INTEGER
    ACCESS          read-write
    STATUS          mandatory
    DESCRIPTION     
            "The period, in seconds, when the log file
             should be checked to see if the file size threshold
             has been reached or if any regular expression matching
             has occurred."
    ::= { siLogEntry 16 }

siLogPollNow OBJECT-TYPE
    SYNTAX          TruthValue
    ACCESS          read-write
    STATUS          mandatory
    DESCRIPTION     
            "Setting this object to true (1) will cause the 
             log file be checked to see if the file size threshold
             has been reached or if any regular expression matching
             has occurred."
    DEFVAL          { false }
    ::= { siLogEntry 17 }

siLogOwner OBJECT-TYPE
    SYNTAX          DisplayString
    ACCESS          read-write
    STATUS          mandatory
    DESCRIPTION     
            "Configured owner of the log file."
    ::= { siLogEntry 27 }

siLogRowStatus OBJECT-TYPE
    SYNTAX          RowStatus
    ACCESS          read-write
    STATUS          mandatory
    DESCRIPTION     
            "The status of this log file entry."
    ::= { siLogEntry 28 }

siLogTraps OBJECT IDENTIFIER
    ::= { siLog 2 }

siLogTrapTextLine OBJECT-TYPE
    SYNTAX          DisplayString
    ACCESS          read-only
    STATUS          mandatory
    DESCRIPTION     
            "The first 255 characters of the log file text line
             where the regular expression match was found."
    ::= { siLogTraps 1 }

siLogMatchTrap TRAP-TYPE
    ENTERPRISE      siLogTraps
    VARIABLES       { siLogTrapTextLine }
--     STATUS          mandatory
    DESCRIPTION     
            "A trap indicating that a regular expression
             match has occurred."
    ::= 2

siLogMaxSizeTrap TRAP-TYPE
    ENTERPRISE      siLogTraps
    VARIABLES       { siLogMaxSize }
--     STATUS          mandatory
    DESCRIPTION     
            "A trap indicating that the log file size
             threshold has been exceeded."
    ::= 3

END -- end of module LOG-MIB.
