MIB-EMSPLUS-IPASOLINK-IPMPLS-MIB DEFINITIONS ::= BEGIN
    
    IMPORTS
        InterfaceIndex
            FROM IF-MIB
        InetAddress, InetAddressType
            FROM INET-ADDRESS-MIB
        OBJECT-TYPE
            FROM RFC-1212
        IpAddress, Opaque
            FROM RFC1155-SMI
        enterprises
            FROM SNMPv2-SMI;
    
    IpeStatsInfo ::=
        INTEGER { invalid(0), validNoMaint(1), validMaint(2),
                        invalidNoMaint(3), invalidMaint(4) }
    
    
    SeverityValue ::=
        INTEGER { cleared(1), indetermine(2), critical(3), major(4),
                        minor(5), warning(6), notReport(7) }
    
    
    -- 1.3.6.1.4.1.119
    nec OBJECT IDENTIFIER
        ::= { enterprises 119 }
    
    -- 1.3.6.1.4.1.119.2
    nec-mib OBJECT IDENTIFIER
        ::= { nec 2 }
    
    -- 1.3.6.1.4.1.119.2.3
    necProductDepend OBJECT IDENTIFIER
        ::= { nec-mib 3 }
    
    -- 1.3.6.1.4.1.119.2.3.69
    radioEquipment OBJECT IDENTIFIER
        ::= { necProductDepend 69 }
    
    -- 1.3.6.1.4.1.119.2.3.69.213
    commonPnmsPlus OBJECT IDENTIFIER
        ::= { radioEquipment 213 }
    
    -- 1.3.6.1.4.1.119.2.3.69.213.502
    ipasolink OBJECT IDENTIFIER
        ::= { commonPnmsPlus 502 }
    
    -- 1.3.6.1.4.1.119.2.3.69.213.502.501
    pasoNeoIpe-common OBJECT IDENTIFIER
        ::= { ipasolink 501 }
    
    -- 1.3.6.1.4.1.119.2.3.69.213.502.501.3
    alarmStatusGroup OBJECT IDENTIFIER
        ::= { pasoNeoIpe-common 3 }
    
    -- 1.3.6.1.4.1.119.2.3.69.213.502.501.3.60
    asIpMplsGroup OBJECT IDENTIFIER
        ::= { alarmStatusGroup 60 }
    
    -- 1.3.6.1.4.1.119.2.3.69.213.502.501.3.60.1
    asIpMplsEquipmentGroup OBJECT IDENTIFIER
        ::= { asIpMplsGroup 1 }
    
    -- 1.3.6.1.4.1.119.2.3.69.213.502.501.3.60.1.1
    asIpMplsEquipmentTable OBJECT-TYPE
        SYNTAX      SEQUENCE OF AsIpMplsEquipmentEntry
        ACCESS      not-accessible
        STATUS      mandatory
        DESCRIPTION
            "This table contains alarm and status information related to
             IP/MPLS mode per equipment."
        ::= { asIpMplsEquipmentGroup 1 }
    
    -- 1.3.6.1.4.1.119.2.3.69.213.502.501.3.60.1.1.1
    asIpMplsEquipmentEntry OBJECT-TYPE
        SYNTAX      AsIpMplsEquipmentEntry
        ACCESS      not-accessible
        STATUS      mandatory
        DESCRIPTION
            ""
        INDEX       { asIpMplsEquipmentNEAddressAddrType, asIpMplsEquipmentNEAddress, asIpMplsEquipmentIndex }
        ::= { asIpMplsEquipmentTable 1 }
    
    AsIpMplsEquipmentEntry ::= SEQUENCE {
        asIpMplsEquipmentIndex                  INTEGER,
        asIpMplsEquipmentNEAddress              InetAddress,
        asIpMplsEquipmentRibV4MaxRouteCount     INTEGER,
        asIpMplsEquipmentRibV4MaxRouteOverflow  SeverityValue,
        asIpMplsEquipmentRibV6MaxRouteCount     INTEGER,
        asIpMplsEquipmentRibV6MaxRouteOverflow  SeverityValue,
        asIpMplsEquipmentLspMaxCount            INTEGER,
        asIpMplsEquipmentLspMaxOverflow         SeverityValue,
        asIpMplsEquipmentHostMaxRouteCount      INTEGER,
        asIpMplsEquipmentHostMaxRouteLimitOver  SeverityValue,
        asIpMplsEquipmentNEAddressAddrType      InetAddressType
    }
    
    -- 1.3.6.1.4.1.119.2.3.69.213.502.501.3.60.1.1.1.1
    asIpMplsEquipmentIndex OBJECT-TYPE
        SYNTAX      INTEGER (1)
        ACCESS      not-accessible
        STATUS      mandatory
        DESCRIPTION
            "Index of this table."
        ::= { asIpMplsEquipmentEntry 1 }
    
    -- 1.3.6.1.4.1.119.2.3.69.213.502.501.3.60.1.1.1.2
    asIpMplsEquipmentNEAddress OBJECT-TYPE
        SYNTAX      InetAddress
        ACCESS      not-accessible
        STATUS      mandatory
        DESCRIPTION
            "reserved."
        ::= { asIpMplsEquipmentEntry 2 }
    
    -- 1.3.6.1.4.1.119.2.3.69.213.502.501.3.60.1.1.1.4
    asIpMplsEquipmentRibV4MaxRouteCount OBJECT-TYPE
        SYNTAX      INTEGER (1..8192)
        ACCESS      read-only
        STATUS      mandatory
        DESCRIPTION
            "This shows the current number of Route Information Base (RIB)
             entry for IPv4."
        ::= { asIpMplsEquipmentEntry 4 }
    
    -- 1.3.6.1.4.1.119.2.3.69.213.502.501.3.60.1.1.1.5
    asIpMplsEquipmentRibV4MaxRouteOverflow OBJECT-TYPE
        SYNTAX      SeverityValue
        ACCESS      read-only
        STATUS      mandatory
        DESCRIPTION
            "This status shows that RIB entry for IPv4 is full."
        ::= { asIpMplsEquipmentEntry 5 }
    
    -- 1.3.6.1.4.1.119.2.3.69.213.502.501.3.60.1.1.1.6
    asIpMplsEquipmentRibV6MaxRouteCount OBJECT-TYPE
        SYNTAX      INTEGER (1..1024)
        ACCESS      read-only
        STATUS      mandatory
        DESCRIPTION
            "This shows the current number of Route Information Base (RIB)
             entry for IPv6."
        ::= { asIpMplsEquipmentEntry 6 }
    
    -- 1.3.6.1.4.1.119.2.3.69.213.502.501.3.60.1.1.1.7
    asIpMplsEquipmentRibV6MaxRouteOverflow OBJECT-TYPE
        SYNTAX      SeverityValue
        ACCESS      read-only
        STATUS      mandatory
        DESCRIPTION
            "This status shows that RIB entry for IPv6 is full."
        ::= { asIpMplsEquipmentEntry 7 }
    
    -- 1.3.6.1.4.1.119.2.3.69.213.502.501.3.60.1.1.1.8
    asIpMplsEquipmentLspMaxCount OBJECT-TYPE
        SYNTAX      INTEGER (1..4096)
        ACCESS      read-only
        STATUS      mandatory
        DESCRIPTION
            "This shows the current number of Route Information Base (RIB)
             entry for LSP."
        ::= { asIpMplsEquipmentEntry 8 }
    
    -- 1.3.6.1.4.1.119.2.3.69.213.502.501.3.60.1.1.1.9
    asIpMplsEquipmentLspMaxOverflow OBJECT-TYPE
        SYNTAX      SeverityValue
        ACCESS      read-only
        STATUS      mandatory
        DESCRIPTION
            "This status shows that RIB LSP entry is full."
        ::= { asIpMplsEquipmentEntry 9 }
    
    -- 1.3.6.1.4.1.119.2.3.69.213.502.501.3.60.1.1.1.10
    asIpMplsEquipmentHostMaxRouteCount OBJECT-TYPE
        SYNTAX      INTEGER (1..8192)
        ACCESS      read-only
        STATUS      mandatory
        DESCRIPTION
            "This shows the current number of HOST entry."
        ::= { asIpMplsEquipmentEntry 10 }
    
    -- 1.3.6.1.4.1.119.2.3.69.213.502.501.3.60.1.1.1.11
    asIpMplsEquipmentHostMaxRouteLimitOver OBJECT-TYPE
        SYNTAX      SeverityValue
        ACCESS      read-only
        STATUS      mandatory
        DESCRIPTION
            "This status shows that RIB Host entry exceeds 90%."
        ::= { asIpMplsEquipmentEntry 11 }
    
    -- 1.3.6.1.4.1.119.2.3.69.213.502.501.3.60.1.1.1.1001
    asIpMplsEquipmentNEAddressAddrType OBJECT-TYPE
        SYNTAX      InetAddressType
        ACCESS      not-accessible
        STATUS      mandatory
        DESCRIPTION
            "Represents the IP address type of NE address index.
             Only ipv4(1) and ipv6(2) are supported."
        ::= { asIpMplsEquipmentEntry 1001 }
    
    -- 1.3.6.1.4.1.119.2.3.69.213.502.501.3.60.2
    asIpMplsBfdGroup OBJECT IDENTIFIER
        ::= { asIpMplsGroup 2 }
    
    -- 1.3.6.1.4.1.119.2.3.69.213.502.501.3.60.2.1
    asIpMplsBfdSessionTable OBJECT-TYPE
        SYNTAX      SEQUENCE OF AsIpMplsBfdSessionEntry
        ACCESS      not-accessible
        STATUS      mandatory
        DESCRIPTION
            "This table contains alarm and status information related to BFD
             Session entry."
        ::= { asIpMplsBfdGroup 1 }
    
    -- 1.3.6.1.4.1.119.2.3.69.213.502.501.3.60.2.1.1
    asIpMplsBfdSessionEntry OBJECT-TYPE
        SYNTAX      AsIpMplsBfdSessionEntry
        ACCESS      not-accessible
        STATUS      mandatory
        DESCRIPTION
            ""
        INDEX       { asIpMplsBfdSessionNEAddressAddrType, asIpMplsBfdSessionNEAddress, asIpMplsBfdSessionAlarmIndex }
        ::= { asIpMplsBfdSessionTable 1 }
    
    AsIpMplsBfdSessionEntry ::= SEQUENCE {
        asIpMplsBfdSessionAlarmIndex            INTEGER,
        asIpMplsBfdSessionNEAddress             InetAddress,
        asIpMplsBfdSessionAlarm                 SeverityValue,
        asIpMplsBfdSessionNEAddressAddrType     InetAddressType
    }
    
    -- 1.3.6.1.4.1.119.2.3.69.213.502.501.3.60.2.1.1.1
    asIpMplsBfdSessionAlarmIndex OBJECT-TYPE
        SYNTAX      INTEGER (1..65535)
        ACCESS      not-accessible
        STATUS      mandatory
        DESCRIPTION
            "Index of this table."
        ::= { asIpMplsBfdSessionEntry 1 }
    
    -- 1.3.6.1.4.1.119.2.3.69.213.502.501.3.60.2.1.1.2
    asIpMplsBfdSessionNEAddress OBJECT-TYPE
        SYNTAX      InetAddress
        ACCESS      not-accessible
        STATUS      mandatory
        DESCRIPTION
            "reserved."
        ::= { asIpMplsBfdSessionEntry 2 }
    
    -- 1.3.6.1.4.1.119.2.3.69.213.502.501.3.60.2.1.1.3
    asIpMplsBfdSessionAlarm OBJECT-TYPE
        SYNTAX      SeverityValue
        ACCESS      read-only
        STATUS      mandatory
        DESCRIPTION
            "This alarm will be asserted when the BFD session is down."
        ::= { asIpMplsBfdSessionEntry 3 }
    
    -- 1.3.6.1.4.1.119.2.3.69.213.502.501.3.60.2.1.1.1001
    asIpMplsBfdSessionNEAddressAddrType OBJECT-TYPE
        SYNTAX      InetAddressType
        ACCESS      not-accessible
        STATUS      mandatory
        DESCRIPTION
            "Represents the IP address type of NE address index.
             Only ipv4(1) and ipv6(2) are supported."
        ::= { asIpMplsBfdSessionEntry 1001 }
    
    -- 1.3.6.1.4.1.119.2.3.69.213.502.501.3.60.3
    asIpMplsLdpGroup OBJECT IDENTIFIER
        ::= { asIpMplsGroup 3 }
    
    -- 1.3.6.1.4.1.119.2.3.69.213.502.501.3.60.3.1
    asIpMplsLdpSessionTable OBJECT-TYPE
        SYNTAX      SEQUENCE OF AsIpMplsLdpSessionEntry
        ACCESS      not-accessible
        STATUS      mandatory
        DESCRIPTION
            "This table contains alarm and status information related to LDP
             Session entry."
        ::= { asIpMplsLdpGroup 1 }
    
    -- 1.3.6.1.4.1.119.2.3.69.213.502.501.3.60.3.1.1
    asIpMplsLdpSessionEntry OBJECT-TYPE
        SYNTAX      AsIpMplsLdpSessionEntry
        ACCESS      not-accessible
        STATUS      mandatory
        DESCRIPTION
            ""
        INDEX       { asIpMplsLdpSessionNEAddressAddrType, asIpMplsLdpSessionNEAddress, asIpMplsLdpSessionAlarmIndex }
        ::= { asIpMplsLdpSessionTable 1 }
    
    AsIpMplsLdpSessionEntry ::= SEQUENCE {
        asIpMplsLdpSessionAlarmIndex            INTEGER,
        asIpMplsLdpSessionNEAddress             InetAddress,
        asIpMplsLdpSessionAlarm                 SeverityValue,
        asIpMplsLdpSessionNEAddressAddrType     InetAddressType
    }
    
    -- 1.3.6.1.4.1.119.2.3.69.213.502.501.3.60.3.1.1.1
    asIpMplsLdpSessionAlarmIndex OBJECT-TYPE
        SYNTAX      INTEGER (1..65535)
        ACCESS      not-accessible
        STATUS      mandatory
        DESCRIPTION
            "Index of this table."
        ::= { asIpMplsLdpSessionEntry 1 }
    
    -- 1.3.6.1.4.1.119.2.3.69.213.502.501.3.60.3.1.1.2
    asIpMplsLdpSessionNEAddress OBJECT-TYPE
        SYNTAX      InetAddress
        ACCESS      not-accessible
        STATUS      mandatory
        DESCRIPTION
            "reserved."
        ::= { asIpMplsLdpSessionEntry 2 }
    
    -- 1.3.6.1.4.1.119.2.3.69.213.502.501.3.60.3.1.1.3
    asIpMplsLdpSessionAlarm OBJECT-TYPE
        SYNTAX      SeverityValue
        ACCESS      read-only
        STATUS      mandatory
        DESCRIPTION
            "This alarm will be asserted when the LDP session is down."
        ::= { asIpMplsLdpSessionEntry 3 }
    
    -- 1.3.6.1.4.1.119.2.3.69.213.502.501.3.60.3.1.1.1001
    asIpMplsLdpSessionNEAddressAddrType OBJECT-TYPE
        SYNTAX      InetAddressType
        ACCESS      not-accessible
        STATUS      mandatory
        DESCRIPTION
            "Represents the IP address type of NE address index.
             Only ipv4(1) and ipv6(2) are supported."
        ::= { asIpMplsLdpSessionEntry 1001 }
    
    -- 1.3.6.1.4.1.119.2.3.69.213.502.501.3.60.4
    asIpMplsRsvpGroup OBJECT IDENTIFIER
        ::= { asIpMplsGroup 4 }
    
    -- 1.3.6.1.4.1.119.2.3.69.213.502.501.3.60.4.1
    asIpMplsRsvpLspTable OBJECT-TYPE
        SYNTAX      SEQUENCE OF AsIpMplsRsvpLspEntry
        ACCESS      not-accessible
        STATUS      mandatory
        DESCRIPTION
            "This table contains alarm and status information related to RSVP
             entry per LSP."
        ::= { asIpMplsRsvpGroup 1 }
    
    -- 1.3.6.1.4.1.119.2.3.69.213.502.501.3.60.4.1.1
    asIpMplsRsvpLspEntry OBJECT-TYPE
        SYNTAX      AsIpMplsRsvpLspEntry
        ACCESS      not-accessible
        STATUS      mandatory
        DESCRIPTION
            ""
        INDEX       { asIpMplsRsvpLspNEAddressAddrType, asIpMplsRsvpLspNEAddress, asIpMplsRsvpLspAlarmIndex }
        ::= { asIpMplsRsvpLspTable 1 }
    
    AsIpMplsRsvpLspEntry ::= SEQUENCE {
        asIpMplsRsvpLspAlarmIndex           INTEGER,
        asIpMplsRsvpLspNEAddress            InetAddress,
        asIpMplsRsvpLspAlarm                SeverityValue,
        asIpMplsRsvpLspNEAddressAddrType    InetAddressType
    }
    
    -- 1.3.6.1.4.1.119.2.3.69.213.502.501.3.60.4.1.1.1
    asIpMplsRsvpLspAlarmIndex OBJECT-TYPE
        SYNTAX      INTEGER (1..65535)
        ACCESS      not-accessible
        STATUS      mandatory
        DESCRIPTION
            "Index of this table."
        ::= { asIpMplsRsvpLspEntry 1 }
    
    -- 1.3.6.1.4.1.119.2.3.69.213.502.501.3.60.4.1.1.2
    asIpMplsRsvpLspNEAddress OBJECT-TYPE
        SYNTAX      InetAddress
        ACCESS      not-accessible
        STATUS      mandatory
        DESCRIPTION
            "reserved."
        ::= { asIpMplsRsvpLspEntry 2 }
    
    -- 1.3.6.1.4.1.119.2.3.69.213.502.501.3.60.4.1.1.3
    asIpMplsRsvpLspAlarm OBJECT-TYPE
        SYNTAX      SeverityValue
        ACCESS      read-only
        STATUS      mandatory
        DESCRIPTION
            "When the RSVP LSP is failure, this Alarm is raised.  This alarm
             is detected by only Head End router."
        ::= { asIpMplsRsvpLspEntry 3 }
    
    -- 1.3.6.1.4.1.119.2.3.69.213.502.501.3.60.4.1.1.1001
    asIpMplsRsvpLspNEAddressAddrType OBJECT-TYPE
        SYNTAX      InetAddressType
        ACCESS      not-accessible
        STATUS      mandatory
        DESCRIPTION
            "Represents the IP address type of NE address index.
             Only ipv4(1) and ipv6(2) are supported."
        ::= { asIpMplsRsvpLspEntry 1001 }
    
    -- 1.3.6.1.4.1.119.2.3.69.213.502.501.11
    rmonGroup OBJECT IDENTIFIER
        ::= { pasoNeoIpe-common 11 }
    
    -- 1.3.6.1.4.1.119.2.3.69.213.502.501.11.60
    rmonIpMplsGroup OBJECT IDENTIFIER
        ::= { rmonGroup 60 }
    
    -- 1.3.6.1.4.1.119.2.3.69.213.502.501.11.60.1
    rmon15minIpMplsCounterGroup OBJECT IDENTIFIER
        ::= { rmonIpMplsGroup 1 }
    
    -- 1.3.6.1.4.1.119.2.3.69.213.502.501.11.60.1.1
    rmon15minIpMplsLspCounterGroup OBJECT IDENTIFIER
        ::= { rmon15minIpMplsCounterGroup 1 }
    
    -- 1.3.6.1.4.1.119.2.3.69.213.502.501.11.60.1.1.1
    rmon15minIpMplsLspInCounterTable OBJECT-TYPE
        SYNTAX      SEQUENCE OF Rmon15minIpMplsLspInCounterEntry
        ACCESS      not-accessible
        STATUS      mandatory
        DESCRIPTION
            "This table contains 15 minutes incmoing LSP counter for IP/MPLS
             mode. The counted value is reset every 15 minutes.
             The filter for SNMP-Get will be specified in
             provIpMplsLspCounterFilterTable to be restricted the get
             objects."
        ::= { rmon15minIpMplsLspCounterGroup 1 }
    
    -- 1.3.6.1.4.1.119.2.3.69.213.502.501.11.60.1.1.1.1
    rmon15minIpMplsLspInCounterEntry OBJECT-TYPE
        SYNTAX      Rmon15minIpMplsLspInCounterEntry
        ACCESS      not-accessible
        STATUS      mandatory
        DESCRIPTION
            ""
        INDEX       { rmon15minIpMplsLspInCounterNEAddressAddrType, rmon15minIpMplsLspInCounterNEAddress, rmon15minIpMplsLspInCounterIndex }
        ::= { rmon15minIpMplsLspInCounterTable 1 }
    
    Rmon15minIpMplsLspInCounterEntry ::= SEQUENCE {
        rmon15minIpMplsLspInCounterIndex                INTEGER,
        rmon15minIpMplsLspInCounterNEAddress            InetAddress,
        rmon15minIpMplsLspInCounterHCPktsStatus         IpeStatsInfo,
        rmon15minIpMplsLspInCounterHCOctetsStatus       IpeStatsInfo,
        rmon15minIpMplsLspInCounterNEAddressAddrType    InetAddressType
    }
    
    -- 1.3.6.1.4.1.119.2.3.69.213.502.501.11.60.1.1.1.1.1
    rmon15minIpMplsLspInCounterIndex OBJECT-TYPE
        SYNTAX      INTEGER (1..2000)
        ACCESS      not-accessible
        STATUS      mandatory
        DESCRIPTION
            "This index object specify the key for incoming LSP.  This key is
             related to provIpMplsMplsInSegmentIndex."
        ::= { rmon15minIpMplsLspInCounterEntry 1 }
    
    -- 1.3.6.1.4.1.119.2.3.69.213.502.501.11.60.1.1.1.1.2
    rmon15minIpMplsLspInCounterNEAddress OBJECT-TYPE
        SYNTAX      InetAddress
        ACCESS      not-accessible
        STATUS      mandatory
        DESCRIPTION
            "reserved."
        ::= { rmon15minIpMplsLspInCounterEntry 2 }
    
    -- 1.3.6.1.4.1.119.2.3.69.213.502.501.11.60.1.1.1.1.4
    rmon15minIpMplsLspInCounterHCPktsStatus OBJECT-TYPE
        SYNTAX      IpeStatsInfo
        ACCESS      read-only
        STATUS      mandatory
        DESCRIPTION
            "RMON 15 minutes Packets Status."
        ::= { rmon15minIpMplsLspInCounterEntry 4 }
    
    -- 1.3.6.1.4.1.119.2.3.69.213.502.501.11.60.1.1.1.1.6
    rmon15minIpMplsLspInCounterHCOctetsStatus OBJECT-TYPE
        SYNTAX      IpeStatsInfo
        ACCESS      read-only
        STATUS      mandatory
        DESCRIPTION
            "RMON 15 minutes Octets Status."
        ::= { rmon15minIpMplsLspInCounterEntry 6 }
    
    -- 1.3.6.1.4.1.119.2.3.69.213.502.501.11.60.1.1.1.1.1001
    rmon15minIpMplsLspInCounterNEAddressAddrType OBJECT-TYPE
        SYNTAX      InetAddressType
        ACCESS      not-accessible
        STATUS      mandatory
        DESCRIPTION
            "Represents the IP address type of NE address index.
             Only ipv4(1) and ipv6(2) are supported."
        ::= { rmon15minIpMplsLspInCounterEntry 1001 }
    
    -- 1.3.6.1.4.1.119.2.3.69.213.502.501.11.60.1.1.2
    rmon15minIpMplsLspOutCounterTable OBJECT-TYPE
        SYNTAX      SEQUENCE OF Rmon15minIpMplsLspOutCounterEntry
        ACCESS      not-accessible
        STATUS      mandatory
        DESCRIPTION
            "This table contains 15 minutes outgoing LSP counter for IP/MPLS
             mode. The counted value is reset every 15 minutes.
             The filter for SNMP-Get will be specified in
             provIpMplsLspCounterFilterTable to be restricted the get
             objects."
        ::= { rmon15minIpMplsLspCounterGroup 2 }
    
    -- 1.3.6.1.4.1.119.2.3.69.213.502.501.11.60.1.1.2.1
    rmon15minIpMplsLspOutCounterEntry OBJECT-TYPE
        SYNTAX      Rmon15minIpMplsLspOutCounterEntry
        ACCESS      not-accessible
        STATUS      mandatory
        DESCRIPTION
            ""
        INDEX       { rmon15minIpMplsLspOutCounterNEAddressAddrType, rmon15minIpMplsLspOutCounterNEAddress, rmon15minIpMplsLspOutCounterIndex }
        ::= { rmon15minIpMplsLspOutCounterTable 1 }
    
    Rmon15minIpMplsLspOutCounterEntry ::= SEQUENCE {
        rmon15minIpMplsLspOutCounterIndex               INTEGER,
        rmon15minIpMplsLspOutCounterNEAddress           InetAddress,
        rmon15minIpMplsLspOutCounterHCPktsStatus        IpeStatsInfo,
        rmon15minIpMplsLspOutCounterHCOctetsStatus      IpeStatsInfo,
        rmon15minIpMplsLspOutCounterNEAddressAddrType   InetAddressType
    }
    
    -- 1.3.6.1.4.1.119.2.3.69.213.502.501.11.60.1.1.2.1.1
    rmon15minIpMplsLspOutCounterIndex OBJECT-TYPE
        SYNTAX      INTEGER (1..2000)
        ACCESS      not-accessible
        STATUS      mandatory
        DESCRIPTION
            "This index object specify the key for outgoing LSP.  This key is
             related to provIpMplsMplsOutSegmentIndex."
        ::= { rmon15minIpMplsLspOutCounterEntry 1 }
    
    -- 1.3.6.1.4.1.119.2.3.69.213.502.501.11.60.1.1.2.1.2
    rmon15minIpMplsLspOutCounterNEAddress OBJECT-TYPE
        SYNTAX      InetAddress
        ACCESS      not-accessible
        STATUS      mandatory
        DESCRIPTION
            "reserved."
        ::= { rmon15minIpMplsLspOutCounterEntry 2 }
    
    -- 1.3.6.1.4.1.119.2.3.69.213.502.501.11.60.1.1.2.1.4
    rmon15minIpMplsLspOutCounterHCPktsStatus OBJECT-TYPE
        SYNTAX      IpeStatsInfo
        ACCESS      read-only
        STATUS      mandatory
        DESCRIPTION
            "RMON 15 minutes Packets Status."
        ::= { rmon15minIpMplsLspOutCounterEntry 4 }
    
    -- 1.3.6.1.4.1.119.2.3.69.213.502.501.11.60.1.1.2.1.6
    rmon15minIpMplsLspOutCounterHCOctetsStatus OBJECT-TYPE
        SYNTAX      IpeStatsInfo
        ACCESS      read-only
        STATUS      mandatory
        DESCRIPTION
            "RMON 15 minutes Octets Status."
        ::= { rmon15minIpMplsLspOutCounterEntry 6 }
    
    -- 1.3.6.1.4.1.119.2.3.69.213.502.501.11.60.1.1.2.1.1001
    rmon15minIpMplsLspOutCounterNEAddressAddrType OBJECT-TYPE
        SYNTAX      InetAddressType
        ACCESS      not-accessible
        STATUS      mandatory
        DESCRIPTION
            "Represents the IP address type of NE address index.
             Only ipv4(1) and ipv6(2) are supported."
        ::= { rmon15minIpMplsLspOutCounterEntry 1001 }
    
    -- 1.3.6.1.4.1.119.2.3.69.213.502.501.11.60.1.2
    rmon15minIpMplsVlanPerPortCounterTable OBJECT-TYPE
        SYNTAX      SEQUENCE OF Rmon15minIpMplsVlanPerPortCounterEntry
        ACCESS      not-accessible
        STATUS      mandatory
        DESCRIPTION
            "This table contains 15 minutes VLAN per port counter. The
             counted value is reset every 15 minutes."
        ::= { rmon15minIpMplsCounterGroup 2 }
    
    -- 1.3.6.1.4.1.119.2.3.69.213.502.501.11.60.1.2.1
    rmon15minIpMplsVlanPerPortCounterEntry OBJECT-TYPE
        SYNTAX      Rmon15minIpMplsVlanPerPortCounterEntry
        ACCESS      not-accessible
        STATUS      mandatory
        DESCRIPTION
            ""
        INDEX       { rmon15minIpMplsVlanPerPortCounterNEAddressAddrType, rmon15minIpMplsVlanPerPortCounterNEAddress, rmon15minIpMplsVlanPerPortCounterPortIndex,
                      rmon15minIpMplsVlanPerPortCounterVlanId }
        ::= { rmon15minIpMplsVlanPerPortCounterTable 1 }
    
    Rmon15minIpMplsVlanPerPortCounterEntry ::= SEQUENCE {
        rmon15minIpMplsVlanPerPortCounterPortIndex          InterfaceIndex,
        rmon15minIpMplsVlanPerPortCounterVlanId             INTEGER,
        rmon15minIpMplsVlanPerPortCounterNEAddress          InetAddress,
        rmon15minIpMplsVlanPerPortCounterHCRxPktsStatus     IpeStatsInfo,
        rmon15minIpMplsVlanPerPortCounterHCTxPktsStatus     IpeStatsInfo,
        rmon15minIpMplsVlanPerPortCounterHCRxOctetsStatus   IpeStatsInfo,
        rmon15minIpMplsVlanPerPortCounterHCTxOctetsStatus   IpeStatsInfo,
        rmon15minIpMplsVlanPerPortCounterNEAddressAddrType  InetAddressType
    }
    
    -- 1.3.6.1.4.1.119.2.3.69.213.502.501.11.60.1.2.1.1
    rmon15minIpMplsVlanPerPortCounterPortIndex OBJECT-TYPE
        SYNTAX      InterfaceIndex
        ACCESS      not-accessible
        STATUS      mandatory
        DESCRIPTION
            "This index object specify the ether port which has VLAN per port
             to be counted the RMON."
        ::= { rmon15minIpMplsVlanPerPortCounterEntry 1 }
    
    -- 1.3.6.1.4.1.119.2.3.69.213.502.501.11.60.1.2.1.2
    rmon15minIpMplsVlanPerPortCounterVlanId OBJECT-TYPE
        SYNTAX      INTEGER (1..4094)
        ACCESS      not-accessible
        STATUS      mandatory
        DESCRIPTION
            "This index object specify the VLAN ID to be counted the RMON."
        ::= { rmon15minIpMplsVlanPerPortCounterEntry 2 }
    
    -- 1.3.6.1.4.1.119.2.3.69.213.502.501.11.60.1.2.1.3
    rmon15minIpMplsVlanPerPortCounterNEAddress OBJECT-TYPE
        SYNTAX      InetAddress
        ACCESS      not-accessible
        STATUS      mandatory
        DESCRIPTION
            "reserved."
        ::= { rmon15minIpMplsVlanPerPortCounterEntry 3 }
    
    -- 1.3.6.1.4.1.119.2.3.69.213.502.501.11.60.1.2.1.5
    rmon15minIpMplsVlanPerPortCounterHCRxPktsStatus OBJECT-TYPE
        SYNTAX      IpeStatsInfo
        ACCESS      read-only
        STATUS      mandatory
        DESCRIPTION
            "RMON 15 minutes RX Packets Status."
        ::= { rmon15minIpMplsVlanPerPortCounterEntry 5 }
    
    -- 1.3.6.1.4.1.119.2.3.69.213.502.501.11.60.1.2.1.7
    rmon15minIpMplsVlanPerPortCounterHCTxPktsStatus OBJECT-TYPE
        SYNTAX      IpeStatsInfo
        ACCESS      read-only
        STATUS      mandatory
        DESCRIPTION
            "RMON 15 minutes TX Packets Status."
        ::= { rmon15minIpMplsVlanPerPortCounterEntry 7 }
    
    -- 1.3.6.1.4.1.119.2.3.69.213.502.501.11.60.1.2.1.9
    rmon15minIpMplsVlanPerPortCounterHCRxOctetsStatus OBJECT-TYPE
        SYNTAX      IpeStatsInfo
        ACCESS      read-only
        STATUS      mandatory
        DESCRIPTION
            "RMON 15 minutes RX Octets Status."
        ::= { rmon15minIpMplsVlanPerPortCounterEntry 9 }
    
    -- 1.3.6.1.4.1.119.2.3.69.213.502.501.11.60.1.2.1.11
    rmon15minIpMplsVlanPerPortCounterHCTxOctetsStatus OBJECT-TYPE
        SYNTAX      IpeStatsInfo
        ACCESS      read-only
        STATUS      mandatory
        DESCRIPTION
            "RMON 15 minutes TX Octets Status."
        ::= { rmon15minIpMplsVlanPerPortCounterEntry 11 }
    
    -- 1.3.6.1.4.1.119.2.3.69.213.502.501.11.60.1.2.1.1001
    rmon15minIpMplsVlanPerPortCounterNEAddressAddrType OBJECT-TYPE
        SYNTAX      InetAddressType
        ACCESS      not-accessible
        STATUS      mandatory
        DESCRIPTION
            "Represents the IP address type of NE address index.
             Only ipv4(1) and ipv6(2) are supported."
        ::= { rmon15minIpMplsVlanPerPortCounterEntry 1001 }
    
    -- 1.3.6.1.4.1.119.2.3.69.213.502.501.11.60.2
    rmon1dayIpMplsCounterGroup OBJECT IDENTIFIER
        ::= { rmonIpMplsGroup 2 }
    
    -- 1.3.6.1.4.1.119.2.3.69.213.502.501.11.60.2.1
    rmon1dayIpMplsLspCounterGroup OBJECT IDENTIFIER
        ::= { rmon1dayIpMplsCounterGroup 1 }
    
    -- 1.3.6.1.4.1.119.2.3.69.213.502.501.11.60.2.1.1
    rmon1dayIpMplsLspInCounterTable OBJECT-TYPE
        SYNTAX      SEQUENCE OF Rmon1dayIpMplsLspInCounterEntry
        ACCESS      not-accessible
        STATUS      mandatory
        DESCRIPTION
            "This table contains 1 day incoming LSP counter for IP/MPLS mode.
             The counted value is reset every day.
             The filter for SNMP-Get will be specified in
             provIpMplsLspCounterFilterTable to be restricted the get
             objects."
        ::= { rmon1dayIpMplsLspCounterGroup 1 }
    
    -- 1.3.6.1.4.1.119.2.3.69.213.502.501.11.60.2.1.1.1
    rmon1dayIpMplsLspInCounterEntry OBJECT-TYPE
        SYNTAX      Rmon1dayIpMplsLspInCounterEntry
        ACCESS      not-accessible
        STATUS      mandatory
        DESCRIPTION
            ""
        INDEX       { rmon1dayIpMplsLspInCounterNEAddressAddrType, rmon1dayIpMplsLspInCounterNEAddress, rmon1dayIpMplsLspInCounterIndex }
        ::= { rmon1dayIpMplsLspInCounterTable 1 }
    
    Rmon1dayIpMplsLspInCounterEntry ::= SEQUENCE {
        rmon1dayIpMplsLspInCounterIndex                 INTEGER,
        rmon1dayIpMplsLspInCounterNEAddress             InetAddress,
        rmon1dayIpMplsLspInCounterHCPktsStatus          IpeStatsInfo,
        rmon1dayIpMplsLspInCounterHCOctetsStatus        IpeStatsInfo,
        rmon1dayIpMplsLspInCounterNEAddressAddrType     InetAddressType
    }
    
    -- 1.3.6.1.4.1.119.2.3.69.213.502.501.11.60.2.1.1.1.1
    rmon1dayIpMplsLspInCounterIndex OBJECT-TYPE
        SYNTAX      INTEGER (1..2000)
        ACCESS      not-accessible
        STATUS      mandatory
        DESCRIPTION
            "This index object specify the key for incoming LSP.  This key is
             related to provIpMplsMplsInSegmentIndex."
        ::= { rmon1dayIpMplsLspInCounterEntry 1 }
    
    -- 1.3.6.1.4.1.119.2.3.69.213.502.501.11.60.2.1.1.1.2
    rmon1dayIpMplsLspInCounterNEAddress OBJECT-TYPE
        SYNTAX      InetAddress
        ACCESS      not-accessible
        STATUS      mandatory
        DESCRIPTION
            "reserved."
        ::= { rmon1dayIpMplsLspInCounterEntry 2 }
    
    -- 1.3.6.1.4.1.119.2.3.69.213.502.501.11.60.2.1.1.1.4
    rmon1dayIpMplsLspInCounterHCPktsStatus OBJECT-TYPE
        SYNTAX      IpeStatsInfo
        ACCESS      read-only
        STATUS      mandatory
        DESCRIPTION
            "RMON 1 day Packets Status."
        ::= { rmon1dayIpMplsLspInCounterEntry 4 }
    
    -- 1.3.6.1.4.1.119.2.3.69.213.502.501.11.60.2.1.1.1.6
    rmon1dayIpMplsLspInCounterHCOctetsStatus OBJECT-TYPE
        SYNTAX      IpeStatsInfo
        ACCESS      read-only
        STATUS      mandatory
        DESCRIPTION
            "RMON 1 day Octets Status."
        ::= { rmon1dayIpMplsLspInCounterEntry 6 }
    
    -- 1.3.6.1.4.1.119.2.3.69.213.502.501.11.60.2.1.1.1.1001
    rmon1dayIpMplsLspInCounterNEAddressAddrType OBJECT-TYPE
        SYNTAX      InetAddressType
        ACCESS      not-accessible
        STATUS      mandatory
        DESCRIPTION
            "Represents the IP address type of NE address index.
             Only ipv4(1) and ipv6(2) are supported."
        ::= { rmon1dayIpMplsLspInCounterEntry 1001 }
    
    -- 1.3.6.1.4.1.119.2.3.69.213.502.501.11.60.2.1.2
    rmon1dayIpMplsLspOutCounterTable OBJECT-TYPE
        SYNTAX      SEQUENCE OF Rmon1dayIpMplsLspOutCounterEntry
        ACCESS      not-accessible
        STATUS      mandatory
        DESCRIPTION
            "This table contains 1 day outgoing LSP counter for IP/MPLS mode.
             The counted value is reset every day.
             The filter for SNMP-Get will be specified in
             provIpMplsLspCounterFilterTable to be restricted the get
             objects."
        ::= { rmon1dayIpMplsLspCounterGroup 2 }
    
    -- 1.3.6.1.4.1.119.2.3.69.213.502.501.11.60.2.1.2.1
    rmon1dayIpMplsLspOutCounterEntry OBJECT-TYPE
        SYNTAX      Rmon1dayIpMplsLspOutCounterEntry
        ACCESS      not-accessible
        STATUS      mandatory
        DESCRIPTION
            ""
        INDEX       { rmon1dayIpMplsLspOutCounterNEAddressAddrType, rmon1dayIpMplsLspOutCounterNEAddress, rmon1dayIpMplsLspOutCounterIndex }
        ::= { rmon1dayIpMplsLspOutCounterTable 1 }
    
    Rmon1dayIpMplsLspOutCounterEntry ::= SEQUENCE {
        rmon1dayIpMplsLspOutCounterIndex                INTEGER,
        rmon1dayIpMplsLspOutCounterNEAddress            InetAddress,
        rmon1dayIpMplsLspOutCounterHCPktsStatus         IpeStatsInfo,
        rmon1dayIpMplsLspOutCounterHCOctetsStatus       IpeStatsInfo,
        rmon1dayIpMplsLspOutCounterNEAddressAddrType    InetAddressType
    }
    
    -- 1.3.6.1.4.1.119.2.3.69.213.502.501.11.60.2.1.2.1.1
    rmon1dayIpMplsLspOutCounterIndex OBJECT-TYPE
        SYNTAX      INTEGER (1..2000)
        ACCESS      not-accessible
        STATUS      mandatory
        DESCRIPTION
            "This index object specify the key for outgoing LSP.  This key is
             related to provIpMplsMplsOutSegmentIndex."
        ::= { rmon1dayIpMplsLspOutCounterEntry 1 }
    
    -- 1.3.6.1.4.1.119.2.3.69.213.502.501.11.60.2.1.2.1.2
    rmon1dayIpMplsLspOutCounterNEAddress OBJECT-TYPE
        SYNTAX      InetAddress
        ACCESS      not-accessible
        STATUS      mandatory
        DESCRIPTION
            "reserved."
        ::= { rmon1dayIpMplsLspOutCounterEntry 2 }
    
    -- 1.3.6.1.4.1.119.2.3.69.213.502.501.11.60.2.1.2.1.4
    rmon1dayIpMplsLspOutCounterHCPktsStatus OBJECT-TYPE
        SYNTAX      IpeStatsInfo
        ACCESS      read-only
        STATUS      mandatory
        DESCRIPTION
            "RMON 1 day Packets Status."
        ::= { rmon1dayIpMplsLspOutCounterEntry 4 }
    
    -- 1.3.6.1.4.1.119.2.3.69.213.502.501.11.60.2.1.2.1.6
    rmon1dayIpMplsLspOutCounterHCOctetsStatus OBJECT-TYPE
        SYNTAX      IpeStatsInfo
        ACCESS      read-only
        STATUS      mandatory
        DESCRIPTION
            "RMON 1 day Octets Status."
        ::= { rmon1dayIpMplsLspOutCounterEntry 6 }
    
    -- 1.3.6.1.4.1.119.2.3.69.213.502.501.11.60.2.1.2.1.1001
    rmon1dayIpMplsLspOutCounterNEAddressAddrType OBJECT-TYPE
        SYNTAX      InetAddressType
        ACCESS      not-accessible
        STATUS      mandatory
        DESCRIPTION
            "Represents the IP address type of NE address index.
             Only ipv4(1) and ipv6(2) are supported."
        ::= { rmon1dayIpMplsLspOutCounterEntry 1001 }
    
    -- 1.3.6.1.4.1.119.2.3.69.213.502.501.11.60.2.2
    rmon1dayIpMplsVlanPerPortCounterTable OBJECT-TYPE
        SYNTAX      SEQUENCE OF Rmon1dayIpMplsVlanPerPortCounterEntry
        ACCESS      not-accessible
        STATUS      mandatory
        DESCRIPTION
            "This table contains 1 day VLAN per port counter. The counted
             value is reset every day."
        ::= { rmon1dayIpMplsCounterGroup 2 }
    
    -- 1.3.6.1.4.1.119.2.3.69.213.502.501.11.60.2.2.1
    rmon1dayIpMplsVlanPerPortCounterEntry OBJECT-TYPE
        SYNTAX      Rmon1dayIpMplsVlanPerPortCounterEntry
        ACCESS      not-accessible
        STATUS      mandatory
        DESCRIPTION
            ""
        INDEX       { rmon1dayIpMplsVlanPerPortCounterNEAddressAddrType, rmon1dayIpMplsVlanPerPortCounterNEAddress, rmon1dayIpMplsVlanPerPortCounterPortIndex,
                      rmon1dayIpMplsVlanPerPortCounterVlanId }
        ::= { rmon1dayIpMplsVlanPerPortCounterTable 1 }
    
    Rmon1dayIpMplsVlanPerPortCounterEntry ::= SEQUENCE {
        rmon1dayIpMplsVlanPerPortCounterPortIndex           InterfaceIndex,
        rmon1dayIpMplsVlanPerPortCounterVlanId              INTEGER,
        rmon1dayIpMplsVlanPerPortCounterNEAddress           InetAddress,
        rmon1dayIpMplsVlanPerPortCounterHCRxPktsStatus      IpeStatsInfo,
        rmon1dayIpMplsVlanPerPortCounterHCTxPktsStatus      IpeStatsInfo,
        rmon1dayIpMplsVlanPerPortCounterHCRxOctetsStatus    IpeStatsInfo,
        rmon1dayIpMplsVlanPerPortCounterHCTxOctetsStatus    IpeStatsInfo,
        rmon1dayIpMplsVlanPerPortCounterNEAddressAddrType   InetAddressType
    }
    
    -- 1.3.6.1.4.1.119.2.3.69.213.502.501.11.60.2.2.1.1
    rmon1dayIpMplsVlanPerPortCounterPortIndex OBJECT-TYPE
        SYNTAX      InterfaceIndex
        ACCESS      not-accessible
        STATUS      mandatory
        DESCRIPTION
            "This index object specify the ether port which has VLAN per port
             to be counted the RMON."
        ::= { rmon1dayIpMplsVlanPerPortCounterEntry 1 }
    
    -- 1.3.6.1.4.1.119.2.3.69.213.502.501.11.60.2.2.1.2
    rmon1dayIpMplsVlanPerPortCounterVlanId OBJECT-TYPE
        SYNTAX      INTEGER (1..4094)
        ACCESS      not-accessible
        STATUS      mandatory
        DESCRIPTION
            "This index object specify the VLAN ID to be counted the RMON."
        ::= { rmon1dayIpMplsVlanPerPortCounterEntry 2 }
    
    -- 1.3.6.1.4.1.119.2.3.69.213.502.501.11.60.2.2.1.3
    rmon1dayIpMplsVlanPerPortCounterNEAddress OBJECT-TYPE
        SYNTAX      InetAddress
        ACCESS      not-accessible
        STATUS      mandatory
        DESCRIPTION
            "reserved."
        ::= { rmon1dayIpMplsVlanPerPortCounterEntry 3 }
    
    -- 1.3.6.1.4.1.119.2.3.69.213.502.501.11.60.2.2.1.5
    rmon1dayIpMplsVlanPerPortCounterHCRxPktsStatus OBJECT-TYPE
        SYNTAX      IpeStatsInfo
        ACCESS      read-only
        STATUS      mandatory
        DESCRIPTION
            "RMON 1 day RX Packets Status."
        ::= { rmon1dayIpMplsVlanPerPortCounterEntry 5 }
    
    -- 1.3.6.1.4.1.119.2.3.69.213.502.501.11.60.2.2.1.7
    rmon1dayIpMplsVlanPerPortCounterHCTxPktsStatus OBJECT-TYPE
        SYNTAX      IpeStatsInfo
        ACCESS      read-only
        STATUS      mandatory
        DESCRIPTION
            "RMON 1 day TX Packets Status."
        ::= { rmon1dayIpMplsVlanPerPortCounterEntry 7 }
    
    -- 1.3.6.1.4.1.119.2.3.69.213.502.501.11.60.2.2.1.9
    rmon1dayIpMplsVlanPerPortCounterHCRxOctetsStatus OBJECT-TYPE
        SYNTAX      IpeStatsInfo
        ACCESS      read-only
        STATUS      mandatory
        DESCRIPTION
            "RMON 1 day RX Octets Status."
        ::= { rmon1dayIpMplsVlanPerPortCounterEntry 9 }
    
    -- 1.3.6.1.4.1.119.2.3.69.213.502.501.11.60.2.2.1.11
    rmon1dayIpMplsVlanPerPortCounterHCTxOctetsStatus OBJECT-TYPE
        SYNTAX      IpeStatsInfo
        ACCESS      read-only
        STATUS      mandatory
        DESCRIPTION
            "RMON 1 day TX Octets Status."
        ::= { rmon1dayIpMplsVlanPerPortCounterEntry 11 }
    
    -- 1.3.6.1.4.1.119.2.3.69.213.502.501.11.60.2.2.1.1001
    rmon1dayIpMplsVlanPerPortCounterNEAddressAddrType OBJECT-TYPE
        SYNTAX      InetAddressType
        ACCESS      not-accessible
        STATUS      mandatory
        DESCRIPTION
            "Represents the IP address type of NE address index.
             Only ipv4(1) and ipv6(2) are supported."
        ::= { rmon1dayIpMplsVlanPerPortCounterEntry 1001 }
    
END -- end of module MIB-EMSPLUS-IPASOLINK-IPMPLS-MIB.
