-- EventManager.MIB : netQoS Event Manager MIB extensions
NQem-MIB DEFINITIONS ::= BEGIN

		IMPORTS
			enterprises, NetworkAddress, IpAddress, Counter		FROM RFC1155-SMI
			DisplayString										FROM RFC1213-MIB
			OBJECT-TYPE											FROM SNMPv2-SMI
			TRAP-TYPE											FROM SNMPv2-CONF;

		-- netQoS enterprise

		netQoS	OBJECT IDENTIFIER ::= {enterprises 4498}

		-- Various netQoS applications
		
		eventManager	OBJECT IDENTIFIER ::= {netQoS 7}
		event		OBJECT IDENTIFIER ::= { eventManager 1 }

		netQoSEventID OBJECT-TYPE
			SYNTAX DisplayString
			ACCESS read-only
			STATUS mandatory
			DESCRIPTION
				"An identifier that Event Manager assigned to the event."
			::= { event 1 }

		netQoSEventType OBJECT-TYPE
			SYNTAX DisplayString (SIZE(1..64))
			ACCESS read-only
			STATUS mandatory
			DESCRIPTION
				"The type of the event."
			::= { event 2 }

		netQoSEventCategory OBJECT-TYPE
			SYNTAX Counter
			ACCESS read-only
			STATUS mandatory
			DESCRIPTION
				"The category of the event:
					0 Unknown
					1 Fault
					2 Config
					3 Accounting
					4 Performance
					5 Security"
			::= { event 3 }

		netQoSEventSeverity OBJECT-TYPE
			SYNTAX Counter
			ACCESS read-only
			STATUS mandatory
			DESCRIPTION
				"The severity of the event:
					0 Normal
					1 Unknown
					2 Minor
					3 Major
					4 Critical
					5 Unavailable"
			::= { event 4 }

		netQoSEventDescription OBJECT-TYPE
			SYNTAX DisplayString
			ACCESS read-only
			STATUS mandatory
			DESCRIPTION
				"A description of why the event was opened."
			::= { event 5 }

		netQoSEventState OBJECT-TYPE
			SYNTAX Counter
			ACCESS read-only
			STATUS mandatory
			DESCRIPTION
				"The current state of the event:
					0 Opened
					1 Acknowledged
					2 Closed
					3 Cleared"
			::= { event 6 }

		netQoSEventOpenTime OBJECT-TYPE
			SYNTAX Counter
			ACCESS read-only
			STATUS mandatory
			DESCRIPTION
				"A Unix timestamp, in UTC, that indicates when the event was opened."
			::= { event 7 }

		-- This table contains a list of the items referenced in the event
		netQoSEventItemTable OBJECT-TYPE
			SYNTAX SEQUENCE OF NetQoSEventItemEntry
			ACCESS not-accessible
			STATUS mandatory
			DESCRIPTION
				"This table contains a list of the managed items referenced in the event."
			::= { event 8 }

		netQoSEventItemEntry OBJECT-TYPE
			SYNTAX NetQoSEventItemEntry
			ACCESS not-accessible
			STATUS mandatory
			DESCRIPTION
				"A particular managed item referenced in the event."
			INDEX { netQoSEventItemIndex }
			::= { netQoSEventItemTable 1}

		NetQoSEventItemEntry ::=
			SEQUENCE {
				netQoSEventItemIndex  INTEGER,
				netQoSEventItemName   DisplayString (SIZE (1..127)),
				netQoSEventItemType   DisplayString (SIZE (0..32)),
				netQoSEventItemSubType DisplayString (SIZE(0..32)),
				netQoSEventItemIpAddress DisplayString
			}

		netQoSEventItemIndex OBJECT-TYPE
			SYNTAX  INTEGER
			ACCESS	read-only
			STATUS	mandatory
			DESCRIPTION
				"A one-based index of this particular managed item referenced in the event."
			::= { netQoSEventItemEntry 1 }

		netQoSEventItemName OBJECT-TYPE
			SYNTAX DisplayString (SIZE (1..127))
			ACCESS	read-only
			STATUS	mandatory
			DESCRIPTION
				"The name of this particular managed item referenced in the event."
			::= { netQoSEventItemEntry 2 }

		netQoSEventItemType OBJECT-TYPE
			SYNTAX DisplayString (SIZE (0..32))
			ACCESS	read-only
			STATUS	mandatory
			DESCRIPTION
				"The type of this particular managed item referenced in the event."
			::= { netQoSEventItemEntry 3 }

		netQoSEventItemSubType OBJECT-TYPE
			SYNTAX DisplayString (SIZE (0..32))
			ACCESS	read-only
			STATUS	mandatory
			DESCRIPTION
				"The subtype of this particular managed item referenced in the event."
			::= { netQoSEventItemEntry 4 }

		netQoSEventItemIpAddress OBJECT-TYPE
			SYNTAX DisplayString
			ACCESS	read-only
			STATUS	mandatory
			DESCRIPTION
				"An IP address associated with this particular managed item referenced in the event."
			::= { netQoSEventItemEntry 5 }

		-- This table contains a list of the properties referenced in the event
		netQoSEventPropertyTable OBJECT-TYPE
			SYNTAX SEQUENCE OF NetQoSEventPropertyEntry
			ACCESS not-accessible
			STATUS mandatory
			DESCRIPTION
				"This table contains a list of the properties contained in the event."
			::= { event 9 }

		netQoSEventPropertyEntry OBJECT-TYPE
			SYNTAX NetQoSEventPropertyEntry
			ACCESS not-accessible
			STATUS mandatory
			DESCRIPTION
				"A particular property contained in the event."
			INDEX { netQoSEventPropertyIndex }
			::= { netQoSEventPropertyTable 1}

		NetQoSEventPropertyEntry ::=
			SEQUENCE {
				netQoSEventPropertyIndex INTEGER,
				netQoSEventPropertyName  DisplayString (SIZE (1..128)),
				netQoSEventPropertyValue DisplayString
			}

		netQoSEventPropertyIndex OBJECT-TYPE
			SYNTAX  INTEGER
			ACCESS	read-only
			STATUS	mandatory
			DESCRIPTION
				"A one-based index of this particular property contained in the event."
			::= { netQoSEventPropertyEntry 1 }

		netQoSEventPropertyName OBJECT-TYPE
			SYNTAX DisplayString (SIZE (1..128))
			ACCESS	read-only
			STATUS	mandatory
			DESCRIPTION
				"The name of this particular property contained in the event."
			::= { netQoSEventPropertyEntry 2 }

		netQoSEventPropertyValue OBJECT-TYPE
			SYNTAX DisplayString
			ACCESS	read-only
			STATUS	mandatory
			DESCRIPTION
				"The value of this particular property contained in the event."
			::= { netQoSEventPropertyEntry 3 }

		netQoSEventMapURL OBJECT-TYPE
			SYNTAX DisplayString
			ACCESS read-only
			STATUS mandatory
			DESCRIPTION
				"A URL for the NPC Map page that contains the event."
			::= { event 10 }

		netQoSEventDetailsURL OBJECT-TYPE
			SYNTAX DisplayString
			ACCESS read-only
			STATUS mandatory
			DESCRIPTION
				"A URL for an NPC page that shows the details for the event."
			::= { event 11 }

		netQoSEventAssociatedItemURL OBJECT-TYPE
			SYNTAX DisplayString
			ACCESS read-only
			STATUS mandatory
			DESCRIPTION
				"A URL for an NPC page that shows the associated item for the event."
			::= { event 12 }

		netQoSEvent TRAP-TYPE
			ENTERPRISE eventManager
			VARIABLES { 
				netQoSEventID, 
				netQoSEventType,
				netQoSEventCategory,
				netQoSEventSeverity,
				netQoSEventDescription,
				netQoSEventState,
				netQoSEventOpenTime,
                                netQoSEventMapURL,
                                netQoSEventDetailsURL,
                                netQoSEventAssociatedItemURL,
				netQoSEventItemName,
				netQoSEventItemType,
				netQoSEventItemSubType,
				netQoSEventItemIpAddress,
				netQoSEventPropertyName,
				netQoSEventPropertyValue }
			DESCRIPTION
				"This SNMP trap is used to forward information about a new or updated event
				received by Event Manager.

				The netQoSEventItemName, netQoSEventItemType, netQoSEventItemSubType and
				netQoSEventItemIpAddress variables will be included once for each
				managed item referenced in the event.  If there is no IP address associated
				with an item (for example, voiplocations or pollinsts), netQoSEventItemIpAddress
				will be the empty string.

				The netQoSEventPropertyName and netQoSEventPropertyValue variables may
				be included multiple times, once for each property contained in the event.
				These two variables are repeated as a group:  Name 1, Value 1, Name 2, Value 2, etc."
			::= 1           

END
