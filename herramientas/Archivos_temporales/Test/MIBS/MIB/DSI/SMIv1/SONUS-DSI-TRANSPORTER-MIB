--
-- This SMIv1 module has been generated by smidump 0.2-cvs. Do not edit.
--

SONUS-DSI-TRANSPORTER-MIB DEFINITIONS ::= BEGIN

IMPORTS
    TRAP-TYPE
        FROM RFC-1215
    sonusEventClass, sonusEventDescription, sonusEventLevel, 
    sonusEventTime
        FROM SONUS-COMMON-MIB
    sonusServicesMIBs
        FROM SONUS-SMI;

sonusDsiTransporterMIB OBJECT IDENTIFIER
    ::= { sonusServicesMIBs 23 }

-- sonusDsiTransporterMIB MODULE-IDENTITY
--     LAST-UPDATED    "200708180000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for DataStreamIntegrator (DSI) Transporter Management."
--     ::= { sonusServicesMIBs 23 }


sonusDsiTransporterMIBObjects OBJECT IDENTIFIER
    ::= { sonusDsiTransporterMIB 1 }

sonusDsiTransporterMIBNotifications OBJECT IDENTIFIER
    ::= { sonusDsiTransporterMIB 2 }

sonusDsiTransporterMIBNotificationsPrefix OBJECT IDENTIFIER
    ::= { sonusDsiTransporterMIBNotifications 0 }

sonusDsiTransporterMIBNotificationsObjects OBJECT IDENTIFIER
    ::= { sonusDsiTransporterMIBNotifications 1 }

sonusDsiTransporterDownNotification TRAP-TYPE
    ENTERPRISE      sonusDsiTransporterMIBNotifications
    VARIABLES       { sonusEventDescription, sonusEventClass, 
                      sonusEventLevel, sonusEventTime }
--     STATUS          mandatory
    DESCRIPTION     
            "."
    ::= 1

sonusDsiTransporterConnDownNotification TRAP-TYPE
    ENTERPRISE      sonusDsiTransporterMIBNotifications
    VARIABLES       { sonusEventDescription, sonusEventClass, 
                      sonusEventLevel, sonusEventTime }
--     STATUS          mandatory
    DESCRIPTION     
            "."
    ::= 2

sonusDsiTransporterFtpDownNotification TRAP-TYPE
    ENTERPRISE      sonusDsiTransporterMIBNotifications
    VARIABLES       { sonusEventDescription, sonusEventClass, 
                      sonusEventLevel, sonusEventTime }
--     STATUS          mandatory
    DESCRIPTION     
            "."
    ::= 3

sonusDsiTransporterFtpLoginFailedNotification TRAP-TYPE
    ENTERPRISE      sonusDsiTransporterMIBNotifications
    VARIABLES       { sonusEventDescription, sonusEventClass, 
                      sonusEventLevel, sonusEventTime }
--     STATUS          mandatory
    DESCRIPTION     
            "."
    ::= 4

sonusDsiTransporterFtpTransferFailedNotification TRAP-TYPE
    ENTERPRISE      sonusDsiTransporterMIBNotifications
    VARIABLES       { sonusEventDescription, sonusEventClass, 
                      sonusEventLevel, sonusEventTime }
--     STATUS          mandatory
    DESCRIPTION     
            "."
    ::= 5

sonusDsiTransporterIOOpenErrorNotification TRAP-TYPE
    ENTERPRISE      sonusDsiTransporterMIBNotifications
    VARIABLES       { sonusEventDescription, sonusEventClass, 
                      sonusEventLevel, sonusEventTime }
--     STATUS          mandatory
    DESCRIPTION     
            "."
    ::= 6

sonusDsiTransporterIOReadErrorNotification TRAP-TYPE
    ENTERPRISE      sonusDsiTransporterMIBNotifications
    VARIABLES       { sonusEventDescription, sonusEventClass, 
                      sonusEventLevel, sonusEventTime }
--     STATUS          mandatory
    DESCRIPTION     
            "."
    ::= 7

sonusDsiTransporterIOWriteErrorNotification TRAP-TYPE
    ENTERPRISE      sonusDsiTransporterMIBNotifications
    VARIABLES       { sonusEventDescription, sonusEventClass, 
                      sonusEventLevel, sonusEventTime }
--     STATUS          mandatory
    DESCRIPTION     
            "."
    ::= 8

sonusDsiTransporterIORenameErrorNotification TRAP-TYPE
    ENTERPRISE      sonusDsiTransporterMIBNotifications
    VARIABLES       { sonusEventDescription, sonusEventClass, 
                      sonusEventLevel, sonusEventTime }
--     STATUS          mandatory
    DESCRIPTION     
            "."
    ::= 9

sonusDsiTransporterIORemoveErrorNotification TRAP-TYPE
    ENTERPRISE      sonusDsiTransporterMIBNotifications
    VARIABLES       { sonusEventDescription, sonusEventClass, 
                      sonusEventLevel, sonusEventTime }
--     STATUS          mandatory
    DESCRIPTION     
            "."
    ::= 10

sonusDsiTransporterCAMFileSeqErrorNotification TRAP-TYPE
    ENTERPRISE      sonusDsiTransporterMIBNotifications
    VARIABLES       { sonusEventDescription, sonusEventClass, 
                      sonusEventLevel, sonusEventTime }
--     STATUS          mandatory
    DESCRIPTION     
            "."
    ::= 11

sonusDsiTransporterCAMFileSizeErrorNotification TRAP-TYPE
    ENTERPRISE      sonusDsiTransporterMIBNotifications
    VARIABLES       { sonusEventDescription, sonusEventClass, 
                      sonusEventLevel, sonusEventTime }
--     STATUS          mandatory
    DESCRIPTION     
            "."
    ::= 12

sonusDsiTransporterCAMFileTimeErrorNotification TRAP-TYPE
    ENTERPRISE      sonusDsiTransporterMIBNotifications
    VARIABLES       { sonusEventDescription, sonusEventClass, 
                      sonusEventLevel, sonusEventTime }
--     STATUS          mandatory
    DESCRIPTION     
            "."
    ::= 13

sonusDsiTransporterCAMFileDupRecordNotification TRAP-TYPE
    ENTERPRISE      sonusDsiTransporterMIBNotifications
    VARIABLES       { sonusEventDescription, sonusEventClass, 
                      sonusEventLevel, sonusEventTime }
--     STATUS          mandatory
    DESCRIPTION     
            "."
    ::= 14

sonusDsiTransporterIOCloseErrorNotification TRAP-TYPE
    ENTERPRISE      sonusDsiTransporterMIBNotifications
    VARIABLES       { sonusEventDescription, sonusEventClass, 
                      sonusEventLevel, sonusEventTime }
--     STATUS          mandatory
    DESCRIPTION     
            "."
    ::= 15

END -- end of module SONUS-DSI-TRANSPORTER-MIB.
