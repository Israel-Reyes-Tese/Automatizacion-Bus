--
-- This SMIv2 module has been generated by smidump 0.2-cvs. Do not edit.
--

SONUS-HA-MIB DEFINITIONS ::= BEGIN

IMPORTS
    InetAddress, InetAddressType
        FROM INET-ADDRESS-MIB
    IpAddress, MODULE-IDENTITY, NOTIFICATION-TYPE, OBJECT-TYPE
        FROM SNMPv2-SMI
    TEXTUAL-CONVENTION
        FROM SNMPv2-TC
    sonusEventClass, sonusEventDescription, sonusEventLevel, 
    sonusEventTime
        FROM SONUS-COMMON-MIB
    sonusHostID
        FROM SONUS-HOST-MIB
    sonusServicesMIBs
        FROM SONUS-SMI;

sonusHAMIB MODULE-IDENTITY
    LAST-UPDATED    "201307200000Z"
    ORGANIZATION    
            "Sonus Networks, Inc."
    CONTACT-INFO    
            "   Customer Support    
             Sonus Networks, Inc.
             250 Apollo Drive
             Chelmsford, MA 01824
             USA
             
             Tel: 978-614-8100
             Fax: 978-614-8609"
    DESCRIPTION     
            "The MIB Module for Sonus High Availability Management."
    ::= { sonusServicesMIBs 17 }


SonusHAState ::= TEXTUAL-CONVENTION
    STATUS          current
    DESCRIPTION     
            "The high availability designation of the host.  This is an operational state."
    SYNTAX          INTEGER { unknown(0), active(1), active-intent(2), 
                        standby(3), standby-intent(4), standalone(5), 
                        suspended(6) }

sonusHAMIBObjects OBJECT IDENTIFIER
    ::= { sonusHAMIB 1 }

sonusHAMIBNotifications OBJECT IDENTIFIER
    ::= { sonusHAMIB 2 }

sonusHAMIBNotificationsPrefix OBJECT IDENTIFIER
    ::= { sonusHAMIBNotifications 0 }

sonusHAMIBNotificationsObjects OBJECT IDENTIFIER
    ::= { sonusHAMIBNotifications 1 }

sonusHAResource OBJECT-TYPE
    SYNTAX          INTEGER { wellknownIp(1), network(2), disk(3), 
                        database(4) }
    MAX-ACCESS      read-only
    STATUS          current
    DESCRIPTION     
            "A resource released by an active system and acquired by a standby system becoming active."
    ::= { sonusHAMIBNotificationsObjects 1 }

sonusHAPrevState OBJECT-TYPE
    SYNTAX          SonusHAState
    MAX-ACCESS      read-only
    STATUS          current
    DESCRIPTION     
            "The previous high availability state of this host."
    ::= { sonusHAMIBNotificationsObjects 2 }

sonusHANewState OBJECT-TYPE
    SYNTAX          SonusHAState
    MAX-ACCESS      read-only
    STATUS          current
    DESCRIPTION     
            "The new high availability state of this host."
    ::= { sonusHAMIBNotificationsObjects 3 }

sonusHAFailoverReason OBJECT-TYPE
    SYNTAX          INTEGER { unknown(0), user-initiated(1), 
                        oracleFailure(2), multipathFailure(3), 
                        raidFailure(4), processFailure(5) }
    MAX-ACCESS      read-write
    STATUS          current
    DESCRIPTION     
            "The reason a failover process was initiated."
    ::= { sonusHAMIBNotificationsObjects 4 }

sonusHACurrentState OBJECT-TYPE
    SYNTAX          SonusHAState
    MAX-ACCESS      read-only
    STATUS          current
    DESCRIPTION     
            "The present high availability state of this host."
    ::= { sonusHAMIBNotificationsObjects 5 }

sonusHAPeerIpAddress OBJECT-TYPE
    SYNTAX          IpAddress
    MAX-ACCESS      read-write
    STATUS          deprecated
    DESCRIPTION     
            "IP Address of the Softswitch - this is a required parameter."
    ::= { sonusHAMIBNotificationsObjects 6 }

sonusHAPeerExtendedIpAddressType OBJECT-TYPE
    SYNTAX          InetAddressType
    MAX-ACCESS      read-write
    STATUS          current
    DESCRIPTION     
            "IP Address type of the Softswitch - this is a required parameter."
    ::= { sonusHAMIBNotificationsObjects 7 }

sonusHAPeerExtendedIpAddress OBJECT-TYPE
    SYNTAX          InetAddress
    MAX-ACCESS      read-write
    STATUS          current
    DESCRIPTION     
            "IP Address of the Softswitch - this is a required parameter."
    ::= { sonusHAMIBNotificationsObjects 8 }

sonusHAFailoverInitiatedNotification NOTIFICATION-TYPE
    OBJECTS         { sonusHAFailoverReason, sonusHostID, 
                      sonusEventDescription, sonusEventClass, 
                      sonusEventLevel, sonusEventTime }
    STATUS          current
    DESCRIPTION     
            "A failover process has been initiated due to the specified reason."
    ::= { sonusHAMIBNotificationsPrefix 1 }

sonusHAConnectToPeerFailureNotification NOTIFICATION-TYPE
    OBJECTS         { sonusHostID, sonusHACurrentState, 
                      sonusHAPeerIpAddress, sonusEventDescription, 
                      sonusEventClass, sonusEventLevel, sonusEventTime }
    STATUS          deprecated
    DESCRIPTION     
            "Failure to connect to peer."
    ::= { sonusHAMIBNotificationsPrefix 2 }

sonusHAConnectToPeerSuccessNotification NOTIFICATION-TYPE
    OBJECTS         { sonusHostID, sonusHAPeerIpAddress, 
                      sonusEventDescription, sonusEventClass, 
                      sonusEventLevel, sonusEventTime }
    STATUS          deprecated
    DESCRIPTION     
            "Successful connection to peer."
    ::= { sonusHAMIBNotificationsPrefix 3 }

sonusHAStateChangeNotification NOTIFICATION-TYPE
    OBJECTS         { sonusHAPrevState, sonusHANewState, sonusHostID, 
                      sonusEventDescription, sonusEventClass, 
                      sonusEventLevel, sonusEventTime }
    STATUS          current
    DESCRIPTION     
            "The host's high availability state has changed."
    ::= { sonusHAMIBNotificationsPrefix 4 }

sonusHAResourceAcquireFailureNotification NOTIFICATION-TYPE
    OBJECTS         { sonusHAResource, sonusHostID, 
                      sonusEventDescription, sonusEventClass, 
                      sonusEventLevel, sonusEventTime }
    STATUS          current
    DESCRIPTION     
            "The high availability component was unable to acquire the specified resource during a failover procedure."
    ::= { sonusHAMIBNotificationsPrefix 5 }

sonusHAResourceReleaseFailureNotification NOTIFICATION-TYPE
    OBJECTS         { sonusHAResource, sonusHostID, 
                      sonusEventDescription, sonusEventClass, 
                      sonusEventLevel, sonusEventTime }
    STATUS          current
    DESCRIPTION     
            "The high availability component was unable to release the specified resource during a failover procedure."
    ::= { sonusHAMIBNotificationsPrefix 6 }

sonusHAHeartBeatFailureNotification NOTIFICATION-TYPE
    OBJECTS         { sonusHostID, sonusEventDescription, 
                      sonusEventClass, sonusEventLevel, sonusEventTime }
    STATUS          current
    DESCRIPTION     
            "No response was received for a heartbeat request sent to the peer."
    ::= { sonusHAMIBNotificationsPrefix 7 }

sonusHAConnectToPeerFailureExtendedNotification NOTIFICATION-TYPE
    OBJECTS         { sonusHostID, sonusHACurrentState, 
                      sonusHAPeerExtendedIpAddressType, 
                      sonusHAPeerExtendedIpAddress, 
                      sonusEventDescription, sonusEventClass, 
                      sonusEventLevel, sonusEventTime }
    STATUS          current
    DESCRIPTION     
            "Failure to connect to peer."
    ::= { sonusHAMIBNotificationsPrefix 8 }

sonusHAConnectToPeerSuccessExtendedNotification NOTIFICATION-TYPE
    OBJECTS         { sonusHostID, sonusHAPeerExtendedIpAddressType, 
                      sonusHAPeerExtendedIpAddress, 
                      sonusEventDescription, sonusEventClass, 
                      sonusEventLevel, sonusEventTime }
    STATUS          current
    DESCRIPTION     
            "Successful connection to peer."
    ::= { sonusHAMIBNotificationsPrefix 9 }

END -- end of module SONUS-HA-MIB.
