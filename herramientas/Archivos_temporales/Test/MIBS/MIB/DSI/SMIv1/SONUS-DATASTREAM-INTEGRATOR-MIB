--
-- This SMIv1 module has been generated by smidump 0.2-cvs. Do not edit.
--

SONUS-DATASTREAM-INTEGRATOR-MIB DEFINITIONS ::= BEGIN

IMPORTS
    amaInPriFilesMiss, amaOutPriFilesMiss, amaStoragePriOccuThres, 
    sessionCompIndex, sessionFtpAuthenFailLoc, sessionFtpAuthenFailRem, 
    sessionFtpMSessionsFail, sessionFtpMaxConsecRetries, 
    sessionFtpSessionFail
        FROM Gr1343Core-MIB
    hrDeviceErrors, hrDeviceIndex, hrStorageAllocationFailures, 
    hrStorageIndex
        FROM HOST-RESOURCES-MIB
    InetAddress, InetAddressType
        FROM INET-ADDRESS-MIB
    OBJECT-TYPE
        FROM RFC-1212
    TRAP-TYPE
        FROM RFC-1215
    Counter
        FROM RFC1155-SMI
    ifIndex, ifOperStatus
        FROM RFC1213-MIB
    DisplayString
        FROM SNMPv2-TC
    sonusEventClass, sonusEventDescription, sonusEventLevel, 
    sonusEventTime
        FROM SONUS-COMMON-MIB
    sonusHostID
        FROM SONUS-HOST-MIB
    sonusSystemMIBs
        FROM SONUS-SMI;

sonusDSIMIB OBJECT IDENTIFIER
    ::= { sonusSystemMIBs 9 }

-- sonusDSIMIB MODULE-IDENTITY
--     LAST-UPDATED    "201109230000Z"
--     ORGANIZATION    
--             "Sonus Networks, Inc."
--     CONTACT-INFO    
--             "   Customer Support    
--              Sonus Networks, Inc.
--              250 Apollo Drive
--              Chelmsford, MA 01824
--              USA
--              
--              Tel: 978-614-8100
--              Fax: 978-614-8609"
--     DESCRIPTION     
--             "The MIB Module for DataStreamIntegrator (DSI) Server Management."
--     ::= { sonusSystemMIBs 9 }


SonusDSIAlarmStatus ::=
    INTEGER { clear(1), set(2) }

-- SonusDSIAlarmStatus ::= TEXTUAL-CONVENTION
--     STATUS          mandatory
--     DESCRIPTION     
--             "Describes whether alarm is set or clear."
--     SYNTAX          INTEGER
--                       { clear(1), set(2) }

SonusDSIClusterName ::=
    DisplayString (SIZE(0..64))

-- SonusDSIClusterName ::= TEXTUAL-CONVENTION
--     STATUS          mandatory
--     DESCRIPTION     
--             "Describes which dsi cluster raised this alarm."
--     SYNTAX          DisplayString (SIZE(0..64))

SonusDSINodeType ::=
    INTEGER { none(0), mnode(1), cnode(2) }

-- SonusDSINodeType ::= TEXTUAL-CONVENTION
--     STATUS          mandatory
--     DESCRIPTION     
--             "Describes which dsi cluster raised this alarm."
--     SYNTAX          INTEGER
--                       { none(0), mnode(1), cnode(2) }

SonusDSIConnStatus ::=
    INTEGER { up(1), down(2) }

-- SonusDSIConnStatus ::= TEXTUAL-CONVENTION
--     STATUS          mandatory
--     DESCRIPTION     
--             "Describes the connection status."
--     SYNTAX          INTEGER
--                       { up(1), down(2) }

SonusDSIProcessName ::=
    DisplayString (SIZE(0..64))

-- SonusDSIProcessName ::= TEXTUAL-CONVENTION
--     STATUS          mandatory
--     DESCRIPTION     
--             "Describes which process this alarm relates to."
--     SYNTAX          DisplayString (SIZE(0..64))

sonusDSIMIBObjects OBJECT IDENTIFIER
    ::= { sonusDSIMIB 1 }

sonusDSIMIBNotifications OBJECT IDENTIFIER
    ::= { sonusDSIMIB 2 }

sonusDSIMIBNotificationsPrefix OBJECT IDENTIFIER
    ::= { sonusDSIMIBNotifications 0 }

sonusDSIMIBNotificationsObjects OBJECT IDENTIFIER
    ::= { sonusDSIMIBNotifications 1 }

sonusDSIAlarmStatus OBJECT-TYPE
    SYNTAX          SonusDSIAlarmStatus
    ACCESS          read-only
    STATUS          mandatory
    DESCRIPTION     
            "A description of the event that generated the trap."
    ::= { sonusDSIMIBNotificationsObjects 1 }

sonusDSIhrStorageWriteFailures OBJECT-TYPE
    SYNTAX          Counter
    ACCESS          read-only
    STATUS          mandatory
    DESCRIPTION     
            " "
    ::= { sonusDSIMIBNotificationsObjects 2 }

sonusDSIhrStorageReadFailures OBJECT-TYPE
    SYNTAX          Counter
    ACCESS          read-only
    STATUS          mandatory
    DESCRIPTION     
            " "
    ::= { sonusDSIMIBNotificationsObjects 3 }

sonusDSIClusterName OBJECT-TYPE
    SYNTAX          SonusDSIClusterName
    ACCESS          read-only
    STATUS          mandatory
    DESCRIPTION     
            "A description of the dsi cluster name that generated the trap."
    ::= { sonusDSIMIBNotificationsObjects 4 }

sonusDSINodeType OBJECT-TYPE
    SYNTAX          SonusDSINodeType
    ACCESS          read-only
    STATUS          mandatory
    DESCRIPTION     
            "A description of the dsi cluster node type that generated the trap."
    ::= { sonusDSIMIBNotificationsObjects 5 }

sonusDSIBPAConnStatus OBJECT-TYPE
    SYNTAX          SonusDSIConnStatus
    ACCESS          read-only
    STATUS          mandatory
    DESCRIPTION     
            "BPA connection status."
    ::= { sonusDSIMIBNotificationsObjects 6 }

sonusDSISaiConnStatus OBJECT-TYPE
    SYNTAX          SonusDSIConnStatus
    ACCESS          read-only
    STATUS          mandatory
    DESCRIPTION     
            "Transporter client connection status."
    ::= { sonusDSIMIBNotificationsObjects 7 }

sonusDSIBECommErrorReason OBJECT-TYPE
    SYNTAX          INTEGER { connectionfailure(1), portqueryfailure(2), 
                        portconnectionfailure(3), cdrtransferfailure(4), 
                        healthcheckfailure(5), invaliddelimiter(6), 
                        invalidusertype(7), brokensocket(8), 
                        streamingConnectionFailure(17), 
                        streamingHealthcheckFailure(18), 
                        streamingBrokenSocket(19) }
    ACCESS          read-only
    STATUS          mandatory
    DESCRIPTION     
            "Specifies a communication problem between 
             the backend stream server and the BPA."
    ::= { sonusDSIMIBNotificationsObjects 8 }

sonusDSIFileSourceAddressType OBJECT-TYPE
    SYNTAX          InetAddressType
    ACCESS          read-only
    STATUS          mandatory
    DESCRIPTION     
            "The IP Address type of the file source."
    ::= { sonusDSIMIBNotificationsObjects 9 }

sonusDSIFileSourceAddress OBJECT-TYPE
    SYNTAX          InetAddress
    ACCESS          read-only
    STATUS          deprecated
    DESCRIPTION     
            "The IP Address of the file source."
    ::= { sonusDSIMIBNotificationsObjects 10 }

sonusDSIProcessName OBJECT-TYPE
    SYNTAX          SonusDSIProcessName
    ACCESS          read-only
    STATUS          mandatory
    DESCRIPTION     
            "The dsi process name for which the trap is raised."
    ::= { sonusDSIMIBNotificationsObjects 11 }

sonusDSIVersionErrorFileName OBJECT-TYPE
    SYNTAX          DisplayString (SIZE(0..64))
    ACCESS          read-only
    STATUS          mandatory
    DESCRIPTION     
            "The file name which contains a version error."
    ::= { sonusDSIMIBNotificationsObjects 12 }

sonusDSIUnprocessedFileCount OBJECT-TYPE
    SYNTAX          INTEGER
    ACCESS          read-only
    STATUS          mandatory
    DESCRIPTION     
            "Number of unprocessed files."
    ::= { sonusDSIMIBNotificationsObjects 13 }

sonusDSINewMaster OBJECT-TYPE
    SYNTAX          DisplayString (SIZE(0..64))
    ACCESS          read-only
    STATUS          mandatory
    DESCRIPTION     
            "The new master dsi."
    ::= { sonusDSIMIBNotificationsObjects 14 }

sonusDSINewLoadPolicy OBJECT-TYPE
    SYNTAX          INTEGER { roundrobin(1), weightedroundrobin(2), 
                        leastloaded(3) }
    ACCESS          read-only
    STATUS          mandatory
    DESCRIPTION     
            "Specifies the new load distribution policy."
    ::= { sonusDSIMIBNotificationsObjects 15 }

sonusDsiBEAmaClosingStatus OBJECT-TYPE
    SYNTAX          INTEGER { manualClosingSuccessful(1), 
                        manualClosingRejected(2), 
                        automaticClosingSuccessful(3), 
                        automaticClosingRejected(4), 
                        automaticClosing64CdrFilesReached(5) }
    ACCESS          read-only
    STATUS          mandatory
    DESCRIPTION     
            "Specifies the AMA file automatic or manual  
             closing request status."
    ::= { sonusDSIMIBNotificationsObjects 16 }

sonusDsiBEAmaClosingFileName OBJECT-TYPE
    SYNTAX          DisplayString (SIZE(0..255))
    ACCESS          read-only
    STATUS          mandatory
    DESCRIPTION     
            "Specifies the name of current AMA file being   
             closed or close request is rejected for 
             automatic or manual closing."
    ::= { sonusDSIMIBNotificationsObjects 17 }

sonusDsiBEDatTransferStatus OBJECT-TYPE
    SYNTAX          INTEGER { transferCompleted(1), 
                        transferRequestRejected(2) }
    ACCESS          read-only
    STATUS          mandatory
    DESCRIPTION     
            "Specifies the AMA file DAT Transfer status."
    ::= { sonusDSIMIBNotificationsObjects 18 }

sonusDsiBEDatTransferFileName OBJECT-TYPE
    SYNTAX          DisplayString (SIZE(0..255))
    ACCESS          read-only
    STATUS          mandatory
    DESCRIPTION     
            "Specifies the name of the TAR for created by 
             DAT Transfer command."
    ::= { sonusDSIMIBNotificationsObjects 19 }

sonusDsiBERtTransferStatus OBJECT-TYPE
    SYNTAX          INTEGER { realtimeTransferResumed(1), 
                        realtimeTransferSuspended(2) }
    ACCESS          read-only
    STATUS          mandatory
    DESCRIPTION     
            "Specifies the Backend Stream Server 
             Real-time Transfer status."
    ::= { sonusDSIMIBNotificationsObjects 20 }

sonusDSIRecoveryFileName OBJECT-TYPE
    SYNTAX          DisplayString
    ACCESS          read-only
    STATUS          mandatory
    DESCRIPTION     
            "The absolute filename of failed job moved to recovery."
    ::= { sonusDSIMIBNotificationsObjects 21 }

sonusDSIDropFileName OBJECT-TYPE
    SYNTAX          DisplayString
    ACCESS          read-only
    STATUS          mandatory
    DESCRIPTION     
            "The relative filename contains dropped records from a job due to field validations."
    ::= { sonusDSIMIBNotificationsObjects 22 }

sonusDSIStrandedFile OBJECT-TYPE
    SYNTAX          DisplayString
    ACCESS          read-only
    STATUS          mandatory
    DESCRIPTION     
            "Health Monitor found Stranded file,duration crossed high watermark."
    ::= { sonusDSIMIBNotificationsObjects 23 }

sonusDSIIdleTime OBJECT-TYPE
    SYNTAX          DisplayString
    ACCESS          read-only
    STATUS          mandatory
    DESCRIPTION     
            "Health Monitor Idle time threshold crossed."
    ::= { sonusDSIMIBNotificationsObjects 24 }

sonusDSIClearIdleTime OBJECT-TYPE
    SYNTAX          DisplayString
    ACCESS          read-only
    STATUS          mandatory
    DESCRIPTION     
            "Clear Health Monitor Idle time threshold crossed alarm."
    ::= { sonusDSIMIBNotificationsObjects 25 }

sonusDSIAppValidation OBJECT-TYPE
    SYNTAX          DisplayString
    ACCESS          read-only
    STATUS          mandatory
    DESCRIPTION     
            "Health Monitor App File validation failed."
    ::= { sonusDSIMIBNotificationsObjects 26 }

sonusDSISAIDuplicateCDR OBJECT-TYPE
    SYNTAX          DisplayString
    ACCESS          read-only
    STATUS          mandatory
    DESCRIPTION     
            "Duplicate CDR received by SAI server from TC."
    ::= { sonusDSIMIBNotificationsObjects 27 }

sonusDSISAIRetransmittedCDR OBJECT-TYPE
    SYNTAX          DisplayString
    ACCESS          read-only
    STATUS          mandatory
    DESCRIPTION     
            "Retransmitted CDR received by SAI server from TC."
    ::= { sonusDSIMIBNotificationsObjects 28 }

sonusDsiMemInfo OBJECT-TYPE
    SYNTAX          DisplayString
    ACCESS          read-only
    STATUS          mandatory
    DESCRIPTION     
            "Health Monitor detected process memory growth reached high watermark."
    ::= { sonusDSIMIBNotificationsObjects 29 }

sonusDsiDiskInfo OBJECT-TYPE
    SYNTAX          DisplayString
    ACCESS          read-only
    STATUS          mandatory
    DESCRIPTION     
            "Health Monitor detected disk usage reached high watermark."
    ::= { sonusDSIMIBNotificationsObjects 30 }

sonusDsiCoreInfo OBJECT-TYPE
    SYNTAX          DisplayString
    ACCESS          read-only
    STATUS          mandatory
    DESCRIPTION     
            "Health Monitor detected number of core files reached high watermark."
    ::= { sonusDSIMIBNotificationsObjects 31 }

sonusDsiFileInfo OBJECT-TYPE
    SYNTAX          DisplayString
    ACCESS          read-only
    STATUS          mandatory
    DESCRIPTION     
            "Health Monitor detected number of files reached high watermark."
    ::= { sonusDSIMIBNotificationsObjects 32 }

sonusDSIFileSourceInetAddress OBJECT-TYPE
    SYNTAX          InetAddress
    ACCESS          read-only
    STATUS          mandatory
    DESCRIPTION     
            "The IP Address of the file source."
    ::= { sonusDSIMIBNotificationsObjects 33 }

sonusDSIDisk100PercentFullNotification TRAP-TYPE
    ENTERPRISE      sonusDSIMIBNotifications
    VARIABLES       { sonusEventDescription, sonusEventClass, 
                      sonusEventLevel, sonusEventTime, 
                      sonusDSIAlarmStatus, hrStorageIndex, 
                      hrStorageAllocationFailures, sonusDSIClusterName, 
                      sonusDSINodeType, sonusHostID }
--     STATUS          mandatory
    DESCRIPTION     
            "This trap with SonusDSIAlarmStatus=set indicates that
             the DSI has used all the disk space assigned to it.
             with SonusDSIAlarmStatus=clear it indicates that the disk 
             no longer full."
    ::= 1

sonusDSIPriAMAOccuThresExcededNotification TRAP-TYPE
    ENTERPRISE      sonusDSIMIBNotifications
    VARIABLES       { sonusEventDescription, sonusEventClass, 
                      sonusEventLevel, sonusEventTime, 
                      sonusDSIAlarmStatus, hrDeviceIndex, 
                      amaStoragePriOccuThres, sonusDSIClusterName, 
                      sonusDSINodeType, sonusHostID }
--     STATUS          mandatory
    DESCRIPTION     
            "This trap with SonusDSIAlarmStatus=set indicates that the DSI has 
             used 90 percent of the disk space assigned to it. With 
             SonusDSIAlarmStatus=clear it indicates that the disk no longer 
             90 percent full, the value of amaStoragePriOccuThres=90%"
    ::= 2

sonusDSIDisk75PercentFullNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap with SonusDSIAlarmStatus=set indicates that
             the DSI has used 75 percent of the disk space assigned to it.
             with SonusDSIAlarmStatus=clear it indicates that the disk 
             no longer 75 percent full."
    ::= 3

sonusDSIDisk50PercentFullNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap with SonusDSIAlarmStatus=set indicates that
             the DSI has used 50 percent of the disk space assigned to it.
             with SonusDSIAlarmStatus=clear it indicates that the disk 
             no longer 50 percent full."
    ::= 4

sonusDSIDiskWriteStatusNotification TRAP-TYPE
    ENTERPRISE      sonusDSIMIBNotifications
    VARIABLES       { sonusEventDescription, sonusEventClass, 
                      sonusEventLevel, sonusEventTime, 
                      sonusDSIAlarmStatus, hrStorageIndex, 
                      sonusDSIhrStorageWriteFailures, 
                      sonusDSIClusterName, sonusDSINodeType, sonusHostID }
--     STATUS          mandatory
    DESCRIPTION     
            "This trap is a warning to indicate that the DSI has failed 
             to write to the disk. Value of SonusDSIAlarmStatus indecates
             whether it is to set or clear."
    ::= 5

sonusDSICDRFileReadStatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has failed to 
             open or read a CDR file. Value of SonusDSIAlarmStatus indecates
             whether it is to set or clear."
    ::= 6

sonusDSICDRRecordStatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected
             a bad CDR record. Value of SonusDSIAlarmStatus indecates
             whether it is to set or clear."
    ::= 7

sonusDSICDRSequenceStatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected 
             a missing CDR. Value of SonusDSIAlarmStatus indecates
             whether it is to set or clear."
    ::= 8

sonusDSIFilePullStatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DM of the DSI has 
             failed to transfer an AMA file to the DM. Value of
             SonusDSIAlarmStatus indecates whether it is to set or clear."
    ::= 9

sonusDSIDDIProtocolDM1StatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected an
             FTP protocol error during an AMA file pull session. Value of 
             SonusDSIAlarmStatus indecates whether it is to set or clear."
    ::= 10

sonusDSIDDIProtocolDM2StatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected an
             FTP protocol error during an AMA file pull session. Value of
             SonusDSIAlarmStatus indecates whether it is to set or clear."
    ::= 11

sonusDSIDDIProtocolDM3StatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected an
             FTP protocol error during an AMA file pull session. Value of 
             SonusDSIAlarmStatus indecates whether it is to set or clear."
    ::= 12

sonusDSIDDIProtocolDM4StatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected an
             FTP protocol error during an AMA file pull session. Value of
             SonusDSIAlarmStatus indecates whether it is to set or clear."
    ::= 13

sonusDSIDDIProtocolGenericStatusNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap is a warning to indicate that the DSI has detected an 
             FTP protocol error during an AMA file pull session. Value of
             SonusDSIAlarmStatus indecates whether it is to set or clear."
    ::= 14

sonusDSITestAlarmNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "This trap indicates that the DSI has received a Test Alarm command
             from the CLI. Value of SonusDSIAlarmStatus indecates whether it is
             to set or clear."
    ::= 15

sonusDSIDiskReadStatusNotificatin TRAP-TYPE
    ENTERPRISE      sonusDSIMIBNotifications
    VARIABLES       { sonusEventDescription, sonusEventClass, 
                      sonusEventLevel, sonusEventTime, 
                      sonusDSIAlarmStatus, hrStorageIndex, 
                      sonusDSIhrStorageReadFailures, sonusDSIClusterName, 
                      sonusDSINodeType, sonusHostID }
--     STATUS          mandatory
    DESCRIPTION     
            ""
    ::= 16

sonusDSIFtpSessionFailNotification TRAP-TYPE
    ENTERPRISE      sonusDSIMIBNotifications
    VARIABLES       { sonusEventDescription, sonusEventClass, 
                      sonusEventLevel, sonusEventTime, 
                      sonusDSIAlarmStatus, sessionCompIndex, 
                      sessionFtpSessionFail, sonusDSIClusterName, 
                      sonusDSINodeType, sonusHostID }
--     STATUS          mandatory
    DESCRIPTION     
            "An attempt to establish FTP session failed. Automatically clears when the
             next FTP session is completed successfully, or when a Persistent FTP
             session failure alarm is issued."
    ::= 17

sonusDSIFtpPersSessionFailNotification TRAP-TYPE
    ENTERPRISE      sonusDSIMIBNotifications
    VARIABLES       { sonusEventDescription, sonusEventClass, 
                      sonusEventLevel, sonusEventTime, 
                      sonusDSIAlarmStatus, sessionCompIndex, 
                      sessionFtpMaxConsecRetries, 
                      sessionFtpMSessionsFail, sonusDSIClusterName, 
                      sonusDSINodeType, sonusHostID }
--     STATUS          mandatory
    DESCRIPTION     
            "When FTP Session Failure counter reaches the value of the
             sessionFtpMaxConsecRetries. Automatically clears when the next FTP
             session is completed successfully."
    ::= 18

sonusDSIFtpFailedAuthenNotification TRAP-TYPE
    ENTERPRISE      sonusDSIMIBNotifications
    VARIABLES       { sonusEventDescription, sonusEventClass, 
                      sonusEventLevel, sonusEventTime, 
                      sonusDSIAlarmStatus, sessionCompIndex, 
                      sessionFtpAuthenFailLoc, sonusDSIClusterName, 
                      sonusDSINodeType, sonusHostID }
--     STATUS          mandatory
    DESCRIPTION     
            "The DSI received a notification of FTP session authentication failure from
             the DPMS. Automatically clears when the next FTP session authentication
             is completed successfully."
    ::= 19

sonusDSIFtpFailedAuthenRemoteNotification TRAP-TYPE
    ENTERPRISE      sonusDSIMIBNotifications
    VARIABLES       { sonusEventDescription, sonusEventClass, 
                      sonusEventLevel, sonusEventTime, 
                      sonusDSIAlarmStatus, sessionCompIndex, 
                      sessionFtpAuthenFailRem, sonusDSIClusterName, 
                      sonusDSINodeType, sonusHostID }
--     STATUS          mandatory
    DESCRIPTION     
            "The DSI failed an FTP session authentication attempt by the DPMS.
             Automatically clears when the next FTP session authentication is
             completed successfully."
    ::= 20

sonusDSIFtpOutPriFileMissNotification TRAP-TYPE
    ENTERPRISE      sonusDSIMIBNotifications
    VARIABLES       { sonusEventDescription, sonusEventClass, 
                      sonusEventLevel, sonusEventTime, 
                      sonusDSIAlarmStatus, sessionCompIndex, 
                      amaOutPriFilesMiss, sonusDSIClusterName, 
                      sonusDSINodeType, sonusHostID }
--     STATUS          mandatory
    DESCRIPTION     
            "The DSI detected missing primary AMA files, which should have been sent to
             the DPMS. Automatically clears when the next FTP session is completed
             successfully."
    ::= 21

sonusDSIInPriFilesMissNotification TRAP-TYPE
    ENTERPRISE      sonusDSIMIBNotifications
    VARIABLES       { sonusEventDescription, sonusEventClass, 
                      sonusEventLevel, sonusEventTime, 
                      sonusDSIAlarmStatus, sessionCompIndex, 
                      amaInPriFilesMiss, sonusDSIClusterName, 
                      sonusDSINodeType, sonusHostID }
--     STATUS          mandatory
    DESCRIPTION     
            "The DSI detected missing primary AMA/CDR files, which were not received
             from the GSX/PSX. Automatically clears when the next AMA/CDR files is
             received successfully by FCP."
    ::= 22

sonusDSIDeviceStatusNotification TRAP-TYPE
    ENTERPRISE      sonusDSIMIBNotifications
    VARIABLES       { sonusEventDescription, sonusEventClass, 
                      sonusEventLevel, sonusEventTime, 
                      sonusDSIAlarmStatus, hrDeviceIndex, hrDeviceErrors, 
                      sonusDSIClusterName, sonusDSINodeType, sonusHostID }
--     STATUS          deprecated
    DESCRIPTION     
            "HA Monitor detected a device error occurred. Automatically clears when the 
             device is working without any error again."
    ::= 23

sonusDSIInterfaceDownNotification TRAP-TYPE
    ENTERPRISE      sonusDSIMIBNotifications
    VARIABLES       { sonusEventDescription, sonusEventClass, 
                      sonusEventLevel, sonusEventTime, 
                      sonusDSIAlarmStatus, ifIndex, ifOperStatus, 
                      sonusDSIClusterName, sonusDSINodeType, sonusHostID }
--     STATUS          deprecated
    DESCRIPTION     
            "The operational status of the interface has just been changed to 
             down(2) by HA Monitor. Automatically clears when the interface is up again."
    ::= 24

sonusDSIStorageStatusNotification TRAP-TYPE
    ENTERPRISE      sonusDSIMIBNotifications
    VARIABLES       { sonusEventDescription, sonusEventClass, 
                      sonusEventLevel, sonusEventTime, 
                      sonusDSIAlarmStatus, hrStorageIndex, 
                      sonusDSIClusterName, sonusDSINodeType, sonusHostID }
--     STATUS          mandatory
    DESCRIPTION     
            "HA Monitor detected a storage (disk) error occurred, Automatically clears
             when the storage is working without any error again."
    ::= 25

sonusDSIApplicationFailureNotification TRAP-TYPE
    ENTERPRISE      sonusDSIMIBNotifications
    VARIABLES       { sonusEventDescription, sonusEventClass, 
                      sonusEventLevel, sonusEventTime, 
                      sonusDSIAlarmStatus, hrDeviceIndex, 
                      sonusDSIClusterName, sonusDSINodeType, sonusHostID }
--     STATUS          mandatory
    DESCRIPTION     
            "HA Monitor detected a DSI software failure, Automatically clears when the
             DSI software is running successfully again."
    ::= 26

sonusDSIFailoverEventNotification TRAP-TYPE
    ENTERPRISE      sonusDSIMIBNotifications
    VARIABLES       { sonusEventDescription, sonusEventClass, 
                      sonusEventLevel, sonusEventTime, 
                      sonusDSIAlarmStatus, hrDeviceIndex, 
                      sonusDSIClusterName, sonusDSINodeType, sonusHostID }
--     STATUS          mandatory
    DESCRIPTION     
            "A system fail-over (from an active server to a standby server) occurred, 
             Must be cleared manually."
    ::= 27

sonusDSITelnetFailedAuthenNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI received a notification of cli telnet authentication failure. 
             Requires a manual clear."
    ::= 28

sonusDSIStorageAllocFailureNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI failed to allocate needed storage on a disk drive. 
             Requires a manual clear."
    ::= 29

sonusDSIStorageWriteFailureNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI failed to write to needed storage on a disk drive. 
             Requires a manual clear."
    ::= 30

sonusDSIStorageReadFailureNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI failed to read needed storage on a disk drive. 
             Requires a manual clear."
    ::= 31

sonusDSISequenceRestartNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI lost the AMA sequence and has restarted. 
             Requires a manual clear."
    ::= 32

sonusDSISoftwareErrorNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI had a critical software error. 
             Requires a manual clear."
    ::= 33

sonusDSIShutdownNotification TRAP-TYPE
    ENTERPRISE      sonusDSIMIBNotifications
    VARIABLES       { sonusEventDescription, sonusEventClass, 
                      sonusEventLevel, sonusEventTime, 
                      sonusDSIAlarmStatus, sessionCompIndex, 
                      sonusDSIClusterName, sonusDSINodeType, sonusHostID }
--     STATUS          mandatory
    DESCRIPTION     
            "The DSI has shutdown.  Automatically clears when DSI is  
             restarted."
    ::= 34

sonusDSISNMPRestartNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI SNMP Agent has restarted.  Automatically clears when DSI 
             SNMP Agent has recovered."
    ::= 35

sonusDSICommFtpErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced a Transporter Ftp Session Error. Cleared 
             when session error is resolved."
    ::= 36

sonusDSICommFtpLoginErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced a Transporter Ftp Login Error. Cleared 
             when login error is resolved."
    ::= 37

sonusDSIFileSizeErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced a File Size Error. Cleared 
             when File Size error is resolved."
    ::= 38

sonusDSIFileTimeErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced a File Time Error. Cleared 
             when File Time error is resolved."
    ::= 39

sonusDSIDupRecordErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced a Duplicate Record Error. Cleared 
             when the error is resolved."
    ::= 40

sonusDSIIORenameErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced an IO Error when renaming the file. Cleared 
             when error is resolved."
    ::= 41

sonusDSIIORemoveErrNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "The DSI has experienced an IO Error when removing the file. Cleared
             when error is resolved."
    ::= 42

sonusDSIDBNotAccessibleNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI had a critical DB Not Accessible error. 
             Automatically clears when DB is accessible."
    ::= 43

sonusDSIConnectionAttemptFailNotifiction TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "The DSI had a node connection attempt failed (Local %s, Remote %s, Reason %s) 
             Automatically clears when node connects ."
    ::= 44

sonusDSINodeDisconnectedNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "The DSI had a node disconnected (with remote node name).
             Automatically clears with sonusDSINodeConnectedNotification ."
    ::= 45

sonusDSINodeConnectedNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "The DSI had a node disconnected (with remote node name).
             Automatically clears when node connects ."
    ::= 46

sonusDSINodeNotAccessibleNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "The DSI had a node not accessible (with remote node name).
             Automatically clears when node is accessible ."
    ::= 47

sonusDSINodeRejectedNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI rejected a node (with reason and node name).
             Automatically clears when node is accepted ."
    ::= 48

sonusDSINodeOutOfServiceNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has a node out of service (with proc name).
             Automatically clears with sonusDSINodeInServiceNotification  ."
    ::= 49

sonusDSINodeInServiceNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has a node out of service (with proc name).
             Automatically clears when node is in-service ."
    ::= 50

sonusDSIConfigChangeFailureNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "The DSI has a Configuration change failed (with which command on which node).
             Automatically clears when configurations are upto date."
    ::= 51

sonusDSINoInputActivityNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has a No input activity in %s since %s
             Operator clears when  neccesary."
    ::= 52

sonusDSIClearNoInputActivityNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has resumed input activity in %s since %s
             Clears No Input activity alarm."
    ::= 53

sonusDSINoOutputActivityNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has not output activity in %s since %s
             Operator clears when  neccesary."
    ::= 54

sonusDSIClearNoOutputActivityNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI has resumed output activity in %s since %s
             Clear No Output activity alarm."
    ::= 55

sonusDSISaiAuthErrNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The DSI SAI Server has received an invalid 
             authentication response from the BPA."
    ::= 56

sonusDSISaiBPAConnStatusNotification TRAP-TYPE
    ENTERPRISE      sonusDSIMIBNotifications
    VARIABLES       { sonusEventDescription, sonusEventClass, 
                      sonusEventLevel, sonusEventTime, 
                      sonusDSIBPAConnStatus, sonusDSIAlarmStatus, 
                      sonusDSIClusterName, sonusDSINodeType, sonusHostID }
--     STATUS          mandatory
    DESCRIPTION     
            "The DSI SAI Server has detected a change of 
             the connection status from the BPA."
    ::= 57

sonusDSISaiConnStatusNotification TRAP-TYPE
    ENTERPRISE      sonusDSIMIBNotifications
    VARIABLES       { sonusEventDescription, sonusEventClass, 
                      sonusEventLevel, sonusEventTime, 
                      sonusDSISaiConnStatus, sonusDSIAlarmStatus, 
                      sonusDSIClusterName, sonusDSINodeType, sonusHostID }
--     STATUS          mandatory
    DESCRIPTION     
            "The DSI SAI Server has detected a change of
             the connection status from the Transporter client."
    ::= 58

sonusDSINoOperatingLicenseNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The system does not have a license to operate."
    ::= 59

sonusDSIMismatchedOperatingLicenseNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "An attempt was made to use an unlicensed feature."
    ::= 60

sonusDsiBECommDownNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          mandatory
    DESCRIPTION     
            "The Backend Stream Server is shut down."
    ::= 61

sonusDsiBECommErrorNotification TRAP-TYPE
    ENTERPRISE      sonusDSIMIBNotifications
    VARIABLES       { sonusEventDescription, sonusEventClass, 
                      sonusEventLevel, sonusEventTime, 
                      sonusDSIClusterName, sonusDSINodeType, 
                      sonusDSIBECommErrorReason, sonusHostID }
--     STATUS          mandatory
    DESCRIPTION     
            "The Backend Stream Server has experienced a 
             problem when communicating with the BPA."
    ::= 62

sonusDsiFileServicesProcessingFailNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "FileServices has encountered a possibly-global error 
             while manipulating directories or files."
    ::= 63

sonusDsiFileServicesSoftwareFailNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "FileServices encountered an error while processing 
             configuration parameters or invoking a filter."
    ::= 64

sonusDsiFileServicesPeerCommFailNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "FileServices cannot communicate with its peer process 
             on the specified server."
    ::= 65

sonusDsiFileServicesSwitchoverNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "FileServices detected that a source has failed over to 
             the other FileServices peer process."
    ::= 66

sonusDsiFileServicesFileSourceFailNotification TRAP-TYPE
    ENTERPRISE      sonusDSIMIBNotifications
    VARIABLES       { sonusEventDescription, sonusEventClass, 
                      sonusEventLevel, sonusEventTime, 
                      sonusDSIClusterName, sonusDSINodeType, 
                      sonusDSIFileSourceAddressType, 
                      sonusDSIFileSourceAddress, sonusHostID }
--     STATUS          deprecated
    DESCRIPTION     
            "FileServices cannot correctly handle a single source 
             and/or source's files. The source is identified by 
             sonusDSIFileSourceAddress."
    ::= 67

sonusDsiOperatingModeErrorNotification TRAP-TYPE
    ENTERPRISE      sonusDSIMIBNotifications
    VARIABLES       { sonusEventDescription, sonusEventClass, 
                      sonusEventLevel, sonusEventTime, 
                      sonusDSIClusterName, sonusDSINodeType, 
                      sonusDSIProcessName, sonusHostID }
--     STATUS          mandatory
    DESCRIPTION     
            "The process raising the alarm is not allowed to run 
             under the current operating mode settings. The name 
             of the process and the current operating mode settings 
             are included in the description."
    ::= 68

sonusDsiUnsupportedVersionError TRAP-TYPE
    ENTERPRISE      sonusDSIMIBNotifications
    VARIABLES       { sonusEventDescription, sonusEventClass, 
                      sonusEventLevel, sonusEventTime, 
                      sonusDSIClusterName, sonusDSINodeType, 
                      sonusDSIVersionErrorFileName, sonusHostID }
--     STATUS          mandatory
    DESCRIPTION     
            "The file <filename> has unsupported version in the header."
    ::= 69

sonusDsiUnprocessedFilesNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusDSIUnprocessedFileCount, 
                      sonusHostID }
--     STATUS          mandatory
    DESCRIPTION     
            "Unprocessed files found in miscFiles directory. File count = <count>."
    ::= 70

sonusDsiLoadPolicyChangeNotification TRAP-TYPE
    ENTERPRISE      sonusDSIMIBNotifications
    VARIABLES       { sonusEventDescription, sonusEventClass, 
                      sonusEventLevel, sonusEventTime, 
                      sonusDSIClusterName, sonusDSINodeType, 
                      sonusDSINewLoadPolicy, sonusHostID }
--     STATUS          mandatory
    DESCRIPTION     
            "Load distribution policy changed to <newPolicy>"
    ::= 71

sonusDsiMaintStartedNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusHostID }
--     STATUS          deprecated
    DESCRIPTION     
            "Maintenance started."
    ::= 72

sonusDsiMasterSwitchoverNotification TRAP-TYPE
    ENTERPRISE      sonusDSIMIBNotifications
    VARIABLES       { sonusEventDescription, sonusEventClass, 
                      sonusEventLevel, sonusEventTime, 
                      sonusDSIClusterName, sonusDSINodeType, 
                      sonusDSINewMaster, sonusHostID }
--     STATUS          deprecated
    DESCRIPTION     
            "Switchover to <newMaster>"
    ::= 73

sonusDsiBEAmaClosingNotification TRAP-TYPE
    ENTERPRISE      sonusDSIMIBNotifications
    VARIABLES       { sonusEventDescription, sonusEventClass, 
                      sonusEventLevel, sonusEventTime, 
                      sonusDSIClusterName, sonusDSINodeType, 
                      sonusDsiBEAmaClosingFileName, 
                      sonusDsiBEAmaClosingStatus, sonusHostID }
--     STATUS          mandatory
    DESCRIPTION     
            "AMA file closing for (%1$s) status (%2$s)"
    ::= 74

sonusDsiBEDatTransferNotification TRAP-TYPE
    ENTERPRISE      sonusDSIMIBNotifications
    VARIABLES       { sonusEventDescription, sonusEventClass, 
                      sonusEventLevel, sonusEventTime, 
                      sonusDSIClusterName, sonusDSINodeType, 
                      sonusDsiBEDatTransferFileName, 
                      sonusDsiBEDatTransferStatus, sonusHostID }
--     STATUS          mandatory
    DESCRIPTION     
            "DAT transfer request (%1$s) status (%2$s)"
    ::= 75

sonusDsiBERtTransferNotification TRAP-TYPE
    ENTERPRISE      sonusDSIMIBNotifications
    VARIABLES       { sonusEventDescription, sonusEventClass, 
                      sonusEventLevel, sonusEventTime, 
                      sonusDSIClusterName, sonusDSINodeType, 
                      sonusDsiBERtTransferStatus, sonusHostID }
--     STATUS          mandatory
    DESCRIPTION     
            "Real-time transfer status has changed to (%1$s)"
    ::= 76

sonusDsiOutOfSynchNotification TRAP-TYPE
    ENTERPRISE      sonusDSIMIBNotifications
    VARIABLES       { sonusEventDescription, sonusEventClass, 
                      sonusEventLevel, sonusEventTime, 
                      sonusDSIClusterName, sonusDSINodeType, sonusHostID }
--     STATUS          deprecated
    DESCRIPTION     
            "M-nodes may be out of synch"
    ::= 77

sonusDsiDBFailoverEventNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "ORACLE Failover event occuring: status in description"
    ::= 78

sonusDsiDBClearFailoverEventNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "Clearing ORACLE Failover event occuring: status in description "
    ::= 79

sonusDsiOracleErrorNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "ORACLE generated error code & msg in description"
    ::= 80

sonusDsiClearOracleErrorNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "Clearing ORACLE error"
    ::= 81

sonusDsiMemHiWatermarkNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusDsiMemInfo, sonusHostID }
--     STATUS          mandatory
    DESCRIPTION     
            "Health Monitor detected process memory growth reached high watermark:(%1$s)"
    ::= 82

sonusDsiDiskHiWatermarkNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusDsiDiskInfo, sonusHostID }
--     STATUS          mandatory
    DESCRIPTION     
            "Health Monitor detected disk usage reached high watermark:(%1$s)"
    ::= 83

sonusDsiCoreHiWatermarkNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusDsiCoreInfo, sonusHostID }
--     STATUS          mandatory
    DESCRIPTION     
            "Health Monitor detected number of core files reached high watermark:(%1$s)"
    ::= 84

sonusDsiFileToRecoveryNotification TRAP-TYPE
    ENTERPRISE      sonusDSIMIBNotifications
    VARIABLES       { sonusEventDescription, sonusEventClass, 
                      sonusEventLevel, sonusEventTime, 
                      sonusDSIClusterName, sonusDSINodeType, 
                      sonusDSIRecoveryFileName, sonusHostID }
--     STATUS          mandatory
    DESCRIPTION     
            "Maintainer detected a failed job, moved job file (%1$s) to recovery"
    ::= 85

sonusDSICdrFileDuplicateNotification TRAP-TYPE
    ENTERPRISE      sonusDSIMIBNotifications
    VARIABLES       { sonusEventDescription, sonusEventClass, 
                      sonusEventLevel, sonusEventTime, 
                      sonusDSIClusterName, sonusDSINodeType, sonusHostID }
--     STATUS          mandatory
    DESCRIPTION     
            "The DSI IMDS Merger accumulates CDR records and generates CDR file in the temporary directory before moving the final CDR file to the CDR storage directory. If the CDR file with the same file name is present in the CDR storage, the alarm is raised."
    ::= 86

sonusDSIFileHiWatermarkNotification TRAP-TYPE
    ENTERPRISE      sonusDSIMIBNotifications
    VARIABLES       { sonusEventDescription, sonusEventClass, 
                      sonusEventLevel, sonusEventTime, 
                      sonusDSIAlarmStatus, sonusDSIClusterName, 
                      sonusDSINodeType, sonusDsiFileInfo, sonusHostID }
--     STATUS          mandatory
    DESCRIPTION     
            "The DSI Health Monitor periodically checks for presence of files in the configured directory. If the number of files present is equal to or more than the configured high watermark, the alarm is raised:(%1$s)"
    ::= 87

sonusDSICDRRecordDropNotification TRAP-TYPE
    ENTERPRISE      sonusDSIMIBNotifications
    VARIABLES       { sonusEventDescription, sonusEventClass, 
                      sonusEventLevel, sonusEventTime, 
                      sonusDSIClusterName, sonusDSINodeType, 
                      sonusDSIDropFileName, sonusHostID }
--     STATUS          mandatory
    DESCRIPTION     
            "TP Processing detected Originating TrunkType field Mismatch, dropped record to (%1$s) file"
    ::= 88

sonusDsiTransporterDownNotification TRAP-TYPE
    ENTERPRISE      sonusDSIMIBNotifications
    VARIABLES       { sonusEventDescription, sonusEventClass, 
                      sonusEventLevel, sonusEventTime }
--     STATUS          mandatory
    DESCRIPTION     
            "."
    ::= 89

sonusDsiTransporterConnDownNotification TRAP-TYPE
    ENTERPRISE      sonusDSIMIBNotifications
    VARIABLES       { sonusEventDescription, sonusEventClass, 
                      sonusEventLevel, sonusEventTime }
--     STATUS          mandatory
    DESCRIPTION     
            "."
    ::= 90

sonusDSIStrandedFileFoundNotification TRAP-TYPE
    ENTERPRISE      sonusDSIMIBNotifications
    VARIABLES       { sonusEventDescription, sonusEventClass, 
                      sonusEventLevel, sonusEventTime, 
                      sonusDSIClusterName, sonusDSINodeType, 
                      sonusDSIStrandedFile, sonusHostID }
--     STATUS          mandatory
    DESCRIPTION     
            "Health Monitor found Stranded file,duration crossed high watermark: (%1$s)"
    ::= 91

sonusDSIIdleTimeThresholdReachedNotification TRAP-TYPE
    ENTERPRISE      sonusDSIMIBNotifications
    VARIABLES       { sonusEventDescription, sonusEventClass, 
                      sonusEventLevel, sonusEventTime, 
                      sonusDSIClusterName, sonusDSINodeType, 
                      sonusDSIIdleTime, sonusHostID }
--     STATUS          mandatory
    DESCRIPTION     
            "Health Monitor Idle time threshold crossed: (%1$s)"
    ::= 92

sonusDSIClearIdleTimeThresholdReachedNotification TRAP-TYPE
    ENTERPRISE      sonusDSIMIBNotifications
    VARIABLES       { sonusEventDescription, sonusEventClass, 
                      sonusEventLevel, sonusEventTime, 
                      sonusDSIClusterName, sonusDSINodeType, 
                      sonusDSIClearIdleTime, sonusHostID }
--     STATUS          mandatory
    DESCRIPTION     
            "Clear Health Monitor Idle time threshold crossed alarm:(%1$s)"
    ::= 93

sonusDSIAppValidationFailedNotification TRAP-TYPE
    ENTERPRISE      sonusDSIMIBNotifications
    VARIABLES       { sonusEventDescription, sonusEventClass, 
                      sonusEventLevel, sonusEventTime, 
                      sonusDSIClusterName, sonusDSINodeType, 
                      sonusDSIAppValidation, sonusHostID }
--     STATUS          mandatory
    DESCRIPTION     
            "Health Monitor App File validation failed: (%1$s)"
    ::= 94

sonusDSITransporterAbortNotification TRAP-TYPE
    ENTERPRISE      sonusDSIMIBNotifications
    VARIABLES       { sonusEventDescription, sonusEventClass, 
                      sonusEventLevel, sonusEventTime, 
                      sonusDSIAlarmStatus }
--     STATUS          mandatory
    DESCRIPTION     
            "Transporter aborted file transfer to all hosts "
    ::= 95

sonusDSISAIDuplicateCDRNotification TRAP-TYPE
    ENTERPRISE      sonusDSIMIBNotifications
    VARIABLES       { sonusEventDescription, sonusEventClass, 
                      sonusEventLevel, sonusEventTime, 
                      sonusDSIClusterName, sonusDSINodeType, 
                      sonusDSISAIDuplicateCDR, sonusHostID }
--     STATUS          mandatory
    DESCRIPTION     
            "Duplicate CDR received by SAI server from TC.: (%1$s)"
    ::= 96

sonusDSISAIRetransmittedCDRReceivedNotification TRAP-TYPE
    ENTERPRISE      sonusDSIMIBNotifications
    VARIABLES       { sonusEventDescription, sonusEventClass, 
                      sonusEventLevel, sonusEventTime, 
                      sonusDSIClusterName, sonusDSINodeType, 
                      sonusDSISAIRetransmittedCDR, sonusHostID }
--     STATUS          mandatory
    DESCRIPTION     
            "Retransmitted CDR received by SAI server from TC, Requires operator to take appropriate action.: (%1$s)"
    ::= 97

sonusDsiFileServicesFileSourceFailNotificationV6 TRAP-TYPE
    ENTERPRISE      sonusDSIMIBNotifications
    VARIABLES       { sonusEventDescription, sonusEventClass, 
                      sonusEventLevel, sonusEventTime, 
                      sonusDSIClusterName, sonusDSINodeType, 
                      sonusDSIFileSourceAddressType, 
                      sonusDSIFileSourceInetAddress, sonusHostID }
--     STATUS          mandatory
    DESCRIPTION     
            "FileServices cannot correctly handle a single source
             and/or source's files. The source is identified by
             sonusDSIFileSourceInetAddress."
    ::= 98

END -- end of module SONUS-DATASTREAM-INTEGRATOR-MIB.
