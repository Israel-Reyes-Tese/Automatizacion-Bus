--
-- This SMIv2 module has been generated by smidump 0.2-cvs. Do not edit.
--

SONUS-SOFTSWITCH-ADA-MIB DEFINITIONS ::= BEGIN

IMPORTS
    Counter32, Gauge32, MODULE-IDENTITY, NOTIFICATION-TYPE, OBJECT-TYPE, 
    TimeTicks
        FROM SNMPv2-SMI
    sonusEventClass, sonusEventDescription, sonusEventLevel, 
    sonusEventTime
        FROM SONUS-COMMON-MIB
    sonusServicesMIBs
        FROM SONUS-SMI
    SonusSystemName
        FROM SONUS-TC;

sonusSoftSwitchADAMIB MODULE-IDENTITY
    LAST-UPDATED    "200707100000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for the Diameter Agent."
    ::= { sonusServicesMIBs 34 }


sonusSoftSwitchADAMIBObjects OBJECT IDENTIFIER
    ::= { sonusSoftSwitchADAMIB 1 }

sonusSoftSwitchADAMIBNotifications OBJECT IDENTIFIER
    ::= { sonusSoftSwitchADAMIB 2 }

sonusSoftSwitchADAMIBNotificationsPrefix OBJECT IDENTIFIER
    ::= { sonusSoftSwitchADAMIBNotifications 0 }

sonusSoftSwitchADAMIBNotificationsObjects OBJECT IDENTIFIER
    ::= { sonusSoftSwitchADAMIBNotifications 1 }

sonusSoftSwitchADADomainControllerProfileName OBJECT-TYPE
    SYNTAX          OCTET STRING
    MAX-ACCESS      read-only
    STATUS          current
    DESCRIPTION     
            "Name of the Domain Controller configured."
    ::= { sonusSoftSwitchADAMIBNotificationsObjects 1 }

sonusSoftSwitchADAStatistics OBJECT IDENTIFIER
    ::= { sonusSoftSwitchADAMIB 3 }

sonusSoftSwitchAdaLookupCounters OBJECT IDENTIFIER
    ::= { sonusSoftSwitchADAStatistics 1 }

sonusSoftSwitchTotalAdaSuccessfullLookups OBJECT-TYPE
    SYNTAX          Counter32
    MAX-ACCESS      read-only
    STATUS          current
    DESCRIPTION     
            "Number of successful AD Lookups."
    ::= { sonusSoftSwitchAdaLookupCounters 1 }

sonusSoftSwitchTotalAdaFailedLookup OBJECT-TYPE
    SYNTAX          Counter32
    MAX-ACCESS      read-only
    STATUS          current
    DESCRIPTION     
            "Number of Failed AD Lookups."
    ::= { sonusSoftSwitchAdaLookupCounters 2 }

sonusSoftSwitchAdaDcCounters OBJECT IDENTIFIER
    ::= { sonusSoftSwitchADAStatistics 2 }

sonusSoftSwitchAdaDcCountersTable OBJECT-TYPE
    SYNTAX          SEQUENCE OF SonusSoftSwitchAdaDcCountersEntry
    MAX-ACCESS      not-accessible
    STATUS          current
    DESCRIPTION     
            "These are domain controller related stats ."
    ::= { sonusSoftSwitchAdaDcCounters 1 }

sonusSoftSwitchAdaDcCountersEntry OBJECT-TYPE
    SYNTAX          SonusSoftSwitchAdaDcCountersEntry
    MAX-ACCESS      not-accessible
    STATUS          current
    DESCRIPTION     
            "An entry per Domain Controller Name."
    INDEX           { sonusSoftSwitchAdaDcCountersName }
    ::= { sonusSoftSwitchAdaDcCountersTable 1 }

SonusSoftSwitchAdaDcCountersEntry ::=
    SEQUENCE {
        sonusSoftSwitchAdaDcCountersName SonusSystemName,
        sonusSoftSwitchAdaDcCountersConnectionStatus            Gauge32,
        sonusSoftSwitchAdaDcCountersSyncStatus      Gauge32,
        sonusSoftSwitchAdaDcCountersLastSyncTime        TimeTicks
    }

sonusSoftSwitchAdaDcCountersName OBJECT-TYPE
    SYNTAX          SonusSystemName
    MAX-ACCESS      read-only
    STATUS          current
    DESCRIPTION     
            "The Domain Controller Name that the Counters apply to"
    ::= { sonusSoftSwitchAdaDcCountersEntry 1 }

sonusSoftSwitchAdaDcCountersConnectionStatus OBJECT-TYPE
    SYNTAX          Gauge32
    MAX-ACCESS      read-only
    STATUS          current
    DESCRIPTION     
            "Domain Controller Connection Status 0-UP and 1-DOWN"
    ::= { sonusSoftSwitchAdaDcCountersEntry 2 }

sonusSoftSwitchAdaDcCountersSyncStatus OBJECT-TYPE
    SYNTAX          Gauge32
    MAX-ACCESS      read-only
    STATUS          current
    DESCRIPTION     
            "Domain Controller Sync Status 0-Synced and 1-Sync Failed"
    ::= { sonusSoftSwitchAdaDcCountersEntry 3 }

sonusSoftSwitchAdaDcCountersLastSyncTime OBJECT-TYPE
    SYNTAX          TimeTicks
    MAX-ACCESS      read-only
    STATUS          current
    DESCRIPTION     
            "This is Last Sync time from Domain Controller."
    ::= { sonusSoftSwitchAdaDcCountersEntry 4 }

sonusSoftSwitchAdaDownNotification NOTIFICATION-TYPE
    OBJECTS         { sonusEventDescription, sonusEventClass, 
                      sonusEventLevel, sonusEventTime }
    STATUS          current
    DESCRIPTION     
            "ADA shutdown event."
    ::= { sonusSoftSwitchADAMIBNotificationsPrefix 1 }

sonusSoftSwitchAdaUpNotification NOTIFICATION-TYPE
    OBJECTS         { sonusEventDescription, sonusEventClass, 
                      sonusEventLevel, sonusEventTime }
    STATUS          current
    DESCRIPTION     
            "ADA startup event"
    ::= { sonusSoftSwitchADAMIBNotificationsPrefix 2 }

sonusSoftSwitchADADomainControllerConnUp NOTIFICATION-TYPE
    OBJECTS         { sonusSoftSwitchADADomainControllerProfileName, 
                      sonusEventDescription, sonusEventClass, 
                      sonusEventLevel, sonusEventTime }
    STATUS          current
    DESCRIPTION     
            "Connection to a Domain Controller is UP."
    ::= { sonusSoftSwitchADAMIBNotificationsPrefix 3 }

sonusSoftSwitchADADomainControllerConnDown NOTIFICATION-TYPE
    OBJECTS         { sonusSoftSwitchADADomainControllerProfileName, 
                      sonusEventDescription, sonusEventClass, 
                      sonusEventLevel, sonusEventTime }
    STATUS          current
    DESCRIPTION     
            "Connection to Domain Controller is down."
    ::= { sonusSoftSwitchADAMIBNotificationsPrefix 4 }

sonusSoftSwitchADADomainControllerSyncUp NOTIFICATION-TYPE
    OBJECTS         { sonusSoftSwitchADADomainControllerProfileName, 
                      sonusEventDescription, sonusEventClass, 
                      sonusEventLevel, sonusEventTime }
    STATUS          current
    DESCRIPTION     
            "Connection to Domain Controller is down."
    ::= { sonusSoftSwitchADAMIBNotificationsPrefix 5 }

sonusSoftSwitchADADomainControllerSyncFailure NOTIFICATION-TYPE
    OBJECTS         { sonusSoftSwitchADADomainControllerProfileName, 
                      sonusEventDescription, sonusEventClass, 
                      sonusEventLevel, sonusEventTime }
    STATUS          current
    DESCRIPTION     
            "Connection to Domain Controller is down."
    ::= { sonusSoftSwitchADAMIBNotificationsPrefix 6 }

END -- end of module SONUS-SOFTSWITCH-ADA-MIB.
