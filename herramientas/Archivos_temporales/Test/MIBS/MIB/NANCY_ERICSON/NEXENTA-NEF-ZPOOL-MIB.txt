NEXENTA-ZPOOL-MIB DEFINITIONS ::= BEGIN
IMPORTS
    MODULE-IDENTITY FROM SNMPv2-SMI
    MODULE-COMPLIANCE FROM SNMPv2-CONF
    OBJECT-TYPE, Integer32 FROM SNMPv2-SMI
    OBJECT-GROUP FROM SNMPv2-CONF
    nexentaNef FROM NEXENTA-MIB
;
zpool MODULE-IDENTITY
    LAST-UPDATED "201810100000Z"
    ORGANIZATION "Nexenta Systems, Inc."
    CONTACT-INFO "postal: 2025 Gateway Place, Suite 160, San Jose, CA 95110 USA
email: support@nexenta.com"
    DESCRIPTION "MIB to support zpool operations"
    REVISION "201810100000Z"
    DESCRIPTION "Second revision"
    ::= { nexentaNef 2 }
zpoolNotifications OBJECT IDENTIFIER ::= { zpool 0 }
zpoolListTable OBJECT-TYPE
    SYNTAX SEQUENCE OF ZpoolListSequence
    MAX-ACCESS not-accessible
    STATUS current
    DESCRIPTION "List of zpools on the appliance"
    ::= { zpool 1 }
zpoolListEntry OBJECT-TYPE
    SYNTAX ZpoolListSequence
    MAX-ACCESS not-accessible
    STATUS current
    DESCRIPTION "Zpool entry"
    INDEX { zpoolName }
    ::= { zpoolListTable 1 }
ZpoolListSequence ::= SEQUENCE {
    zpoolName OCTET STRING,
    zpoolHealth OCTET STRING,
    zpoolSize Integer32,
    zpoolAllocated Integer32,
    zpoolFree Integer32,
    zpoolCapacity Integer32
}
zpoolName OBJECT-TYPE
    SYNTAX OCTET STRING (SIZE (1..255))
    MAX-ACCESS read-only
    STATUS current
    DESCRIPTION "Zpool name"
    ::= { zpoolListEntry 1 }
zpoolHealth OBJECT-TYPE
    SYNTAX OCTET STRING
    MAX-ACCESS read-only
    STATUS current
    DESCRIPTION "Current zpool status"
    ::= { zpoolListEntry 2 }
zpoolSize OBJECT-TYPE
    SYNTAX Integer32
    MAX-ACCESS read-only
    STATUS current
    DESCRIPTION "Size of zpool in MBytes"
    ::= { zpoolListEntry 3 }
zpoolAllocated OBJECT-TYPE
    SYNTAX Integer32
    MAX-ACCESS read-only
    STATUS current
    DESCRIPTION "Number of MBytes allocated"
    ::= { zpoolListEntry 4 }
zpoolFree OBJECT-TYPE
    SYNTAX Integer32
    MAX-ACCESS read-only
    STATUS current
    DESCRIPTION "Number of MBytes free"
    ::= { zpoolListEntry 5 }
zpoolCapacity OBJECT-TYPE
    SYNTAX Integer32
    MAX-ACCESS read-only
    STATUS current
    DESCRIPTION "Percentage of pool space used"
    ::= { zpoolListEntry 6 }
zpoolCompliances OBJECT IDENTIFIER ::= { zpool 1000 }
zpoolObjGrp OBJECT-GROUP
    OBJECTS { zpoolName, zpoolHealth, zpoolSize, zpoolAllocated, zpoolFree, zpoolCapacity }
    STATUS current
    DESCRIPTION "Default objects conformance group for NEXENTA-ZPOOL-MIB"
    ::= { zpoolCompliances 2 }
zpoolCompliance MODULE-COMPLIANCE
    STATUS current
    DESCRIPTION "Default compliance statement for NEXENTA-ZPOOL-MIB"
    MODULE MANDATORY-GROUPS { zpoolObjGrp }
    ::= { zpoolCompliances 1 }
END
