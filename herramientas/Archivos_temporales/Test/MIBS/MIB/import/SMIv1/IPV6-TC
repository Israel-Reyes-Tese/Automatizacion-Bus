--
-- This SMIv1 module has been generated by smidump 0.2-cvs. Do not edit.
--

IPV6-TC DEFINITIONS ::= BEGIN

Ipv6Address ::=
    OCTET STRING (SIZE(16))

-- Ipv6Address ::= TEXTUAL-CONVENTION
--     DISPLAY-HINT    "2x:"
--     STATUS          mandatory
--     DESCRIPTION     
--             "This data type is used to model IPv6 addresses.
--              This is a binary string of 16 octets in network
--              byte-order."
--     SYNTAX          OCTET STRING (SIZE(16))

Ipv6AddressPrefix ::=
    OCTET STRING (SIZE(0..16))

-- Ipv6AddressPrefix ::= TEXTUAL-CONVENTION
--     DISPLAY-HINT    "2x:"
--     STATUS          mandatory
--     DESCRIPTION     
--             "This data type is used to model IPv6 address
--              prefixes. This is a binary string of up to 16
--              octets in network byte-order."
--     SYNTAX          OCTET STRING (SIZE(0..16))

Ipv6AddressIfIdentifier ::=
    OCTET STRING (SIZE(0..8))

-- Ipv6AddressIfIdentifier ::= TEXTUAL-CONVENTION
--     DISPLAY-HINT    "2x:"
--     STATUS          mandatory
--     DESCRIPTION     
--             "This data type is used to model IPv6 address
--              interface identifiers. This is a binary string
--               of up to 8 octets in network byte-order."
--     SYNTAX          OCTET STRING (SIZE(0..8))

Ipv6IfIndex ::=
    INTEGER (1..2147483647)

-- Ipv6IfIndex ::= TEXTUAL-CONVENTION
--     DISPLAY-HINT    "d"
--     STATUS          mandatory
--     DESCRIPTION     
--             "A unique value, greater than zero for each
--              internetwork-layer interface in the managed
--              system. It is recommended that values are assigned
--              contiguously starting from 1. The value for each
--              internetwork-layer interface must remain constant
--              at least from one re-initialization of the entity's
--              network management system to the next
--              re-initialization."
--     SYNTAX          INTEGER (1..2147483647)

Ipv6IfIndexOrZero ::=
    INTEGER (0..2147483647)

-- Ipv6IfIndexOrZero ::= TEXTUAL-CONVENTION
--     DISPLAY-HINT    "d"
--     STATUS          mandatory
--     DESCRIPTION     
--             "This textual convention is an extension of the
--              Ipv6IfIndex convention.  The latter defines
--              a greater than zero value used to identify an IPv6
--              interface in the managed system.  This extension
--              permits the additional value of zero.  The value
--              zero is object-specific and must therefore be
--              defined as part of the description of any object
--              which uses this syntax.  Examples of the usage of
--              zero might include situations where interface was
--              unknown, or when none or all interfaces need to be
--              referenced."
--     SYNTAX          INTEGER (0..2147483647)

END -- end of module IPV6-TC.
