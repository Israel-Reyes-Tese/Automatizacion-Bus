--
-- This SMIv1 module has been generated by smidump 0.2-cvs. Do not edit.
--

DHCP-SERVER-MIB DEFINITIONS ::= BEGIN

IMPORTS
    InetAddressIPv4
        FROM INET-ADDRESS-MIB
    OBJECT-TYPE
        FROM RFC-1212
    TRAP-TYPE
        FROM RFC-1215
    Counter, Gauge
        FROM RFC1155-SMI
    mib-2
        FROM RFC1213-MIB
    DateAndTime
        FROM SNMPv2-TC;

serverMIB OBJECT IDENTIFIER
    ::= { dhcp 1 }

-- serverMIB MODULE-IDENTITY
--     LAST-UPDATED    "200211040429Z"
--     ORGANIZATION    
--             "IETF DHC Working Group
--              General Discussion: dhcwg@ietf.org 
--              Subscribe: http://www1.ietf.org/mailman/listinfo/dhcwg 
--              Archive: http://www1.ietf.org/mailman/listinfo/dhcwg 
--              Chair: Ralph Droms, rdroms@cisco.com "
--     CONTACT-INFO    
--             "        Richard Barr Hibbs 
--              Postal:  952 Sanchex Street 
--                       San Francisco, California 94114-3362 
--                       USA 
--                 Tel:  +1-(415)-648-3920 
--                 Fax:  +1-(415)-648-9017 
--              E-mail:  rbhibbs@pacbell.net 
--               
--                       Glenn Waters 
--              Postal:  Nortel Networks, Inc. 
--                       310-875 Carling Avenue 
--                       Ottawa, Ontario K1S 5P1 
--                       Canada 
--                 Tel:  +1-(613)-798-4925 
--              E-mail:  gww@NortelNetworks.com "
--     DESCRIPTION     
--             "The MIB module for entities implementing the server side of 
--              the Bootstrap Protocol (BOOTP) and the Dynamic Host 
--              Configuration protocol (DHCP) for Internet Protocol version 
--              4(IPv4).  This MIB does not include support for Dynamic DNS 
--              (DDNS) updating nor for the DHCP Failover Protocol."
--     REVISION        "200211040429Z"
--     DESCRIPTION     
--             "Initial Version, published as RFC xxxx."
--     ::= { dhcp 1 }


DhcpTimeInterval ::=
    Gauge

-- DhcpTimeInterval ::= TEXTUAL-CONVENTION
--     STATUS          mandatory
--     DESCRIPTION     
--             "The number of milliseconds that has elapsed since some epoch.  
--              Systems that cannot measure events to the millisecond 
--              resolution SHOULD round this value to the next available 
--              resolution that the system supports."
--     SYNTAX          Gauge

HardwareAddressType ::=
    OCTET STRING (SIZE(1))

-- HardwareAddressType ::= TEXTUAL-CONVENTION
--     STATUS          mandatory
--     DESCRIPTION     
--             "The value of the hardware type field, as used in ARP messages 
--              (e.g., 1 for Ethernet, 6 for token ring).  IANA maintains the 
--              list of registered numbers for this field."
--     SYNTAX          OCTET STRING (SIZE(1))

HardwareAddressLength ::=
    OCTET STRING (SIZE(1))

-- HardwareAddressLength ::= TEXTUAL-CONVENTION
--     STATUS          mandatory
--     DESCRIPTION     
--             "The length in octets of the hardware address field (e.g., 6 
--              for Ethernet).  IANA maintains the list of registered numbers 
--              for this field."
--     SYNTAX          OCTET STRING (SIZE(1))

MacAddress ::=
    OCTET STRING (SIZE(1..16))

-- MacAddress ::= TEXTUAL-CONVENTION
--     STATUS          mandatory
--     DESCRIPTION     
--             "A Layer 1 address, the hardware address of the MAC (Media 
--              Adapter Card) interface.  The address length is fixed for a 
--              given hardware address type, but varies by type."
--     SYNTAX          OCTET STRING (SIZE(1..16))

PhysicalAddress ::=
    OCTET STRING (SIZE(3..18))

-- PhysicalAddress ::= TEXTUAL-CONVENTION
--     STATUS          mandatory
--     DESCRIPTION     
--             "A Layer 1 address which includes the hardware type space as 
--              well as the usual MAC address.  This encoding is intended to 
--              mirror the representation of physical addresses in DHCP."
--     SYNTAX          OCTET STRING (SIZE(3..18))

dhcp OBJECT IDENTIFIER
    ::= { mib-2 99 }

serverMIBObjects OBJECT IDENTIFIER
    ::= { serverMIB 1 }

serverSystem OBJECT IDENTIFIER
    ::= { serverMIBObjects 1 }

serverSystemDescr OBJECT-TYPE
    SYNTAX          SnmpAdminString (SIZE(0..255))
    ACCESS          read-only
    STATUS          mandatory
    DESCRIPTION     
            "A textual description of the server.  This value should 
             include the full name and version identification of the 
             server."
    ::= { serverSystem 1 }

serverSystemObjectID OBJECT-TYPE
    SYNTAX          OBJECT IDENTIFIER
    ACCESS          read-only
    STATUS          mandatory
    DESCRIPTION     
            "The vendor's authoritative identification of the network 
             management subsystem contained in this entity.  This value is 
             allocated within the SMI enterprise subtree (1.3.6.1.4.1) and 
             provides an easy and unambiguous means for determining 'what 
             kind of server' is being managed.  For example, if vendor 
             'VeryBigServers, Inc.' is assigned the subtree 
             1.3.6.1.4.1.4242, it may assign the identifier 
             1.3.6.1.4.1.4242.1.1 to its `Hercules DHCP Server'."
    ::= { serverSystem 2 }

bootpCounters OBJECT IDENTIFIER
    ::= { serverMIBObjects 2 }

bootpCountRequests OBJECT-TYPE
    SYNTAX          Counter
    ACCESS          read-only
    STATUS          mandatory
    DESCRIPTION     
            "The number of packets received that contain a Message Type of 
             1 (BOOTREQUEST) in the first octet and do not contain option 
             number 53 (DHCP Message Type) in the options."
--     REFERENCE       
--             "RFC-1541."
    ::= { bootpCounters 1 }

bootpCountInvalids OBJECT-TYPE
    SYNTAX          Counter
    ACCESS          read-only
    STATUS          mandatory
    DESCRIPTION     
            "The number of packets received that do not contain a Message 
             Type of 1 (BOOTREQUEST) in the first octet or are not valid 
             BOOTP packets (e.g., too short, invalid field in packet 
             header)."
    ::= { bootpCounters 2 }

bootpCountReplies OBJECT-TYPE
    SYNTAX          Counter
    ACCESS          read-only
    STATUS          mandatory
    DESCRIPTION     
            "The number of packets sent that contain a Message Type of 2 
             (BOOTREPLY) in the first octet and do not contain option number 
             53 (DHCP Message Type) in the options."
--     REFERENCE       
--             "RFC-1541."
    ::= { bootpCounters 3 }

bootpCountDroppedUnknownClients OBJECT-TYPE
    SYNTAX          Counter
    ACCESS          read-only
    STATUS          mandatory
    DESCRIPTION     
            "The number of BOOTP packets dropped due to the server not 
             recognizing or not providing service to the hardware address 
             received in the incoming packet."
    ::= { bootpCounters 4 }

bootpCountDroppedNotServingSubnet OBJECT-TYPE
    SYNTAX          Counter
    ACCESS          read-only
    STATUS          mandatory
    DESCRIPTION     
            "The number of BOOTP packets dropped due to the server not 
             being configured or not otherwise able to serve addresses on 
             the subnet from which this message was received."
    ::= { bootpCounters 5 }

dhcpCounters OBJECT IDENTIFIER
    ::= { serverMIBObjects 3 }

dhcpCountDiscovers OBJECT-TYPE
    SYNTAX          Counter
    ACCESS          read-only
    STATUS          mandatory
    DESCRIPTION     
            "The number of DHCPDISCOVER (option 53 with value 1) packets 
             received."
--     REFERENCE       
--             "RFC2131; RFC2132, section 9.6."
    ::= { dhcpCounters 1 }

dhcpCountRequests OBJECT-TYPE
    SYNTAX          Counter
    ACCESS          read-only
    STATUS          mandatory
    DESCRIPTION     
            "The number of DHCPREQUEST (option 53 with value 3) packets 
             received."
--     REFERENCE       
--             "RFC2131; RFC2132, section 9.6."
    ::= { dhcpCounters 2 }

dhcpCountReleases OBJECT-TYPE
    SYNTAX          Counter
    ACCESS          read-only
    STATUS          mandatory
    DESCRIPTION     
            "The number of DHCPRELEASE (option 53 with value 7) packets 
             received."
--     REFERENCE       
--             "RFC2131; RFC2132, section 9.6."
    ::= { dhcpCounters 3 }

dhcpCountDeclines OBJECT-TYPE
    SYNTAX          Counter
    ACCESS          read-only
    STATUS          mandatory
    DESCRIPTION     
            "The number of DHCPDECLINE (option 53 with value 4) packets 
             received."
--     REFERENCE       
--             "RFC2131; RFC2132, section 9.6."
    ::= { dhcpCounters 4 }

dhcpCountInforms OBJECT-TYPE
    SYNTAX          Counter
    ACCESS          read-only
    STATUS          mandatory
    DESCRIPTION     
            "The number of DHCPINFORM (option 53 with value 8) packets 
             received."
--     REFERENCE       
--             "RFC2131; RFC2132, section 9.6."
    ::= { dhcpCounters 5 }

dhcpCountLeaseQueries OBJECT-TYPE
    SYNTAX          Counter
    ACCESS          read-only
    STATUS          mandatory
    DESCRIPTION     
            "The number of DHCPLEASEQUERY (option 53 with value 9) packets 
             received."
--     REFERENCE       
--             "draft-ietf-dhc-leasequery-02.txt."
    ::= { dhcpCounters 6 }

dhcpCountPlaceHolder1 OBJECT-TYPE
    SYNTAX          Counter
    ACCESS          read-only
    STATUS          mandatory
    DESCRIPTION     
            "Placeholder for anticipated new DHCP option 53 message type."
--     REFERENCE       
--             "None."
    ::= { dhcpCounters 7 }

dhcpCountPlaceHolder2 OBJECT-TYPE
    SYNTAX          Counter
    ACCESS          read-only
    STATUS          mandatory
    DESCRIPTION     
            "Placeholder for anticipated new DHCP option 53 message type."
--     REFERENCE       
--             "None."
    ::= { dhcpCounters 8 }

dhcpCountOffers OBJECT-TYPE
    SYNTAX          Counter
    ACCESS          read-only
    STATUS          mandatory
    DESCRIPTION     
            "The number of DHCPOFFER (option 53 with value 2) packets 
             sent."
--     REFERENCE       
--             "RFC2131; RFC2132, section 9.6."
    ::= { dhcpCounters 9 }

dhcpCountAcks OBJECT-TYPE
    SYNTAX          Counter
    ACCESS          read-only
    STATUS          mandatory
    DESCRIPTION     
            "The number of DHCPACK (option 53 with value 5) packets sent."
--     REFERENCE       
--             "RFC2131; RFC2132, section 9.6."
    ::= { dhcpCounters 10 }

dhcpCountNacks OBJECT-TYPE
    SYNTAX          Counter
    ACCESS          read-only
    STATUS          mandatory
    DESCRIPTION     
            "The number of DHCPNACK (option 53 with value 6) packets sent."
--     REFERENCE       
--             "RFC2131; RFC2132, section 9.6."
    ::= { dhcpCounters 11 }

dhcpCountForcedRenews OBJECT-TYPE
    SYNTAX          Counter
    ACCESS          read-only
    STATUS          mandatory
    DESCRIPTION     
            "The number of DHCPFORCERENEW (option 53 with value TBD) 
             packets sent."
--     REFERENCE       
--             "draft-ietf-dhc-pv4-reconfigure-06.txt."
    ::= { dhcpCounters 12 }

dhcpCountKnowns OBJECT-TYPE
    SYNTAX          Counter
    ACCESS          read-only
    STATUS          mandatory
    DESCRIPTION     
            "The number of DHCPKNOWN (option 53 with value TBD) packets 
             sent."
--     REFERENCE       
--             "draft-ietf-dhc-leasequery-03.txt."
    ::= { dhcpCounters 13 }

dhcpCountUnknowns OBJECT-TYPE
    SYNTAX          Counter
    ACCESS          read-only
    STATUS          mandatory
    DESCRIPTION     
            "The number of DHCPUNKNOWN (option 53 with value TBD) packets 
             sent."
--     REFERENCE       
--             "draft-ietf-dhc-leasequery-03.txt."
    ::= { dhcpCounters 14 }

dhcpCountActives OBJECT-TYPE
    SYNTAX          Counter
    ACCESS          read-only
    STATUS          mandatory
    DESCRIPTION     
            "The number of DHCPACTIVE (option 53 with value TBD) packets 
             sent."
--     REFERENCE       
--             "draft-ietf-dhc-leasequery-03.txt."
    ::= { dhcpCounters 15 }

dhcpCountUnimplementeds OBJECT-TYPE
    SYNTAX          Counter
    ACCESS          read-only
    STATUS          mandatory
    DESCRIPTION     
            "The number of DHCPUNIMPLEMENTED (option 53 with value TBD) 
             packets sent."
--     REFERENCE       
--             "draft-ietf-dhc-leasequery-03.txt."
    ::= { dhcpCounters 16 }

dhcpCountPlaceHolder3 OBJECT-TYPE
    SYNTAX          Counter
    ACCESS          read-only
    STATUS          mandatory
    DESCRIPTION     
            "Placeholder for anticipated new DHCP option 53 message types."
--     REFERENCE       
--             "None."
    ::= { dhcpCounters 17 }

dhcpCountPlaceHolder4 OBJECT-TYPE
    SYNTAX          Counter
    ACCESS          read-only
    STATUS          mandatory
    DESCRIPTION     
            "Placeholder for anticipated new DHCP option 53 message types."
--     REFERENCE       
--             "None."
    ::= { dhcpCounters 18 }

dhcpCountInvalids OBJECT-TYPE
    SYNTAX          Counter
    ACCESS          read-only
    STATUS          mandatory
    DESCRIPTION     
            "The number of DHCP packets received whose DHCP message type 
             (i.e., option number 53) is not understood or handled by the 
             server."
    ::= { dhcpCounters 19 }

dhcpCountDroppedUnknownClient OBJECT-TYPE
    SYNTAX          Counter
    ACCESS          read-only
    STATUS          mandatory
    DESCRIPTION     
            "The number of DHCP packets dropped due to the server not 
             recognizing or not providing service to the client-id and/or 
             hardware address received in the incoming packet."
    ::= { dhcpCounters 20 }

dhcpCountDroppedNotServingSubnet OBJECT-TYPE
    SYNTAX          Counter
    ACCESS          read-only
    STATUS          mandatory
    DESCRIPTION     
            "The number of DHCP packets dropped due to the server not being 
             configured or not otherwise able to serve addresses on the 
             subnet from which this message was received."
    ::= { dhcpCounters 21 }

bootpOptionalStatistics OBJECT IDENTIFIER
    ::= { serverMIBObjects 4 }

bootpStatMinArrivalInterval OBJECT-TYPE
    SYNTAX          DhcpTimeInterval
    ACCESS          read-only
    STATUS          mandatory
    DESCRIPTION     
            "The minimum amount of time between receiving two BOOTP 
             messages.  A message is received at the server when the server 
             is able to begin processing the message.  This typically occurs 
             immediately after the message is read into server memory.  If 
             no messages have been received, then this object contains a 
             zero value."
    ::= { bootpOptionalStatistics 1 }

bootpStatMaxArrivalInterval OBJECT-TYPE
    SYNTAX          DhcpTimeInterval
    ACCESS          read-only
    STATUS          mandatory
    DESCRIPTION     
            "The maximum amount of time between receiving two BOOTP 
             messages.  A message is received at the server when the server 
             is able to begin processing the message.  This typically occurs 
             immediately after the message is read into server memory.  If 
             no messages have been received, then this object contains a 
             zero value."
    ::= { bootpOptionalStatistics 2 }

bootpStatLastArrivalTime OBJECT-TYPE
    SYNTAX          DateAndTime
    ACCESS          read-only
    STATUS          mandatory
    DESCRIPTION     
            "The date and time that the last valid BOOTP message was 
             received by the server.  Invalid messages do not cause this 
             value to change.  If valid no messages have been received, then 
             this object contains a date and time that is all zero."
    ::= { bootpOptionalStatistics 3 }

-- bootpStatSumSquaresArrivalTime OBJECT-TYPE
--     SYNTAX          Counter64
--     ACCESS          read-only
--     STATUS          mandatory
--     DESCRIPTION     
--             "The sum of the squared BOOTP packet inter-arrival times in 
--              microseconds.  This value may be used to compute the variance 
--              and standard deviation of the BOOTP arrival times.  Note that a 
--              microsecond resolution of this object requires a clock 
--              resolution to the millisecond since the square of a millisecond 
--              value produces a value with microsecond resolution."
--     ::= { bootpOptionalStatistics 4 }

bootpStatMinResponseTime OBJECT-TYPE
    SYNTAX          DhcpTimeInterval
    ACCESS          read-only
    STATUS          mandatory
    DESCRIPTION     
            "The smallest time interval measured as the difference between 
             the arrival of a BOOTP message at the server and the successful 
             transmission of the response to that message.  A message is 
             received at the server when the server is able to begin 
             processing the message.  A message is transmitted after the 
             server has no further use for the message.  Note that the 
             operating system may still have the message queued internally. 
              
             The operating system queue time is not to be considered as part 
             of the response time.  Invalid messages do not cause this value 
             to change.  If no valid messages have been received, then this 
             object contains a zero value."
    ::= { bootpOptionalStatistics 5 }

bootpStatMaxResponseTime OBJECT-TYPE
    SYNTAX          DhcpTimeInterval
    ACCESS          read-only
    STATUS          mandatory
    DESCRIPTION     
            "The largest time interval measured as the difference between 
             the arrival of a BOOTP message at the server and the successful 
             transmission of the response to that message.  A message is 
             received at the server when the server is able to begin 
             processing the message.  A message is transmitted after the 
             server has no further use for the message.  Note that the 
             operating system may still have the message queued internally. 
              
             The operating system queue time is not to be considered as part 
             of the response time.  Invalid messages do not cause this value 
             to change.  If no valid messages have been received, then this 
             object contains a zero value."
    ::= { bootpOptionalStatistics 6 }

bootpStatSumResponseTime OBJECT-TYPE
    SYNTAX          Counter
    ACCESS          read-only
    STATUS          mandatory
    DESCRIPTION     
            "The sum of the response time intervals in milliseconds where a 
             response time interval is measured as the difference between 
             the arrival of a BOOTP message at the server and the successful 
             transmission of the response to that message.  A message is 
             received at the server when the server is able to begin 
             processing the message.  A message is transmitted after the 
             server has no further use for the message.  Note that the 
             operating system may still have the message queued internally. 
              
             The operating system queue time is not to be considered as part 
             of the response time.  Invalid messages do not cause this value 
             to change.  If no valid messages have been received, then this 
             object contains a zero value."
    ::= { bootpOptionalStatistics 7 }

-- bootpStatSumSquaresResponseTime OBJECT-TYPE
--     SYNTAX          Counter64
--     ACCESS          read-only
--     STATUS          mandatory
--     DESCRIPTION     
--             "The sum of the squared BOOTP packet response times in micro- 
--              seconds.  This value may be used to compute the variance and 
--              standard deviation of the BOOTP response times.  Note that a 
--              microsecond resolution of this object requires a clock 
--              resolution to the millisecond since the square of a millisecond 
--              value produces a value with microsecond resolution."
--     ::= { bootpOptionalStatistics 8 }

dhcpOptionalStatistics OBJECT IDENTIFIER
    ::= { serverMIBObjects 5 }

dhcpStatMinArrivalInterval OBJECT-TYPE
    SYNTAX          DhcpTimeInterval
    ACCESS          read-only
    STATUS          mandatory
    DESCRIPTION     
            "The minimum amount of time between receiving two DHCP 
             messages.  A message is received at the server when the server 
             is able to begin processing the message.  This typically occurs 
             immediately after the message is read into server memory.  If 
             no messages have been received, then this object contains a 
             zero value."
    ::= { dhcpOptionalStatistics 1 }

dhcpStatMaxArrivalInterval OBJECT-TYPE
    SYNTAX          DhcpTimeInterval
    ACCESS          read-only
    STATUS          mandatory
    DESCRIPTION     
            "The maximum amount of time between receiving two DHCP 
             messages.  A message is received at the server when the server 
             is able to begin processing the message.  This typically occurs 
             immediately after the message is read into server memory.  If 
             no messages have been received, then this object contains a 
             zero value."
    ::= { dhcpOptionalStatistics 2 }

dhcpStatLastArrivalTime OBJECT-TYPE
    SYNTAX          DateAndTime
    ACCESS          read-only
    STATUS          mandatory
    DESCRIPTION     
            "The date and time that the last valid DHCP message was 
             received by the server.  Invalid messages do not cause this 
             value to change.  If no valid messages have been received, then 
             this object contains a date and time that is all zero."
    ::= { dhcpOptionalStatistics 3 }

-- dhcpStatSumSquaresArrivalTime OBJECT-TYPE
--     SYNTAX          Counter64
--     ACCESS          read-only
--     STATUS          mandatory
--     DESCRIPTION     
--             "The sum of the squared DHCP packet inter-arrival times in 
--              microseconds.  This value may be used to compute the variance 
--              and standard deviation of the DHCP arrival times.  Note that a 
--              microsecond resolution of this object requires a clock 
--              resolution to the millisecond since the square of a millisecond 
--              value produces a value with microsecond resolution."
--     ::= { dhcpOptionalStatistics 4 }

dhcpStatMinResponseTime OBJECT-TYPE
    SYNTAX          DhcpTimeInterval
    ACCESS          read-only
    STATUS          mandatory
    DESCRIPTION     
            "The smallest time interval measured as the difference between 
             the arrival of a DHCP message at the server and the successful 
             transmission of the response to that message.  A message is 
             received at the server when the server is able to begin 
             processing the message.  A message is transmitted after the 
             server has no further use for the message.  Note that the 
             operating system may still have the message queued internally.  
             The operating system queue time is not to be considered as part 
             of the response time.  Invalid messages do not cause this value 
             to change.  If no valid messages have been received, then this 
             object contains a zero value."
    ::= { dhcpOptionalStatistics 5 }

dhcpStatMaxResponseTime OBJECT-TYPE
    SYNTAX          DhcpTimeInterval
    ACCESS          read-only
    STATUS          mandatory
    DESCRIPTION     
            "The largest time interval measured as the difference between 
             the arrival of a DHCP message at the server and the successful 
             transmission of the response to that message.  A message is 
             received at the server when the server is able to begin 
             processing the message.  A message is transmitted after the 
             server has no further use for the message.  Note that the 
             operating system may still have the message queued internally.  
             The operating system queue time is not to be considered as part 
             of the response time.  Invalid messages do not cause this value 
             to change.  If no valid messages have been received, then this 
             object contains a zero value."
    ::= { dhcpOptionalStatistics 6 }

dhcpStatSumResponseTime OBJECT-TYPE
    SYNTAX          Counter
    ACCESS          read-only
    STATUS          mandatory
    DESCRIPTION     
            "The sum of the response time intervals in milliseconds where a 
             response time interval is measured as the difference between 
             the arrival of a DHCP message at the server and the successful 
             transmission of the response to that message.  A message is 
             received at the server when the server is able to begin 
             processing the message.  A message is transmitted after the 
             server has no further use for the message.  Note that the 
             operating system may still have the message queued internally.  
             The operating system queue time is not to be considered as part 
             of the response time.  Invalid messages do not cause this value 
             to change.  If no valid messages have been received, then this 
             object contains a zero value."
    ::= { dhcpOptionalStatistics 7 }

-- dhcpStatSumSquaresResponseTime OBJECT-TYPE
--     SYNTAX          Counter64
--     ACCESS          read-only
--     STATUS          mandatory
--     DESCRIPTION     
--             "The sum of the squared DHCP packet response times in micro- 
--              seconds.  This value may be used to compute the variance and 
--              standard deviation of the DHCP response times.  Note that a 
--              microsecond resolution of this object requires a clock 
--              resolution to the millisecond since the square of a millisecond 
--              value produces a value with microsecond resolution."
--     ::= { dhcpOptionalStatistics 8 }

serverConfiguration OBJECT IDENTIFIER
    ::= { serverMIBObjects 6 }

serverSharedNetworkTable OBJECT-TYPE
    SYNTAX          SEQUENCE OF ServerSharedNetworkEntry
    ACCESS          not-accessible
    STATUS          mandatory
    DESCRIPTION     
            "A list of shared networks that are configured in the server.  
             A shared network is the logical aggregation of one or more 
             subnets that share a common network segment (e.g., multi-tapped 
             coaxial cable, wiring hub, or switch).  This table is present 
             ONLY for those servers that organize the ranges of addresses 
             available for assignment where a higher-level grouping (i.e., 
             the `shared' network) exists above ranges and subnets."
    ::= { serverConfiguration 1 }

serverSharedNetworkEntry OBJECT-TYPE
    SYNTAX          ServerSharedNetworkEntry
    ACCESS          not-accessible
    STATUS          mandatory
    DESCRIPTION     
            "A logical row in the serverSharedNetworkTable."
    INDEX           { serverSharedNetworkName }
    ::= { serverSharedNetworkTable 1 }

ServerSharedNetworkEntry ::=
    SEQUENCE {
        serverSharedNetworkName         SnmpAdminString,
        serverSharedNetworkFreeAddresses Gauge,
        serverSharedNetworkReservedAddresses    Gauge,
        serverSharedNetworkTotalAddresses Gauge
    }

serverSharedNetworkName OBJECT-TYPE
    SYNTAX          SnmpAdminString (SIZE(1..100))
    ACCESS          not-accessible
    STATUS          mandatory
    DESCRIPTION     
            "The name of the shared network, which uniquely identifies an 
             entry in the serverSharedNetworkTable."
    ::= { serverSharedNetworkEntry 1 }

serverSharedNetworkFreeAddresses OBJECT-TYPE
    SYNTAX          Gauge
    ACCESS          read-only
    STATUS          mandatory
    DESCRIPTION     
            "The number of IP addresses which are available within this 
             shared network.  If the server does not count free addresses by 
             shared network segment, this value will be zero."
    ::= { serverSharedNetworkEntry 2 }

serverSharedNetworkReservedAddresses OBJECT-TYPE
    SYNTAX          Gauge
    ACCESS          read-only
    STATUS          mandatory
    DESCRIPTION     
            "The number of IP addresses which are reserved (not available 
             for assignement) within this shared network.  If the server 
             does not count reserved addresses by shared network segment, 
             this value will be zero."
    ::= { serverSharedNetworkEntry 3 }

serverSharedNetworkTotalAddresses OBJECT-TYPE
    SYNTAX          Gauge
    ACCESS          read-only
    STATUS          mandatory
    DESCRIPTION     
            "The number of IP addresses which are available within this 
             shared network.  If the server does not count total addresses 
             by shared network segment, this value will be zero."
    ::= { serverSharedNetworkEntry 4 }

serverSubnetTable OBJECT-TYPE
    SYNTAX          SEQUENCE OF ServerSubnetEntry
    ACCESS          not-accessible
    STATUS          mandatory
    DESCRIPTION     
            "A list of subnets that are configured in this server."
    ::= { serverConfiguration 2 }

serverSubnetEntry OBJECT-TYPE
    SYNTAX          ServerSubnetEntry
    ACCESS          not-accessible
    STATUS          mandatory
    DESCRIPTION     
            "A logical row in the serverSubnetTable."
    INDEX           { serverSubnet }
    ::= { serverSubnetTable 1 }

ServerSubnetEntry ::=
    SEQUENCE {
        serverSubnet                    InetAddressIPv4,
        serverSubnetMask                InetAddressIPv4,
        serverSubnetSharedNetworkName   SnmpAdminString,
        serverSubnetFreeAddressLowThreshold   Gauge,
        serverSubnetFreeAddressHighThreshold    Gauge,
        serverSubnetFreeAddresses       Gauge
    }

serverSubnet OBJECT-TYPE
    SYNTAX          InetAddressIPv4
    ACCESS          read-only
    STATUS          mandatory
    DESCRIPTION     
            "The IP address of the subnet."
    ::= { serverSubnetEntry 1 }

serverSubnetMask OBJECT-TYPE
    SYNTAX          InetAddressIPv4
    ACCESS          read-only
    STATUS          mandatory
    DESCRIPTION     
            "The subnet mask of the subnet.  This MUST be the same as the 
             value of DHCP option 1 offered to clients on this subnet."
    ::= { serverSubnetEntry 2 }

serverSubnetSharedNetworkName OBJECT-TYPE
    SYNTAX          SnmpAdminString (SIZE(1..100))
    ACCESS          read-only
    STATUS          mandatory
    DESCRIPTION     
            "The shared subnet name (used as an index into the server 
             shared subnet table) to which this subnet belongs.  This value 
             will be null for servers that do not organize or describe 
             networks in this manner."
    ::= { serverSubnetEntry 3 }

serverSubnetFreeAddressLowThreshold OBJECT-TYPE
    SYNTAX          Gauge
    ACCESS          read-only
    STATUS          mandatory
    DESCRIPTION     
            "The low threshold for available free addresses in this subnet.  
             If the value for available free addresses in this subnet 
             becomes equal to or less than this value, a 
             serverSubnetFreeAddressLowThreshold event is generated for this 
             shared network.  No more serverSubnetFreeAddressLowThreshold 
             events will be generated for this subnet during this execution 
             of the DHCP server until the value for available free addresses 
             has exceeded the value of 
             serverSubnetFreeAddressHighThreshold."
    ::= { serverSubnetEntry 4 }

serverSubnetFreeAddressHighThreshold OBJECT-TYPE
    SYNTAX          Gauge
    ACCESS          read-only
    STATUS          mandatory
    DESCRIPTION     
            "The high threshold for available free addresses in this 
             subnet.  If a serverSubnetFreeAddressLowThreshold event has 
             been generated for this subnet, and the value for available 
             free addresses has exceeded the value of 
             serverSubnetFreeAddressHighThreshold, then a 
             serverFreeAddressessHigh event will be generated.  No more 
             serverFreeAddressessHigh events will be generated for this 
             subnet during this execution of the DHCP server until the value 
             for available free addresses becomes equal to or less than the 
             value of serverSubnetFreeAddressHighThreshold."
    ::= { serverSubnetEntry 5 }

serverSubnetFreeAddresses OBJECT-TYPE
    SYNTAX          Gauge
    ACCESS          read-only
    STATUS          mandatory
    DESCRIPTION     
            ""
    ::= { serverSubnetEntry 6 }

serverRangeTable OBJECT-TYPE
    SYNTAX          SEQUENCE OF ServerRangeEntry
    ACCESS          not-accessible
    STATUS          mandatory
    DESCRIPTION     
            "A list of ranges that are configured on this server."
    ::= { serverConfiguration 3 }

serverRangeEntry OBJECT-TYPE
    SYNTAX          ServerRangeEntry
    ACCESS          not-accessible
    STATUS          mandatory
    DESCRIPTION     
            "A logical row in the serverRangeTable."
    INDEX           { serverRangeStart }
    ::= { serverRangeTable 1 }

ServerRangeEntry ::=
    SEQUENCE {
        serverRangeStart                InetAddressIPv4,
        serverRangeEnd                  InetAddressIPv4,
        serverRangeSubnetMask           InetAddressIPv4,
        serverRangeInUse                Gauge,
        serverRangeOutstandingOffers    Gauge
    }

serverRangeStart OBJECT-TYPE
    SYNTAX          InetAddressIPv4
    ACCESS          read-only
    STATUS          mandatory
    DESCRIPTION     
            "The IP address of the first address in the range.  The value 
             of range start must be less than or equal to the value of range 
             end."
    ::= { serverRangeEntry 1 }

serverRangeEnd OBJECT-TYPE
    SYNTAX          InetAddressIPv4
    ACCESS          read-only
    STATUS          mandatory
    DESCRIPTION     
            "The IP address of the last address in the range.  The value of 
             range end must be greater than or equal to the value of range 
             start."
    ::= { serverRangeEntry 2 }

serverRangeSubnetMask OBJECT-TYPE
    SYNTAX          InetAddressIPv4
    ACCESS          read-only
    STATUS          mandatory
    DESCRIPTION     
            "The subnet address mask for this range."
    ::= { serverRangeEntry 3 }

serverRangeInUse OBJECT-TYPE
    SYNTAX          Gauge
    ACCESS          read-only
    STATUS          mandatory
    DESCRIPTION     
            "The number of addresses in this range that are currently in 
             use.  This number includes those addresses whose lease has not 
             expired and addresses which have been reserved (either by the 
             server or through configuration)."
    ::= { serverRangeEntry 4 }

serverRangeOutstandingOffers OBJECT-TYPE
    SYNTAX          Gauge
    ACCESS          read-only
    STATUS          mandatory
    DESCRIPTION     
            "The number of outstanding DHCPOFFER messages for this range is 
             reported with this value.  An offer is outstanding if the 
             server has sent a DHCPOFFER message to a client, but has not 
             yet received a DHCPREQUEST message from the client nor has the 
             server-specific timeout (limiting the time in which a client 
             can respond to the offer message) for the offer message 
             expired."
    ::= { serverRangeEntry 5 }

serverAddressTable OBJECT-TYPE
    SYNTAX          SEQUENCE OF ServerAddressEntry
    ACCESS          not-accessible
    STATUS          mandatory
    DESCRIPTION     
            "An optional list of addresses that are known by this server.  
             The list MUST contain addresses that have not expired.  The 
             list MUST NOT contain addresses that have never been assigned 
             by the server UNLESS the lease is pre-configured in the server 
             (e.g., a static lease for a host).  Expired leases MAY appear 
             during the time they are 'remembered' by the server for 
             subsequent assignment to the same host."
    ::= { serverConfiguration 4 }

serverAddressEntry OBJECT-TYPE
    SYNTAX          ServerAddressEntry
    ACCESS          not-accessible
    STATUS          mandatory
    DESCRIPTION     
            "A logical row in the serverAddressTable."
    INDEX           { serverAddress }
    ::= { serverAddressTable 1 }

ServerAddressEntry ::=
    SEQUENCE {
        serverAddress                   InetAddressIPv4,
        serverAddressSubnetMask         InetAddressIPv4,
        serverAddressRange              InetAddressIPv4,
        serverAddressType               INTEGER,
        serverAddressTimeRemaining      Gauge,
        serverAddressAllowedProtocol    INTEGER,
        serverAddressServedProtocol     INTEGER,
        serverAddressHardwareAddress    PhysicalAddress,
        serverAddressClientId           OCTET STRING,
        serverAddressHostName           SnmpAdminString,
        serverAddressDomainName         SnmpAdminString
    }

serverAddress OBJECT-TYPE
    SYNTAX          InetAddressIPv4
    ACCESS          not-accessible
    STATUS          mandatory
    DESCRIPTION     
            "The IP address of the entry."
    ::= { serverAddressEntry 1 }

serverAddressSubnetMask OBJECT-TYPE
    SYNTAX          InetAddressIPv4
    ACCESS          read-only
    STATUS          mandatory
    DESCRIPTION     
            "The subnet mask (DHCP option 1) provided to the client offered 
             this address.  The subnet, resulting from logically ANDing the 
             subnet mask with the entry's IP address, must be configured on 
             this server and appear as a row in the dhcpSubnetTable."
    ::= { serverAddressEntry 2 }

serverAddressRange OBJECT-TYPE
    SYNTAX          InetAddressIPv4
    ACCESS          read-only
    STATUS          mandatory
    DESCRIPTION     
            "The starting IP address (serverRangeStart object) of the range 
             to which this address belongs.  If the address does not fall 
             into one of the configured ranges (e.g., a statically 
             configured address on a subnet) the range may be 0.0.0.0."
    ::= { serverAddressEntry 3 }

serverAddressType OBJECT-TYPE
    SYNTAX          INTEGER { static(1), dynamic(2), expired(3), 
                        configuration-reserved(4), server-reserved(5) }
    ACCESS          read-only
    STATUS          mandatory
    DESCRIPTION     
            "The type of this address.  Types are: 
             (1) Static addresses defined by the server configuration. 
             (2) Dynamic addresses defined by the server configuration 
                 AND actually assigned by the server. 
             (3) Expired dynamic addresses, previously assigned by the 
                 server and 'remembered' for subsequent assignment to the 
                 same host. 
             (4) Addresses reserved (i.e., not assignable) by the server 
                 configuration. 
             (5) Addresses previously assigned by the server, but 
                 temporarily or permanently removed from assignable state 
                 for some reason, e.g., the server received an ICMP 
                 ECHOREPLY for the IP address or a DHCPDECLINE message 
                 has been received for the IP address."
    ::= { serverAddressEntry 4 }

serverAddressTimeRemaining OBJECT-TYPE
    SYNTAX          Gauge
    ACCESS          read-only
    STATUS          mandatory
    DESCRIPTION     
            "The number of seconds until the lease expires.  A value of 
             4294967295 (i.e., 0xFFFFFFFF) should be used for leases that 
             have a lease time which is 'infinite' and for BOOTP leases."
    ::= { serverAddressEntry 5 }

serverAddressAllowedProtocol OBJECT-TYPE
    SYNTAX          INTEGER { none(1), bootp(2), dhcp(3), 
                        bootp-or-dhcp(4) }
    ACCESS          read-only
    STATUS          mandatory
    DESCRIPTION     
            "The type of protocol that is allowed to be used to serve this 
             address.  A type of none (1) indicates that the address is not 
             available to be served (e.g., a reserved address).Type (2) are 
             reserved for BOOTP only devices, while type (3) are reserved 
             for DHCP only devices.  A type of bootp-or-dhcp (4) may be 
             offered to any type of client."
    ::= { serverAddressEntry 6 }

serverAddressServedProtocol OBJECT-TYPE
    SYNTAX          INTEGER { none(1), bootp(2), dhcp(3) }
    ACCESS          read-only
    STATUS          mandatory
    DESCRIPTION     
            "The type of protocol that was used when this address was 
             assigned.  This object will have the value of none (1) if the 
             address has not been served."
    ::= { serverAddressEntry 7 }

serverAddressHardwareAddress OBJECT-TYPE
    SYNTAX          PhysicalAddress
    ACCESS          read-only
    STATUS          mandatory
    DESCRIPTION     
            "The hardware type and hardware address of the client that has 
             been assigned this lease.  The first octet of this object 
             contains the hardware type from the 'htype' field of the BOOTP 
             packet and the remaining octets contain the hardware address 
             from the 'chaddr' field of the BOOTP packet.  This object may 
             be empty if the address has not been previously served."
    ::= { serverAddressEntry 8 }

serverAddressClientId OBJECT-TYPE
    SYNTAX          OCTET STRING (SIZE(0..255))
    ACCESS          read-only
    STATUS          mandatory
    DESCRIPTION     
            "The client-id of the client that has been assigned this lease.  
             The client-id is the value specified in option 61 (client-id 
             option) when the lease was assigned.  This object may be empty 
             if the lease has not been previously assigned or if the client-
             id option was not specified when the address was assigned."
    ::= { serverAddressEntry 9 }

serverAddressHostName OBJECT-TYPE
    SYNTAX          SnmpAdminString (SIZE(1..255))
    ACCESS          read-only
    STATUS          mandatory
    DESCRIPTION     
            "The host name (DHCP option 12) the client is configured to 
             use, or if no host name was configured then the host name that 
             the client supplied when requesting an address.  While this 
             object has a maximum size of 255 octets, a Fully-Qualified 
             Domain Name (FQDN) consisting of a Host Name part and a Domain 
             Name part is currently limited to 255 octets.  Therefore, the 
             sum of the string lengths for this object and the 
             serverAddressDomainName must, in practice, be less than 256 
             octets."
    ::= { serverAddressEntry 10 }

serverAddressDomainName OBJECT-TYPE
    SYNTAX          SnmpAdminString (SIZE(1..255))
    ACCESS          read-only
    STATUS          mandatory
    DESCRIPTION     
            "The domain name (DHCP option 15) assigned to the client.  
             While this object has a maximum size of 255 octets, a Fully-
             Qualified Domain Name (FQDN) consisting of a Host Name part and 
             a Domain Name part is currently limited to 255 octets, less the 
             separator (.) character.  Therefore, the sum of the string 
             lengths for this object and the serverAddressHostName must, in 
             practice, be less than 256 octets."
    ::= { serverAddressEntry 11 }

serverClientTable OBJECT-TYPE
    SYNTAX          SEQUENCE OF ServerClientEntry
    ACCESS          not-accessible
    STATUS          mandatory
    DESCRIPTION     
            "A list of clients that are known by this server.  Details 
             about the clients may be found by indexing into the 
             serverAddressTable using the serverClientHardwareAddress and 
             serverClientAddress objects.  This table is indexed first by 
             the MAC address of the client and then by the subnet address on 
             which the client resides.  The subnet is included as an index 
             since a MAC address is only guaranteed to be unique within a 
             subnet (i.e., a MAC address is not globally unique)."
    ::= { serverConfiguration 5 }

serverClientEntry OBJECT-TYPE
    SYNTAX          ServerClientEntry
    ACCESS          not-accessible
    STATUS          mandatory
    DESCRIPTION     
            "A logical row in the serverClientTable.  An entry in this 
             table may be a client that requested an address but was refused 
             (e.g., not authorized).Servers MAY track these types of clients 
             if desired and may choose to remove such client entries using a 
             server defined algorithm.  As an example, a server may choose 
             to keep client request that does not map to an address for a 
             one hour time period before removing that entry from this 
             table."
    INDEX           { serverClientHardwareAddress, serverClientAddress }
    ::= { serverClientTable 1 }

ServerClientEntry ::=
    SEQUENCE {
        serverClientHardwareAddress     PhysicalAddress,
        serverClientAddress             InetAddressIPv4,
        serverClientSubnetMask          InetAddressIPv4,
        serverClientLastRequestTime     DateAndTime,
        serverClientLastRequestType     INTEGER,
        serverClientLastResponseType    INTEGER
    }

serverClientHardwareAddress OBJECT-TYPE
    SYNTAX          PhysicalAddress
    ACCESS          not-accessible
    STATUS          mandatory
    DESCRIPTION     
            "The hardware type and hardware address of the client that has 
             been assigned this lease.  The first octet of this object 
             contains the hardware type from the 'htype' field of the BOOTP 
             packet and the remaining octets contain the hardware address 
             from the 'chaddr' field of the BOOTP packet."
    ::= { serverClientEntry 1 }

serverClientAddress OBJECT-TYPE
    SYNTAX          InetAddressIPv4
    ACCESS          read-only
    STATUS          mandatory
    DESCRIPTION     
            "The IP address of the entry.  May be used to index into the 
             serverAddressTable.  May be 0.0.0.0 if an address is not 
             associated with this client."
    ::= { serverClientEntry 2 }

serverClientSubnetMask OBJECT-TYPE
    SYNTAX          InetAddressIPv4
    ACCESS          not-accessible
    STATUS          mandatory
    DESCRIPTION     
            "The subnet mask (DHCP option 1) applied to 
             serverClientAddress."
    ::= { serverClientEntry 3 }

serverClientLastRequestTime OBJECT-TYPE
    SYNTAX          DateAndTime
    ACCESS          read-only
    STATUS          mandatory
    DESCRIPTION     
            "The timestamp of the last request received, to millisecond 
             precision if available on the server."
    ::= { serverClientEntry 4 }

serverClientLastRequestType OBJECT-TYPE
    SYNTAX          INTEGER { bootprequest(0), dhcpdiscover(1), 
                        dhcprequest(3), dhcpdecline(4), dhcprelease(7), 
                        dhcpinform(8), dhcpleasequery(99) }
    ACCESS          read-only
    STATUS          mandatory
    DESCRIPTION     
            "The type of the last request message received for this 
             client.If the server does not capture this information, the 
             value 32,767 is returned."
--     REFERENCE       
--             "RFC2131; RFC2132, section 9.6; draft-ietf-dhc-leasequery-
--              02.txt."
    ::= { serverClientEntry 5 }

serverClientLastResponseType OBJECT-TYPE
    SYNTAX          INTEGER { bootpreply(1), dhcpoffer(2), dhcpack(5), 
                        dhcpnak(6), dhcpknown(99), dhcpunknown(98) }
    ACCESS          read-only
    STATUS          mandatory
    DESCRIPTION     
            "The type of the last response message sent to this client.  If 
             the server does not capture this information, the value 32,767 
             is returned."
--     REFERENCE       
--             "RFC2131; RFC2132, section 9.6;draft-ietf-dhc-pv4-reconfigure-
--              06.txt;draft-ietf-dhc-leasequery-02.txt"
    ::= { serverClientEntry 6 }

bootpClients OBJECT IDENTIFIER
    ::= { serverMIBObjects 7 }

dhcpClients OBJECT IDENTIFIER
    ::= { serverMIBObjects 8 }

serverNotifyObjects OBJECT IDENTIFIER
    ::= { serverMIB 2 }

serverNotifyDuplicateIpAddress OBJECT-TYPE
    SYNTAX          InetAddressIPv4
    ACCESS          read-only
    STATUS          mandatory
    DESCRIPTION     
            "The IP address found to be a duplicate.  Duplicates are 
             detected by servers which issue an ICMP ECHOREQUEST prior to 
             offering an IP address lease."
    ::= { serverNotifyObjects 1 }

serverNotifyDuplicateMAC OBJECT-TYPE
    SYNTAX          PhysicalAddress
    ACCESS          read-only
    STATUS          mandatory
    DESCRIPTION     
            "The offending MAC address which caused a duplicate IP address 
             to be detected, if captured by the server, else 00-00-00-00-00-
             00."
    ::= { serverNotifyObjects 2 }

serverNotifyClientDuplicateIP OBJECT-TYPE
    SYNTAX          InetAddressIPv4
    ACCESS          read-only
    STATUS          mandatory
    DESCRIPTION     
            "The IP Address offered by a server that the requesting client 
             has determined to be a duplicate, detected by means of a 
             gratuitous ARP message and reported through a DHCPDECLINE 
             message."
    ::= { serverNotifyObjects 3 }

serverMIBNotificationPrefix OBJECT IDENTIFIER
    ::= { serverMIB 3 }

serverMIBNotifications OBJECT IDENTIFIER
    ::= { serverMIBNotificationPrefix 0 }

serverMIBConformance OBJECT IDENTIFIER
    ::= { serverMIB 4 }

serverMIBCompliances OBJECT IDENTIFIER
    ::= { serverMIBConformance 1 }

serverMIBGroups OBJECT IDENTIFIER
    ::= { serverMIBConformance 2 }

serverFreeAddressLow TRAP-TYPE
    ENTERPRISE      serverMIBNotificationPrefix
    VARIABLES       { serverSubnetFreeAddressLowThreshold, 
                      serverSubnetFreeAddresses }
--     STATUS          mandatory
    DESCRIPTION     
            "This notification signifies that the number of available IP 
             addresses for a particular shared network has fallen below the 
             value of serverSharedNetworkFreeAddressLowThreshold for that 
             shared network."
    ::= 1

serverFreeAddressHigh TRAP-TYPE
    ENTERPRISE      serverMIBNotificationPrefix
    VARIABLES       { serverSubnetFreeAddressHighThreshold, 
                      serverSubnetFreeAddresses }
--     STATUS          mandatory
    DESCRIPTION     
            "This notification signifies that the number of available IP 
             addresses for a particular shared network has risen above the 
             value of serverSharedNetworkFreeAddressHighThreshold for that 
             shared network."
    ::= 2

serverServerStart TRAP-TYPE
    ENTERPRISE      serverMIBNotificationPrefix
    VARIABLES       { serverNotifyClientDuplicateIP }
--     STATUS          mandatory
    DESCRIPTION     
            "This notification signifies that the server of the specified 
             type has started on the host from which this notification has 
             been sent."
    ::= 3

serverServerStop TRAP-TYPE
    ENTERPRISE      serverMIBNotificationPrefix
    VARIABLES       { serverNotifyClientDuplicateIP }
--     STATUS          mandatory
    DESCRIPTION     
            "This notification signifies that the server of the specified 
             type has stopped normally on the host from which this 
             notification has been sent."
    ::= 4

serverDuplicateAddress TRAP-TYPE
    ENTERPRISE      serverMIBNotificationPrefix
    VARIABLES       { serverNotifyDuplicateIpAddress, 
                      serverNotifyDuplicateMAC }
--     STATUS          mandatory
    DESCRIPTION     
            "This notification signifies that a duplicate IP address has 
             been detected.  The DHCP server can detect this condition 
             through the ping-before-offer mechanism.  Alternatively, the 
             client may have sent a DHCPDECLINE back to the server; this is 
             assumed to be the result of the client detecting that the 
             address was in use.  In either case, the DHCP server marks the 
             IP address as unavailable for leasing to clients.  The 
             serverNotifyClientDuplicateMAC object indicates whether the 
             client or server detected this condition."
    ::= 5

serverAddressConflict TRAP-TYPE
    ENTERPRISE      serverMIBNotificationPrefix
    VARIABLES       { serverNotifyClientDuplicateIP }
--     STATUS          mandatory
    DESCRIPTION     
            ""
    ::= 6

serverSystemGroup OBJECT IDENTIFIER
    ::= { serverMIBGroups 1 }

-- serverSystemGroup OBJECT-GROUP
--     OBJECTS         { serverSystemDescr, serverSystemObjectID }
--     STATUS          mandatory
--     DESCRIPTION     
--             "Objects belonging to the serverSystemGroup."
--     ::= { serverMIBGroups 1 }

bootpCountersGroup OBJECT IDENTIFIER
    ::= { serverMIBGroups 2 }

-- bootpCountersGroup OBJECT-GROUP
--     OBJECTS         { bootpCountRequests, bootpCountInvalids, 
--                       bootpCountReplies, 
--                       bootpCountDroppedUnknownClients, 
--                       bootpCountDroppedNotServingSubnet }
--     STATUS          mandatory
--     DESCRIPTION     
--             "Objects belonging to the bootpBountersGroup."
--     ::= { serverMIBGroups 2 }

dhcpCountersGroup OBJECT IDENTIFIER
    ::= { serverMIBGroups 3 }

-- dhcpCountersGroup OBJECT-GROUP
--     OBJECTS         { dhcpCountDiscovers, dhcpCountRequests, 
--                       dhcpCountReleases, dhcpCountDeclines, 
--                       dhcpCountInforms, dhcpCountLeaseQueries, 
--                       dhcpCountPlaceHolder1, dhcpCountPlaceHolder2, 
--                       dhcpCountOffers, dhcpCountAcks, dhcpCountNacks, 
--                       dhcpCountForcedRenews, dhcpCountKnowns, 
--                       dhcpCountUnknowns, dhcpCountActives, 
--                       dhcpCountUnimplementeds, dhcpCountPlaceHolder3, 
--                       dhcpCountPlaceHolder4, dhcpCountInvalids, 
--                       dhcpCountDroppedUnknownClient, 
--                       dhcpCountDroppedNotServingSubnet }
--     STATUS          mandatory
--     DESCRIPTION     
--             "Objects belonging to the dhcpCountersGroup."
--     ::= { serverMIBGroups 3 }

bootpOptionalStatisticsGroup OBJECT IDENTIFIER
    ::= { serverMIBGroups 4 }

-- bootpOptionalStatisticsGroup OBJECT-GROUP
--     OBJECTS         { bootpStatMinArrivalInterval, 
--                       bootpStatMaxArrivalInterval, 
--                       bootpStatLastArrivalTime, 
--                       bootpStatSumSquaresArrivalTime, 
--                       bootpStatMinResponseTime, 
--                       bootpStatMaxResponseTime, 
--                       bootpStatSumResponseTime, 
--                       bootpStatSumSquaresResponseTime }
--     STATUS          mandatory
--     DESCRIPTION     
--             "Objects belonging to the bootpOptionalStatisticsGroup."
--     ::= { serverMIBGroups 4 }

dhcpOptionalStatisticsGroup OBJECT IDENTIFIER
    ::= { serverMIBGroups 5 }

-- dhcpOptionalStatisticsGroup OBJECT-GROUP
--     OBJECTS         { dhcpStatMinArrivalInterval, 
--                       dhcpStatMaxArrivalInterval, 
--                       dhcpStatLastArrivalTime, 
--                       dhcpStatSumSquaresArrivalTime, 
--                       dhcpStatMinResponseTime, 
--                       dhcpStatMaxResponseTime, 
--                       dhcpStatSumResponseTime, 
--                       dhcpStatSumSquaresResponseTime }
--     STATUS          mandatory
--     DESCRIPTION     
--             "Objects belonging to the dhcpOptionalStatisticsGroup."
--     ::= { serverMIBGroups 5 }

serverConfigurationGroup OBJECT IDENTIFIER
    ::= { serverMIBGroups 6 }

-- serverConfigurationGroup OBJECT-GROUP
--     OBJECTS         { serverSubnet, serverSubnetMask, 
--                       serverSubnetSharedNetworkName, serverRangeStart, 
--                       serverRangeEnd, serverRangeSubnetMask, 
--                       serverRangeInUse, serverRangeOutstandingOffers, 
--                       serverAddressSubnetMask, serverAddressRange, 
--                       serverAddressType, serverAddressTimeRemaining, 
--                       serverAddressAllowedProtocol, 
--                       serverAddressServedProtocol, 
--                       serverAddressHardwareAddress, 
--                       serverAddressClientId, serverAddressHostName, 
--                       serverAddressDomainName }
--     STATUS          mandatory
--     DESCRIPTION     
--             "Objects belonging to the serverConfigurationGroup."
--     ::= { serverMIBGroups 6 }

serverClientsGroup OBJECT IDENTIFIER
    ::= { serverMIBGroups 7 }

-- serverClientsGroup OBJECT-GROUP
--     OBJECTS         { serverClientAddress, 
--                       serverClientLastRequestTime, 
--                       serverClientLastRequestType, 
--                       serverClientLastResponseType }
--     STATUS          mandatory
--     DESCRIPTION     
--             "Objects belonging to the serverClientsGroup."
--     ::= { serverMIBGroups 7 }

serverSharedNetworkObjectsGroup OBJECT IDENTIFIER
    ::= { serverMIBGroups 8 }

-- serverSharedNetworkObjectsGroup OBJECT-GROUP
--     OBJECTS         { serverSubnetFreeAddressLowThreshold, 
--                       serverSubnetFreeAddressHighThreshold, 
--                       serverSubnetFreeAddresses }
--     STATUS          mandatory
--     DESCRIPTION     
--             "DHCP Server MIB objects used in shared networks."
--     ::= { serverMIBGroups 8 }

serverNotifyObjectsGroup OBJECT IDENTIFIER
    ::= { serverMIBGroups 9 }

-- serverNotifyObjectsGroup OBJECT-GROUP
--     OBJECTS         { serverNotifyDuplicateIpAddress, 
--                       serverNotifyDuplicateMAC, 
--                       serverNotifyClientDuplicateIP }
--     STATUS          mandatory
--     DESCRIPTION     
--             "DHCP Server MIB objects used in notifications."
--     ::= { serverMIBGroups 9 }

serverNotificationsGroup OBJECT IDENTIFIER
    ::= { serverMIBGroups 10 }

-- serverNotificationsGroup NOTIFICATION-GROUP
--     NOTIFICATIONS   { serverFreeAddressLow, serverFreeAddressHigh, 
--                       serverServerStart, serverServerStop, 
--                       serverDuplicateAddress, serverAddressConflict }
--     STATUS          mandatory
--     DESCRIPTION     
--             "Notifications that are implemented by the DHCP Server agent."
--     ::= { serverMIBGroups 10 }

serverMIBCompliance OBJECT IDENTIFIER
    ::= { serverMIBCompliances 1 }

-- serverMIBCompliance MODULE-COMPLIANCE
--     STATUS          mandatory
--     DESCRIPTION     
--             "Describes the requirements for conformance to the DCHP Server 
--              MIB"

--     MODULE          -- -- this module

--         MANDATORY-GROUPS    { serverSystemGroup, bootpCountersGroup, 
--                       dhcpCountersGroup, serverConfigurationGroup, 
--                       serverClientsGroup }

--     ::= { serverMIBCompliances 1 }

END -- end of module DHCP-SERVER-MIB.
