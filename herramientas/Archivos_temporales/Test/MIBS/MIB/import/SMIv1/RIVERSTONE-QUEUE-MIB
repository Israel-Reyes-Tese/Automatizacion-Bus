--
-- This SMIv1 module has been generated by smidump 0.2-cvs. Do not edit.
--

RIVERSTONE-QUEUE-MIB DEFINITIONS ::= BEGIN

IMPORTS
    ifIndex
        FROM IF-MIB
    OBJECT-TYPE
        FROM RFC-1212
    Counter, Gauge
        FROM RFC1155-SMI
    riverstoneMibs
        FROM RIVERSTONE-SMI-MIB
    RsDiscardPolicy
        FROM RIVERSTONE-TC-MIB
    SnmpAdminString
        FROM SNMP-FRAMEWORK-MIB
    TimeStamp
        FROM SNMPv2-TC;

rsQueueMIB OBJECT IDENTIFIER
    ::= { riverstoneMibs 70 }

-- rsQueueMIB MODULE-IDENTITY
--     LAST-UPDATED    "200206120000Z"
--     ORGANIZATION    
--             "Riverstone Networks, Inc"
--     CONTACT-INFO    
--             "Riverstone Networks
--              Customer Service
--              
--              Postal:
--              Riverstone Networks, Inc
--              5200 Great America Parkway
--              Santa Clara CA 95054 USA
--              
--              PHONE:+1 408.878.6500
--              EMAIL: nms-eng@riverstonenet.com
--              WEB: http://www.riverstonenet.com"
--     DESCRIPTION     
--             "This MIB module represents information on each of the queues
--              for each port."
--     REVISION        "200206120000Z"
--     DESCRIPTION     
--             "Initial version."
--     ::= { riverstoneMibs 70 }


IndexInteger ::=
    Gauge (1..4294967295)

-- IndexInteger ::= TEXTUAL-CONVENTION
--     DISPLAY-HINT    "d"
--     STATUS          mandatory
--     DESCRIPTION     
--             "An integer which may be used as a table index."
--     SYNTAX          Gauge (1..4294967295)

rsQueueMIBObjects OBJECT IDENTIFIER
    ::= { rsQueueMIB 1 }

rsQueuePropertiesTable OBJECT-TYPE
    SYNTAX          SEQUENCE OF RsQueuePropertiesEntry
    ACCESS          not-accessible
    STATUS          mandatory
    DESCRIPTION     
            "This table contains descriptions of different queues. It is 
             used as a reference table by rsQueueStatsTable."
    ::= { rsQueueMIBObjects 1 }

rsQueuePropertiesEntry OBJECT-TYPE
    SYNTAX          RsQueuePropertiesEntry
    ACCESS          not-accessible
    STATUS          mandatory
    DESCRIPTION     
            "This entry represents a queue and its properties. It is 
             indexed by a natural number."
    INDEX           { rsQueueId }
    ::= { rsQueuePropertiesTable 1 }

RsQueuePropertiesEntry ::=
    SEQUENCE {
        rsQueueId                       IndexInteger,
        rsQueueName                     SnmpAdminString,
        rsQueueDescr                    SnmpAdminString,
        rsQueueDiscardPolicy            RsDiscardPolicy,
        rsQueueMaxCapacity              Gauge
    }

rsQueueId OBJECT-TYPE
    SYNTAX          IndexInteger
    ACCESS          not-accessible
    STATUS          mandatory
    DESCRIPTION     
            "An index that enumerates the number of queue entries."
    ::= { rsQueuePropertiesEntry 1 }

rsQueueName OBJECT-TYPE
    SYNTAX          SnmpAdminString
    ACCESS          read-only
    STATUS          mandatory
    DESCRIPTION     
            "The name of the queue. For example, on the RS platform, 
             the four queue names are control, high, medium, and low."
    ::= { rsQueuePropertiesEntry 2 }

rsQueueDescr OBJECT-TYPE
    SYNTAX          SnmpAdminString
    ACCESS          read-only
    STATUS          mandatory
    DESCRIPTION     
            "A more detailed description of the functionality of the queue."
    ::= { rsQueuePropertiesEntry 3 }

rsQueueDiscardPolicy OBJECT-TYPE
    SYNTAX          RsDiscardPolicy
    ACCESS          read-only
    STATUS          mandatory
    DESCRIPTION     
            "The type of policy used by the queue to drop a frame."
    ::= { rsQueuePropertiesEntry 4 }

rsQueueMaxCapacity OBJECT-TYPE
    SYNTAX          Gauge
    ACCESS          read-only
    STATUS          mandatory
    DESCRIPTION     
            "The max number of frames the queue can contain."
    ::= { rsQueuePropertiesEntry 6 }

rsQueueStatsTable OBJECT-TYPE
    SYNTAX          SEQUENCE OF RsQueueStatsEntry
    ACCESS          not-accessible
    STATUS          mandatory
    DESCRIPTION     
            "This table contains stats per queue for each physical interface."
    ::= { rsQueueMIBObjects 2 }

rsQueueStatsEntry OBJECT-TYPE
    SYNTAX          RsQueueStatsEntry
    ACCESS          not-accessible
    STATUS          mandatory
    DESCRIPTION     
            "The stats per queue for each physical interface."
    INDEX           { ifIndex, rsQueueId }
    ::= { rsQueueStatsTable 1 }

RsQueueStatsEntry ::=
    SEQUENCE {
        rsQueueStatsLastCapChange       TimeStamp,
        rsQueueStatsValid               OCTET STRING,
        rsQueueBytes                    Counter,
        rsQueueFrames                   Counter,
        rsQueueDiscards                 Counter
--         rsQueueHCBytes                  Counter64,
--         rsQueueHCFrames                 Counter64
    }

rsQueueStatsLastCapChange OBJECT-TYPE
    SYNTAX          TimeStamp
    ACCESS          read-only
    STATUS          mandatory
    DESCRIPTION     
            "The value of sysUpTime at the time when the port capability
             changed. As a result of this change, the application need to 
             restart its counter collection. For example, the card may have 
             been hotswapped out and replaced by another card."
    ::= { rsQueueStatsEntry 1 }

rsQueueStatsValid OBJECT-TYPE
    SYNTAX          OCTET STRING
--                       { validBytes(0), validFrames(1), 
--                         validDiscards(2), validHCBytes(3), 
--                         validHCFrames(4) }
    ACCESS          read-only
    STATUS          mandatory
    DESCRIPTION     
            "The current state of each counter in this table. Each bit 
             indicate the validity of a counter. Some queues may not support
             every counter in the table."
    ::= { rsQueueStatsEntry 2 }

rsQueueBytes OBJECT-TYPE
    SYNTAX          Counter
    ACCESS          read-only
    STATUS          mandatory
    DESCRIPTION     
            "The number of bytes that have passed through this priority 
             queue on this port."
    ::= { rsQueueStatsEntry 101 }

rsQueueFrames OBJECT-TYPE
    SYNTAX          Counter
    ACCESS          read-only
    STATUS          mandatory
    DESCRIPTION     
            "The number of frames that have passed through this priority 
             queue on this port."
    ::= { rsQueueStatsEntry 102 }

rsQueueDiscards OBJECT-TYPE
    SYNTAX          Counter
    ACCESS          read-only
    STATUS          mandatory
    DESCRIPTION     
            "The number of frames into this queue that were discarded
             because the queue was full."
    ::= { rsQueueStatsEntry 103 }

-- rsQueueHCBytes OBJECT-TYPE
--     SYNTAX          Counter64
--     ACCESS          read-only
--     STATUS          mandatory
--     DESCRIPTION     
--             "The number of bytes stored in a 64 bit counter that have
--              passed through this priority queue on this port."
--     ::= { rsQueueStatsEntry 201 }

-- rsQueueHCFrames OBJECT-TYPE
--     SYNTAX          Counter64
--     ACCESS          read-only
--     STATUS          mandatory
--     DESCRIPTION     
--             "The number of frames stored in a 64 bit counter that have 
--              passed through this priority queue on this port."
--     ::= { rsQueueStatsEntry 202 }

rsQueueConformance OBJECT IDENTIFIER
    ::= { rsQueueMIB 2 }

rsQueueCompliances OBJECT IDENTIFIER
    ::= { rsQueueConformance 1 }

rsQueueGroups OBJECT IDENTIFIER
    ::= { rsQueueConformance 2 }

rsQueuePropertiesGroup OBJECT IDENTIFIER
    ::= { rsQueueGroups 1 }

-- rsQueuePropertiesGroup OBJECT-GROUP
--     OBJECTS         { rsQueueName, rsQueueDescr, rsQueueDiscardPolicy, 
--                       rsQueueMaxCapacity }
--     STATUS          mandatory
--     DESCRIPTION     
--             "The collection of objects used to represent properties of a queue."
--     ::= { rsQueueGroups 1 }

rsQueueStatsGroup OBJECT IDENTIFIER
    ::= { rsQueueGroups 2 }

-- rsQueueStatsGroup OBJECT-GROUP
--     OBJECTS         { rsQueueStatsLastCapChange, rsQueueStatsValid, 
--                       rsQueueBytes, rsQueueFrames, rsQueueDiscards, 
--                       rsQueueHCBytes, rsQueueHCFrames }
--     STATUS          mandatory
--     DESCRIPTION     
--             "The collection of objects used to represent the queue stats."
--     ::= { rsQueueGroups 2 }

rsQueueCompliance OBJECT IDENTIFIER
    ::= { rsQueueCompliances 1 }

-- rsQueueCompliance MODULE-COMPLIANCE
--     STATUS          mandatory
--     DESCRIPTION     
--             "The compliance statement for RIVERSTONE-STATS-MIB."

--     MODULE          -- -- this module

--         MANDATORY-GROUPS    { rsQueuePropertiesGroup, 
--                       rsQueueStatsGroup }

--     ::= { rsQueueCompliances 1 }

END -- end of module RIVERSTONE-QUEUE-MIB.
