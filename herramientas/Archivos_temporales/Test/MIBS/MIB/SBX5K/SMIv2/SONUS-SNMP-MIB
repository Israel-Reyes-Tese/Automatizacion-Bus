--
-- This SMIv2 module has been generated by smidump 0.2-cvs. Do not edit.
--

SONUS-SNMP-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusSnmpMIB MODULE-IDENTITY
    LAST-UPDATED    "201212310000Z"
    ORGANIZATION    
            "Ribbon Communications, Inc."
    CONTACT-INFO    
            "Customer Support        
             Ribbon Communications, Inc. 
             4 Technology Park Drive 
             Westford, MA 01886      
             USA                     
                                     
             Tel: 978-614-8100       
             Fax: 978-614-8609"
    DESCRIPTION     
            "The MIB Module for SNMP configuration and status."
    REVISION        "201212310000Z"
    DESCRIPTION     
            "Auto generated MIB."
    ::= { sonusCommonSoftwarePlatformServicesMIBs 19 }


UnsignedShort ::= TEXTUAL-CONVENTION
    DISPLAY-HINT    "d"
    STATUS          current
    DESCRIPTION     
            "xs:unsignedShort"
    SYNTAX          Unsigned32 (0..65535)

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

HexList ::= TEXTUAL-CONVENTION
    DISPLAY-HINT    "1x:"
    STATUS          current
    DESCRIPTION     
            "confd:hexList"
    SYNTAX          OCTET STRING

SnmpCommunityNameType ::= TEXTUAL-CONVENTION
    DISPLAY-HINT    "1t"
    STATUS          current
    DESCRIPTION     
            ""
    SYNTAX          OCTET STRING

SonusSnmpVersionType ::= TEXTUAL-CONVENTION
    STATUS          current
    DESCRIPTION     
            "
             This data type lists SNMP version supported.
             "
    SYNTAX          INTEGER { v1v2c(1), v3only(2) }

SnmpCommunityIndexType ::= TEXTUAL-CONVENTION
    DISPLAY-HINT    "1t"
    STATUS          current
    DESCRIPTION     
            ""
    SYNTAX          OCTET STRING (SIZE(1..32))

SonusSnmpAuthProtocolType ::= TEXTUAL-CONVENTION
    STATUS          current
    DESCRIPTION     
            "
             This data type lists SNMP authentication protocols supported.
             "
    SYNTAX          INTEGER { hmacmd5(1), hmacsha(2) }

SonusSnmpGroupType ::= TEXTUAL-CONVENTION
    STATUS          current
    DESCRIPTION     
            "
             This data type lists SNMP SNMP-VIEW-BASED-ACM-MIB vacmGroupName supported.
             "
    SYNTAX          INTEGER { admin(1), operator(2), guest(3) }

SonusSnmpSecurityLevelType ::= TEXTUAL-CONVENTION
    STATUS          current
    DESCRIPTION     
            "
             This data type lists SNMP security levels.
             "
    SYNTAX          INTEGER { noAuthNoPriv(1), authNoPriv(2), 
                        authPriv(3) }

SonusSnmpPrivProtocolType ::= TEXTUAL-CONVENTION
    STATUS          current
    DESCRIPTION     
            "
             This data type lists SNMP privacy protocols supported.
             "
    SYNTAX          INTEGER { des(1), aes128(2) }

SonusSnmpTrapTypeType ::= TEXTUAL-CONVENTION
    STATUS          current
    DESCRIPTION     
            ""
    SYNTAX          INTEGER { v1(1), v2(2), inform(3), v3(4) }

SonusSnmpName ::= TEXTUAL-CONVENTION
    DISPLAY-HINT    "1t"
    STATUS          current
    DESCRIPTION     
            "
             This data type is used to model textual information taken
             from the NVT ASCII character set.  The SonusSnmpName type is used
             to label Sonus Trap Target Named objects.
             "
    SYNTAX          OCTET STRING (SIZE(0..32))

sonusSnmp OBJECT IDENTIFIER
    ::= { sonusSnmpMIB 1 }

sonusSnmpCommunity OBJECT IDENTIFIER
    ::= { sonusSnmp 1 }

sonusSnmpCommunityEngineId OBJECT-TYPE
    SYNTAX          HexList (SIZE(5..32))
    MAX-ACCESS      read-only
    STATUS          current
    DESCRIPTION     
            "
             The SNMP community context engine ID.
             "
    ::= { sonusSnmpCommunity 1 }

sonusSnmpTrapTargetTable OBJECT-TYPE
    SYNTAX          SEQUENCE OF SonusSnmpTrapTargetEntry
    MAX-ACCESS      not-accessible
    STATUS          current
    DESCRIPTION     
            ""
    ::= { sonusSnmp 2 }

sonusSnmpTrapTargetEntry OBJECT-TYPE
    SYNTAX          SonusSnmpTrapTargetEntry
    MAX-ACCESS      not-accessible
    STATUS          current
    DESCRIPTION     
            ""
    INDEX           { sonusSnmpTrapTargetName }
    ::= { sonusSnmpTrapTargetTable 1 }

SonusSnmpTrapTargetEntry ::=
    SEQUENCE {
        sonusSnmpTrapTargetName         SonusSnmpName,
        sonusSnmpTrapTargetIpAddress    InetAddressIP,
        sonusSnmpTrapTargetPort         UnsignedShort,
        sonusSnmpTrapTargetTrapType     SonusSnmpTrapTypeType,
        sonusSnmpTrapTargetState        INTEGER,
        sonusSnmpTrapTargetRowstatus    RowStatus
    }

sonusSnmpTrapTargetName OBJECT-TYPE
    SYNTAX          SonusSnmpName
    MAX-ACCESS      not-accessible
    STATUS          current
    DESCRIPTION     
            "
             The name of the trap target.
             "
    ::= { sonusSnmpTrapTargetEntry 1 }

sonusSnmpTrapTargetIpAddress OBJECT-TYPE
    SYNTAX          InetAddressIP
    MAX-ACCESS      read-create
    STATUS          current
    DESCRIPTION     
            "
             The IP address of this trap target.
             "
    ::= { sonusSnmpTrapTargetEntry 2 }

sonusSnmpTrapTargetPort OBJECT-TYPE
    SYNTAX          UnsignedShort (1..65535)
    MAX-ACCESS      read-create
    STATUS          current
    DESCRIPTION     
            "
             The port number for SNMP traps.
             "
    ::= { sonusSnmpTrapTargetEntry 3 }

sonusSnmpTrapTargetTrapType OBJECT-TYPE
    SYNTAX          SonusSnmpTrapTypeType
    MAX-ACCESS      read-create
    STATUS          current
    DESCRIPTION     
            "
             The type of the trap sent to the target.
             "
    DEFVAL          { v2 }
    ::= { sonusSnmpTrapTargetEntry 4 }

sonusSnmpTrapTargetState OBJECT-TYPE
    SYNTAX          INTEGER { disabled(1), enabled(2) }
    MAX-ACCESS      read-create
    STATUS          current
    DESCRIPTION     
            "
             The configured state of the trap target entry.
             "
    ::= { sonusSnmpTrapTargetEntry 5 }

sonusSnmpTrapTargetRowstatus OBJECT-TYPE
    SYNTAX          RowStatus
    MAX-ACCESS      read-create
    STATUS          current
    DESCRIPTION     
            ""
    ::= { sonusSnmpTrapTargetEntry 6 }

END -- end of module SONUS-SNMP-MIB.
