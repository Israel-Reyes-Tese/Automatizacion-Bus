--
-- This SMIv2 module has been generated by smidump 0.2-cvs. Do not edit.
--

Gr1343Core-MIB DEFINITIONS ::= BEGIN

IMPORTS
    hrDeviceIndex
        FROM HOST-RESOURCES-MIB
    InetAddress, InetAddressType
        FROM INET-ADDRESS-MIB
    Counter32, Gauge32, Integer32, IpAddress, OBJECT-TYPE, enterprises
        FROM SNMPv2-SMI;

DateAndTime ::=
    DisplayString (SIZE(11))

telcordia OBJECT IDENTIFIER
    ::= { enterprises 148 }

requirements OBJECT IDENTIFIER
    ::= { telcordia 1 }

gr1343Core OBJECT IDENTIFIER
    ::= { requirements 7 }

session OBJECT IDENTIFIER
    ::= { gr1343Core 1 }

sessionComp OBJECT IDENTIFIER
    ::= { session 1 }

sessionCompTable OBJECT-TYPE
    SYNTAX          SEQUENCE OF SessionCompEntry
    MAX-ACCESS      not-accessible
    STATUS          obsolete
    DESCRIPTION     
            "The (conceptual) table of components that communicate with the host."
    ::= { sessionComp 1 }

sessionCompEntry OBJECT-TYPE
    SYNTAX          SessionCompEntry
    MAX-ACCESS      not-accessible
    STATUS          obsolete
    DESCRIPTION     
            "The (conceptual) entry for one component that communicates with the host."
    INDEX           { sessionCompIndex }
    ::= { sessionCompTable 1 }

SessionCompEntry ::=
    SEQUENCE {
        sessionCompIndex                Integer32,
        sessionCompIdCode               DisplayString,
        sessionCompPrimAddr             IpAddress,
        sessionCompSecAddr              IpAddress,
        sessionCompEntryStatus          INTEGER
    }

sessionCompIndex OBJECT-TYPE
    SYNTAX          Integer32 (1..2147483647)
    MAX-ACCESS      read-only
    STATUS          obsolete
    DESCRIPTION     
            "A unique value for each component with an associated component
             identification code."
    ::= { sessionCompEntry 1 }

sessionCompIdCode OBJECT-TYPE
    SYNTAX          DisplayString (SIZE(6))
    MAX-ACCESS      read-write
    STATUS          obsolete
    DESCRIPTION     
            "The component identification code (e.g., DPMS #0123 = 030123)."
    ::= { sessionCompEntry 2 }

sessionCompPrimAddr OBJECT-TYPE
    SYNTAX          IpAddress
    MAX-ACCESS      read-write
    STATUS          obsolete
    DESCRIPTION     
            "The primary IP address for the component corresponding to the component ID
             code."
    ::= { sessionCompEntry 3 }

sessionCompSecAddr OBJECT-TYPE
    SYNTAX          IpAddress
    MAX-ACCESS      read-write
    STATUS          obsolete
    DESCRIPTION     
            "The secondary IP address for the component corresponding to the component
             ID code."
    ::= { sessionCompEntry 4 }

sessionCompEntryStatus OBJECT-TYPE
    SYNTAX          INTEGER { valid(1), invalid(2) }
    MAX-ACCESS      read-write
    STATUS          obsolete
    DESCRIPTION     
            "This object indicates if a table entry is valid or invalid. The value of this object
             is set to 1 when the entry is active and is set to 2 when the entry is inactive."
    ::= { sessionCompEntry 5 }

sessionCompExtTable OBJECT-TYPE
    SYNTAX          SEQUENCE OF SessionCompExtEntry
    MAX-ACCESS      not-accessible
    STATUS          current
    DESCRIPTION     
            "The (conceptual) table of components that communicate with the host."
    ::= { sessionComp 2 }

sessionCompExtEntry OBJECT-TYPE
    SYNTAX          SessionCompExtEntry
    MAX-ACCESS      not-accessible
    STATUS          current
    DESCRIPTION     
            "The (conceptual) entry for one component that communicates with the hos
             t."
    INDEX           { sessionCompExtIndex }
    ::= { sessionCompExtTable 1 }

SessionCompExtEntry ::=
    SEQUENCE {
        sessionCompExtIndex             Integer32,
        sessionCompExtIdCode            DisplayString,
        sessionCompExtPrimAddrType      InetAddressType,
        sessionCompExtPrimAddr          InetAddress,
        sessionCompExtSecAddrType       InetAddressType,
        sessionCompExtSecAddr           InetAddress,
        sessionCompExtEntryStatus       INTEGER
    }

sessionCompExtIndex OBJECT-TYPE
    SYNTAX          Integer32 (1..2147483647)
    MAX-ACCESS      read-only
    STATUS          current
    DESCRIPTION     
            "A unique value for each component with an associated component
             identification code."
    ::= { sessionCompExtEntry 1 }

sessionCompExtIdCode OBJECT-TYPE
    SYNTAX          DisplayString (SIZE(6))
    MAX-ACCESS      read-write
    STATUS          current
    DESCRIPTION     
            "The component identification code (e.g., DPMS #0123 = 030123)."
    ::= { sessionCompExtEntry 2 }

sessionCompExtPrimAddrType OBJECT-TYPE
    SYNTAX          InetAddressType
    MAX-ACCESS      read-write
    STATUS          current
    DESCRIPTION     
            "The primary IP address type for the component corresponding to the comp
             onent ID
             code."
    ::= { sessionCompExtEntry 3 }

sessionCompExtPrimAddr OBJECT-TYPE
    SYNTAX          InetAddress
    MAX-ACCESS      read-write
    STATUS          current
    DESCRIPTION     
            "The primary IP address for the component corresponding to the component
             ID
                    code."
    ::= { sessionCompExtEntry 4 }

sessionCompExtSecAddrType OBJECT-TYPE
    SYNTAX          InetAddressType
    MAX-ACCESS      read-write
    STATUS          current
    DESCRIPTION     
            "The secondary IP address type for the component corresponding to the co
             mponent
             ID code."
    ::= { sessionCompExtEntry 5 }

sessionCompExtSecAddr OBJECT-TYPE
    SYNTAX          InetAddress
    MAX-ACCESS      read-write
    STATUS          current
    DESCRIPTION     
            "The secondary IP address for the component corresponding to the compone
             nt
             ID code."
    ::= { sessionCompExtEntry 6 }

sessionCompExtEntryStatus OBJECT-TYPE
    SYNTAX          INTEGER { valid(1), invalid(2) }
    MAX-ACCESS      read-write
    STATUS          current
    DESCRIPTION     
            "This object indicates if a table entry is valid or invalid. The value o
             f this object
             is set to 1 when the entry is active and is set to 2 when the entry is
             inactive."
    ::= { sessionCompExtEntry 7 }

sessionFtp OBJECT IDENTIFIER
    ::= { session 2 }

sessionFtpControlTimeout OBJECT-TYPE
    SYNTAX          Integer32 (0..2147483647)
    MAX-ACCESS      read-write
    STATUS          current
    DESCRIPTION     
            "The maximum amount of time (in seconds) allowed for a period when no
             messages are exchanged between two components over a control connection
             during an FTP session. If a silent period exceeds this time period, other than
             during a file transfer, the corresponding FTP session is forcefully ended. The
             default value is 30."
    ::= { sessionFtp 1 }

sessionFtpDataTimeout OBJECT-TYPE
    SYNTAX          Integer32 (0..2147483647)
    MAX-ACCESS      read-write
    STATUS          current
    DESCRIPTION     
            "The maximum amount of time (in seconds) allowed for a period when no
             messages are exchanged between two components over a data connection
             during an FTP session. If a silent period exceeds this time period, the
             corresponding FTP session is forcefully ended. The default value is 30."
    ::= { sessionFtp 2 }

sessionFtpMaxConsecRetries OBJECT-TYPE
    SYNTAX          Integer32 (0..2147483647)
    MAX-ACCESS      read-write
    STATUS          current
    DESCRIPTION     
            "The maximum number of consecutive times the initiator of an FTP session (i.e.,
             the FTP User) should attempt to complete a failed session before ceasing to do
             so, in which case the problem is assumed to be permanent and must be fixed
             before another session is attempted. The default value is 3."
    ::= { sessionFtp 3 }

sessionFtpRetryWaitTime OBJECT-TYPE
    SYNTAX          Integer32 (0..2147483647)
    MAX-ACCESS      read-write
    STATUS          current
    DESCRIPTION     
            "The amount of time (in minutes) the initiator of an FTP session should wait
             after a failed session before requesting a session again. The default value is 1."
    ::= { sessionFtp 4 }

sessionFtpTable OBJECT-TYPE
    SYNTAX          SEQUENCE OF SessionFtpEntry
    MAX-ACCESS      not-accessible
    STATUS          current
    DESCRIPTION     
            "The (conceptual) table of FTP sessions with other communication
             components."
    ::= { sessionFtp 5 }

sessionFtpEntry OBJECT-TYPE
    SYNTAX          SessionFtpEntry
    MAX-ACCESS      not-accessible
    STATUS          current
    DESCRIPTION     
            "The (conceptual) entry of FTP sessions for one component that communicates
             with the local host. The sessionCompIndex represents the entry in the
             sessionCompTable that corresponds to the sessionFtpEntry."
    INDEX           { sessionCompIndex }
    ::= { sessionFtpTable 1 }

SessionFtpEntry ::=
    SEQUENCE {
        sessionFtpServInvocLoc          Counter32,
        sessionFtpServInvocFailLoc      Counter32,
        sessionFtpAuthenLoc             Counter32,
        sessionFtpAuthenFailLoc         Counter32,
        sessionFtpAuthenRem             Counter32,
        sessionFtpAuthenFailRem         Counter32,
        sessionFtpSessions              Counter32,
        sessionFtpLastSession           DateAndTime,
        sessionFtpLastSuccSession       DateAndTime,
        sessionFtpSessionFail           Counter32,
        sessionFtpFileTransferFail      Counter32,
        sessionFtpTimeouts              Counter32,
        sessionFtpLocAborts             Counter32,
        sessionFtpRemAborts             Counter32,
        sessionFtpTestFileExchange      Integer32,
        sessionFtpTestFileErrors        Counter32,
        sessionFtpEntryStatus           INTEGER,
        sessionFtpMSessionsFail         Counter32
    }

sessionFtpServInvocLoc OBJECT-TYPE
    SYNTAX          Counter32
    MAX-ACCESS      read-only
    STATUS          current
    DESCRIPTION     
            "The number of FTP service invocations made by the local host to the
             component corresponding to the sessionCompIndex."
    ::= { sessionFtpEntry 1 }

sessionFtpServInvocFailLoc OBJECT-TYPE
    SYNTAX          Counter32
    MAX-ACCESS      read-only
    STATUS          current
    DESCRIPTION     
            "The number of times an FTP service invocation made by the local host to the
             component corresponding to the sessionCompIndex has failed."
    ::= { sessionFtpEntry 2 }

sessionFtpAuthenLoc OBJECT-TYPE
    SYNTAX          Counter32
    MAX-ACCESS      read-only
    STATUS          current
    DESCRIPTION     
            "The number of FTP authentication attempts made by the local host to the
             component corresponding to the sessionCompIndex."
    ::= { sessionFtpEntry 3 }

sessionFtpAuthenFailLoc OBJECT-TYPE
    SYNTAX          Counter32
    MAX-ACCESS      read-only
    STATUS          current
    DESCRIPTION     
            "The number of times an FTP authentication attempt made by the local host
             to the component corresponding to the sessionCompIndex has failed."
    ::= { sessionFtpEntry 4 }

sessionFtpAuthenRem OBJECT-TYPE
    SYNTAX          Counter32
    MAX-ACCESS      read-only
    STATUS          current
    DESCRIPTION     
            "The number of FTP authentication attempts made by the component
             corresponding to the sessionCompIndex to the local host."
    ::= { sessionFtpEntry 5 }

sessionFtpAuthenFailRem OBJECT-TYPE
    SYNTAX          Counter32
    MAX-ACCESS      read-only
    STATUS          current
    DESCRIPTION     
            "The number of times an FTP authentication attempt made by the component
             corresponding to the sessionCompIndex to the local host has failed."
    ::= { sessionFtpEntry 6 }

sessionFtpSessions OBJECT-TYPE
    SYNTAX          Counter32
    MAX-ACCESS      read-only
    STATUS          current
    DESCRIPTION     
            "The number of FTP sessions with the component corresponding to the
             sessionCompIndex."
    ::= { sessionFtpEntry 7 }

sessionFtpLastSession OBJECT-TYPE
    SYNTAX          DateAndTime
    MAX-ACCESS      read-only
    STATUS          current
    DESCRIPTION     
            "The date and time when the last FTP session with the component
             corresponding to the sessionCompIndex ended."
    ::= { sessionFtpEntry 8 }

sessionFtpLastSuccSession OBJECT-TYPE
    SYNTAX          DateAndTime
    MAX-ACCESS      read-only
    STATUS          current
    DESCRIPTION     
            "The date and time when the last successful FTP session (i.e., the session
             terminated normally) with the component corresponding to the
             sessionCompIndex ended."
    ::= { sessionFtpEntry 9 }

sessionFtpSessionFail OBJECT-TYPE
    SYNTAX          Counter32
    MAX-ACCESS      read-only
    STATUS          current
    DESCRIPTION     
            "The number of times an FTP session with the component corresponding to the
             sessionCompIndex has ended abnormally (e.g., as a result of time-outs, aborts,
             or failures)."
    ::= { sessionFtpEntry 10 }

sessionFtpFileTransferFail OBJECT-TYPE
    SYNTAX          Counter32
    MAX-ACCESS      read-only
    STATUS          current
    DESCRIPTION     
            "The number of times an established FTP session with the component
             corresponding to the sessionCompIndex has been interrupted while the file was
             being transferred."
    ::= { sessionFtpEntry 11 }

sessionFtpTimeouts OBJECT-TYPE
    SYNTAX          Counter32
    MAX-ACCESS      read-only
    STATUS          current
    DESCRIPTION     
            "The number of times an FTP session with the component corresponding to the
             sessionCompIndex has been ended due to an FTP timeout."
    ::= { sessionFtpEntry 12 }

sessionFtpLocAborts OBJECT-TYPE
    SYNTAX          Counter32
    MAX-ACCESS      read-only
    STATUS          current
    DESCRIPTION     
            "The number of times an FTP session with the component corresponding to the
             sessionCompIndex has been ended due to a local abort."
    ::= { sessionFtpEntry 13 }

sessionFtpRemAborts OBJECT-TYPE
    SYNTAX          Counter32
    MAX-ACCESS      read-only
    STATUS          current
    DESCRIPTION     
            "The number of times an FTP session with the component corresponding to the
             sessionCompIndex has been ended due to a remote abort."
    ::= { sessionFtpEntry 14 }

sessionFtpTestFileExchange OBJECT-TYPE
    SYNTAX          Integer32 (0..2147483647)
    MAX-ACCESS      read-write
    STATUS          current
    DESCRIPTION     
            "The number of times a test file must be sent to the component corresponding
             to the sessionCompIndex during a test file exchange procedure. The default
             value is 1."
    ::= { sessionFtpEntry 15 }

sessionFtpTestFileErrors OBJECT-TYPE
    SYNTAX          Counter32
    MAX-ACCESS      read-only
    STATUS          current
    DESCRIPTION     
            "The number of differences detected between sent and received test files during
             test file exchange procedures with the component corresponding to the
             sessionCompIndex."
    ::= { sessionFtpEntry 16 }

sessionFtpEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { sessionFtpEntry 17 }

sessionFtpMSessionsFail OBJECT-TYPE
    SYNTAX          Counter32
    MAX-ACCESS      read-only
    STATUS          current
    DESCRIPTION     
            "The number of times an FTP session with the component corresponding to the
             sessionCompIndex has ended abnormally (e.g., as a result of timeouts, aborts,
             or failures) M consecutive times (M = sessionFtpMaxConsecRetries)."
    ::= { sessionFtpEntry 18 }

sessionRda OBJECT IDENTIFIER
    ::= { session 3 }

sessionRdaTimeout OBJECT-TYPE
    SYNTAX          Integer32 (0..2147483647)
    MAX-ACCESS      read-write
    STATUS          current
    DESCRIPTION     
            "The maximum amount of time (in seconds) allowed for a period when no
             messages are exchanged between two components during an RDA session (i.e.,
             RDA dialogue). If a silent period exceeds this time period, other than during a
             query response, the corresponding RDA dialogue is forcefully ended. The
             default value is 30."
    ::= { sessionRda 1 }

sessionRdaMaxConsecFail OBJECT-TYPE
    SYNTAX          Integer32 (0..2147483647)
    MAX-ACCESS      read-write
    STATUS          current
    DESCRIPTION     
            "The maximum number of consecutive times an RDA session can end
             abnormally. Hence, the RDA Server (i.e., DPMS) stops accepting RDA session
             requests, in which case the problem is assumed to be permanent and must be
             fixed before another session is allowed. The default value is 3."
    ::= { sessionRda 2 }

sessionRdaTable OBJECT-TYPE
    SYNTAX          SEQUENCE OF SessionRdaEntry
    MAX-ACCESS      not-accessible
    STATUS          current
    DESCRIPTION     
            "The (conceptual) table of RDA sessions with other communication
             components."
    ::= { sessionRda 3 }

sessionRdaEntry OBJECT-TYPE
    SYNTAX          SessionRdaEntry
    MAX-ACCESS      not-accessible
    STATUS          current
    DESCRIPTION     
            "The (conceptual) entry of RDA sessions for one component that communicates
             with the local host. The sessionCompIndex represents the entry in the
             sessionCompTable that corresponds to the sessionRdaEntry."
    INDEX           { sessionCompIndex }
    ::= { sessionRdaTable 1 }

SessionRdaEntry ::=
    SEQUENCE {
        sessionRdaAuthen                Counter32,
        sessionRdaAuthenFail            Counter32,
        sessionRdaSessions              Counter32,
        sessionRdaLastSession           DateAndTime,
        sessionRdaLastSuccSession       DateAndTime,
        sessionRdaSqlQueries            Counter32,
        sessionRdaResponseBytes         Counter32,
        sessionRdaSessionFail           Counter32,
        sessionRdaTimeouts              Counter32,
        sessionRdaEntryStatus           INTEGER
    }

sessionRdaAuthen OBJECT-TYPE
    SYNTAX          Counter32
    MAX-ACCESS      read-only
    STATUS          current
    DESCRIPTION     
            "The number of RDA authentication attempts made by the component
             corresponding to the sessionCompIndex to the local host."
    ::= { sessionRdaEntry 1 }

sessionRdaAuthenFail OBJECT-TYPE
    SYNTAX          Counter32
    MAX-ACCESS      read-only
    STATUS          current
    DESCRIPTION     
            "The number of times an RDA authentication attempt made by the component
             corresponding to the sessionCompIndex to the local host has failed."
    ::= { sessionRdaEntry 2 }

sessionRdaSessions OBJECT-TYPE
    SYNTAX          Counter32
    MAX-ACCESS      read-only
    STATUS          current
    DESCRIPTION     
            "The number of RDA sessions with the component corresponding to the
             sessionCompIndex."
    ::= { sessionRdaEntry 3 }

sessionRdaLastSession OBJECT-TYPE
    SYNTAX          DateAndTime
    MAX-ACCESS      read-only
    STATUS          current
    DESCRIPTION     
            "The date and time when the last RDA session with the component
             corresponding to the sessionCompIndex ended."
    ::= { sessionRdaEntry 4 }

sessionRdaLastSuccSession OBJECT-TYPE
    SYNTAX          DateAndTime
    MAX-ACCESS      read-only
    STATUS          current
    DESCRIPTION     
            "The date and time when the last successful RDA session (i.e., the session
             terminated normally) with the component corresponding to the
             sessionCompIndex ended."
    ::= { sessionRdaEntry 5 }

sessionRdaSqlQueries OBJECT-TYPE
    SYNTAX          Counter32
    MAX-ACCESS      read-only
    STATUS          current
    DESCRIPTION     
            "The number of SQL queries sent to the local host by the component
             corresponding to the sessionCompIndex."
    ::= { sessionRdaEntry 6 }

sessionRdaResponseBytes OBJECT-TYPE
    SYNTAX          Counter32
    MAX-ACCESS      read-only
    STATUS          current
    DESCRIPTION     
            "The number of bytes sent in response to SQL queries received from the
             component corresponding to the sessionCompIndex."
    ::= { sessionRdaEntry 7 }

sessionRdaSessionFail OBJECT-TYPE
    SYNTAX          Counter32
    MAX-ACCESS      read-only
    STATUS          current
    DESCRIPTION     
            "The number of times an RDA session with the component corresponding to the
             sessionCompIndex has ended abnormally (e.g., as a result of time-outs, aborts,
             or failures)."
    ::= { sessionRdaEntry 8 }

sessionRdaTimeouts OBJECT-TYPE
    SYNTAX          Counter32
    MAX-ACCESS      read-only
    STATUS          current
    DESCRIPTION     
            "The number of times an RDA session with the component corresponding to the
             sessionCompIndex has been terminated due to an RDA timeout."
    ::= { sessionRdaEntry 9 }

sessionRdaEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { sessionRdaEntry 10 }

sessionTelnet OBJECT IDENTIFIER
    ::= { session 4 }

sessionTelnetTimeout OBJECT-TYPE
    SYNTAX          Integer32 (0..2147483647)
    MAX-ACCESS      read-write
    STATUS          current
    DESCRIPTION     
            "The maximum amount of time (in seconds) allowed for a period when no
             messages are exchanged between two components during an Telnet session
             (i.e., Telnet connection). If a silent period exceeds this time period, the
             corresponding Telnet session is forcefully ended. The default value is 600."
    ::= { sessionTelnet 1 }

sessionTelnetTable OBJECT-TYPE
    SYNTAX          SEQUENCE OF SessionTelnetEntry
    MAX-ACCESS      not-accessible
    STATUS          current
    DESCRIPTION     
            "The (conceptual) table of Telnet sessions with other communication
             components."
    ::= { sessionTelnet 2 }

sessionTelnetEntry OBJECT-TYPE
    SYNTAX          SessionTelnetEntry
    MAX-ACCESS      not-accessible
    STATUS          current
    DESCRIPTION     
            "The (conceptual) entry of Telnet sessions for one component that
             communicates with the local host. The sessionCompIndex represents the entry
             in the sessionCompTable that corresponds to the sessionTelnetEntry."
    INDEX           { sessionCompIndex }
    ::= { sessionTelnetTable 1 }

SessionTelnetEntry ::=
    SEQUENCE {
        sessionTelnetAuthenLoc          Counter32,
        sessionTelnetAuthenFailLoc      Counter32,
        sessionTelnetAuthenRem          Counter32,
        sessionTelnetAuthenFailRem      Counter32,
        sessionTelnetSessions           Counter32,
        sessionTelnetLastSession        DateAndTime,
        sessionTelnetLastSuccSession    DateAndTime,
        sessionTelnetSessionFail        Counter32,
        sessionTelnetTimeouts           Counter32,
        sessionTelnetEntryStatus        INTEGER
    }

sessionTelnetAuthenLoc OBJECT-TYPE
    SYNTAX          Counter32
    MAX-ACCESS      read-only
    STATUS          current
    DESCRIPTION     
            "The number of Telnet authentication attempts made by the local host to the
             component corresponding to the sessionCompIndex."
    ::= { sessionTelnetEntry 1 }

sessionTelnetAuthenFailLoc OBJECT-TYPE
    SYNTAX          Counter32
    MAX-ACCESS      read-only
    STATUS          current
    DESCRIPTION     
            "The number of times a Telnet authentication attempt made by the local host to
             the component corresponding to the sessionCompIndex has failed."
    ::= { sessionTelnetEntry 2 }

sessionTelnetAuthenRem OBJECT-TYPE
    SYNTAX          Counter32
    MAX-ACCESS      read-only
    STATUS          current
    DESCRIPTION     
            "The number of Telnet authentication attempts made by the component
             corresponding to the sessionCompIndex to the local host."
    ::= { sessionTelnetEntry 3 }

sessionTelnetAuthenFailRem OBJECT-TYPE
    SYNTAX          Counter32
    MAX-ACCESS      read-only
    STATUS          current
    DESCRIPTION     
            "The number of times a Telnet authentication attempt made by the component
             corresponding to the sessionCompIndex to the local host has failed."
    ::= { sessionTelnetEntry 4 }

sessionTelnetSessions OBJECT-TYPE
    SYNTAX          Counter32
    MAX-ACCESS      read-only
    STATUS          current
    DESCRIPTION     
            "The number of Telnet sessions with the component corresponding to the
             sessionCompIndex."
    ::= { sessionTelnetEntry 5 }

sessionTelnetLastSession OBJECT-TYPE
    SYNTAX          DateAndTime
    MAX-ACCESS      read-only
    STATUS          current
    DESCRIPTION     
            "The date and time when the last Telnet session with the component
             corresponding to the sessionCompIndex ended."
    ::= { sessionTelnetEntry 6 }

sessionTelnetLastSuccSession OBJECT-TYPE
    SYNTAX          DateAndTime
    MAX-ACCESS      read-only
    STATUS          current
    DESCRIPTION     
            "The date and time when the last successful Telnet session (i.e., the session
             terminated normally) with the component corresponding to the
             sessionCompIndex ended."
    ::= { sessionTelnetEntry 7 }

sessionTelnetSessionFail OBJECT-TYPE
    SYNTAX          Counter32
    MAX-ACCESS      read-only
    STATUS          current
    DESCRIPTION     
            "The number of times a Telnet session with the component corresponding to the
             sessionCompIndex has ended abnormally (e.g., as a result of time-outs, aborts,
             or failures)."
    ::= { sessionTelnetEntry 8 }

sessionTelnetTimeouts OBJECT-TYPE
    SYNTAX          Counter32
    MAX-ACCESS      read-only
    STATUS          current
    DESCRIPTION     
            "The number of times a Telnet session with the component corresponding to the
             sessionCompIndex has been terminated due to a Telnet timeout."
    ::= { sessionTelnetEntry 9 }

sessionTelnetEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { sessionTelnetEntry 10 }

sessionTftp OBJECT IDENTIFIER
    ::= { session 5 }

sessionTftpTable OBJECT-TYPE
    SYNTAX          SEQUENCE OF SessionTftpEntry
    MAX-ACCESS      not-accessible
    STATUS          current
    DESCRIPTION     
            "The (conceptual) table of TFTP sessions with other components."
    ::= { sessionTftp 1 }

sessionTftpEntry OBJECT-TYPE
    SYNTAX          SessionTftpEntry
    MAX-ACCESS      not-accessible
    STATUS          current
    DESCRIPTION     
            "The (conceptual) entry of TFTP sessions for one component that
             communicates with the local host. The sessionCompIndex represents the entry
             in the sessionCompTable that corresponds to the sessionTftpEntry."
    INDEX           { sessionCompIndex }
    ::= { sessionTftpTable 1 }

SessionTftpEntry ::=
    SEQUENCE {
        sessionTftpSessions             Counter32,
        sessionTftpLastSession          DateAndTime,
        sessionTftpLastSessionStatus    INTEGER,
        sessionTftpSessionFail          Counter32,
        sessionTftpFileTransferFail     Counter32,
        sessionTftpTimeouts             Counter32,
        sessionTftpLocAborts            Counter32,
        sessionTftpRemAborts            Counter32,
        sessionTftpEntryStatus          INTEGER
    }

sessionTftpSessions OBJECT-TYPE
    SYNTAX          Counter32
    MAX-ACCESS      read-only
    STATUS          current
    DESCRIPTION     
            "The cumulative number of TFTP sessions with the component corresponding
             to the sessionCompIndex."
    ::= { sessionTftpEntry 1 }

sessionTftpLastSession OBJECT-TYPE
    SYNTAX          DateAndTime
    MAX-ACCESS      read-only
    STATUS          current
    DESCRIPTION     
            "The date and time of the last TFTP session with the component corresponding
             to the sessionCompIndex."
    ::= { sessionTftpEntry 2 }

sessionTftpLastSessionStatus OBJECT-TYPE
    SYNTAX          INTEGER { ongoing(1), gracefullyreleased(2), 
                        failed(3), unknown(4) }
    MAX-ACCESS      read-only
    STATUS          current
    DESCRIPTION     
            "The status of the last TFTP session with the component corresponding to the
             sessionCompIndex."
    ::= { sessionTftpEntry 3 }

sessionTftpSessionFail OBJECT-TYPE
    SYNTAX          Counter32
    MAX-ACCESS      read-only
    STATUS          current
    DESCRIPTION     
            "The number of times a TFTP session with the component corresponding to the
             sessionCompIndex has ended abnormally (e.g., as a result of timeouts, aborts,
             or failures)."
    ::= { sessionTftpEntry 4 }

sessionTftpFileTransferFail OBJECT-TYPE
    SYNTAX          Counter32
    MAX-ACCESS      read-only
    STATUS          current
    DESCRIPTION     
            "The number of times an established TFTP session with the component
             corresponding to the sessionCompIndex has been interrupted while the file was
             being transferred."
    ::= { sessionTftpEntry 5 }

sessionTftpTimeouts OBJECT-TYPE
    SYNTAX          Counter32
    MAX-ACCESS      read-only
    STATUS          current
    DESCRIPTION     
            "The number of times an TFTP session with the component corresponding to
             the sessionCompIndex has been ended due to a TFTP timeout."
    ::= { sessionTftpEntry 6 }

sessionTftpLocAborts OBJECT-TYPE
    SYNTAX          Counter32
    MAX-ACCESS      read-only
    STATUS          current
    DESCRIPTION     
            "The number of times an TFTP session with the component corresponding to
             the sessionCompIndex has been ended due to a local abort."
    ::= { sessionTftpEntry 7 }

sessionTftpRemAborts OBJECT-TYPE
    SYNTAX          Counter32
    MAX-ACCESS      read-only
    STATUS          current
    DESCRIPTION     
            "The number of times an TFTP session with the component corresponding to
             the sessionCompIndex has been ended due to a remote abort."
    ::= { sessionTftpEntry 8 }

sessionTftpEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { sessionTftpEntry 9 }

ama OBJECT IDENTIFIER
    ::= { gr1343Core 2 }

amaIn OBJECT IDENTIFIER
    ::= { ama 1 }

amaInTable OBJECT-TYPE
    SYNTAX          SEQUENCE OF AmaInEntry
    MAX-ACCESS      not-accessible
    STATUS          current
    DESCRIPTION     
            "The (conceptual) table of incoming files and records."
    ::= { amaIn 1 }

amaInEntry OBJECT-TYPE
    SYNTAX          AmaInEntry
    MAX-ACCESS      not-accessible
    STATUS          current
    DESCRIPTION     
            "The (conceptual) entry of files and records received from one component that
             communicates with the local host. The sessionCompIndex represents the entry
             in the sessionCompTable that corresponds to the amaInEntry."
    INDEX           { sessionCompIndex }
    ::= { amaInTable 1 }

AmaInEntry ::=
    SEQUENCE {
        amaInPriAmaFiles                Counter32,
        amaInSecAmaFiles                Counter32,
        amaInPriErrFiles                Counter32,
        amaInSecErrFiles                Counter32,
        amaInPriTestFiles               Counter32,
        amaInSecTestFiles               Counter32,
        amaInProgramFiles               Counter32,
        amaInPriorFilesFour             Counter32,
        amaInPriorFilesThree            Counter32,
        amaInPriorFilesTwo              Counter32,
        amaInPriorFilesOne              Counter32,
        amaInLastFileTime               DateAndTime,
        amaInPriFilesMiss               Counter32,
        amaInFilesDupl                  Counter32,
        amaInPriAmaRec                  Counter32,
        amaInSecAmaRec                  Counter32,
        amaInPriErrRecRcv               Counter32,
        amaInSecErrRecRcv               Counter32,
        amaInErrRecDet                  Counter32,
        amaInEntryStatus                INTEGER,
        amaInCriticalLocFileSeqRestart  Counter32,
        amaInMinorLocFileSeqRestart     Counter32,
        amaInRemFileSeqRestart          Counter32
    }

amaInPriAmaFiles OBJECT-TYPE
    SYNTAX          Counter32
    MAX-ACCESS      read-only
    STATUS          current
    DESCRIPTION     
            "The number of primary AMA files received from the component
             corresponding to the sessionCompIndex."
    ::= { amaInEntry 1 }

amaInSecAmaFiles OBJECT-TYPE
    SYNTAX          Counter32
    MAX-ACCESS      read-only
    STATUS          current
    DESCRIPTION     
            "The number of secondary AMA files received from the component
             corresponding to the sessionCompIndex."
    ::= { amaInEntry 2 }

amaInPriErrFiles OBJECT-TYPE
    SYNTAX          Counter32
    MAX-ACCESS      read-only
    STATUS          current
    DESCRIPTION     
            "The number of primary error files received from the component
             corresponding to the sessionCompIndex."
    ::= { amaInEntry 3 }

amaInSecErrFiles OBJECT-TYPE
    SYNTAX          Counter32
    MAX-ACCESS      read-only
    STATUS          current
    DESCRIPTION     
            "The number of secondary error files received from the component
             corresponding to the sessionCompIndex."
    ::= { amaInEntry 4 }

amaInPriTestFiles OBJECT-TYPE
    SYNTAX          Counter32
    MAX-ACCESS      read-only
    STATUS          current
    DESCRIPTION     
            "The number of primary test files received from the component corresponding
             to the sessionCompIndex."
    ::= { amaInEntry 5 }

amaInSecTestFiles OBJECT-TYPE
    SYNTAX          Counter32
    MAX-ACCESS      read-only
    STATUS          current
    DESCRIPTION     
            "The number of secondary test files received from the component
             corresponding to the sessionCompIndex."
    ::= { amaInEntry 6 }

amaInProgramFiles OBJECT-TYPE
    SYNTAX          Counter32
    MAX-ACCESS      read-only
    STATUS          current
    DESCRIPTION     
            "The number of program files received from the component corresponding to
             the sessionCompIndex."
    ::= { amaInEntry 7 }

amaInPriorFilesFour OBJECT-TYPE
    SYNTAX          Counter32
    MAX-ACCESS      read-only
    STATUS          current
    DESCRIPTION     
            "The number of files received with priority level 4 from the component
             corresponding to the sessionCompIndex."
    ::= { amaInEntry 8 }

amaInPriorFilesThree OBJECT-TYPE
    SYNTAX          Counter32
    MAX-ACCESS      read-only
    STATUS          current
    DESCRIPTION     
            "The number of files received with priority level 3 from the component
             corresponding to the sessionCompIndex."
    ::= { amaInEntry 9 }

amaInPriorFilesTwo OBJECT-TYPE
    SYNTAX          Counter32
    MAX-ACCESS      read-only
    STATUS          current
    DESCRIPTION     
            "The number of files received with priority level 2 from the component
             corresponding to the sessionCompIndex."
    ::= { amaInEntry 10 }

amaInPriorFilesOne OBJECT-TYPE
    SYNTAX          Counter32
    MAX-ACCESS      read-only
    STATUS          current
    DESCRIPTION     
            "The number of files received with priority level 1 from the component
             corresponding to the sessionCompIndex."
    ::= { amaInEntry 11 }

amaInLastFileTime OBJECT-TYPE
    SYNTAX          DateAndTime
    MAX-ACCESS      read-only
    STATUS          current
    DESCRIPTION     
            "The date and time the last file was received from the component corresponding
             to sessionCompIndex."
    ::= { amaInEntry 12 }

amaInPriFilesMiss OBJECT-TYPE
    SYNTAX          Counter32
    MAX-ACCESS      read-only
    STATUS          current
    DESCRIPTION     
            "The number of missing primary AMA files supposed to be received from the
             component corresponding to the sessionCompIndex. A trap is generated when
             this counter is incremented."
    ::= { amaInEntry 13 }

amaInFilesDupl OBJECT-TYPE
    SYNTAX          Counter32
    MAX-ACCESS      read-only
    STATUS          current
    DESCRIPTION     
            "The number of duplicated primary AMA files received from the component
             corresponding to the sessionCompIndex. A trap is generated when this
             counter is incremented."
    ::= { amaInEntry 14 }

amaInPriAmaRec OBJECT-TYPE
    SYNTAX          Counter32
    MAX-ACCESS      read-only
    STATUS          current
    DESCRIPTION     
            "The number of primary AMA records received from the component
             corresponding to the sessionCompIndex."
    ::= { amaInEntry 16 }

amaInSecAmaRec OBJECT-TYPE
    SYNTAX          Counter32
    MAX-ACCESS      read-only
    STATUS          current
    DESCRIPTION     
            "The number of secondary AMA records received from the component
             corresponding to the sessionCompIndex."
    ::= { amaInEntry 17 }

amaInPriErrRecRcv OBJECT-TYPE
    SYNTAX          Counter32
    MAX-ACCESS      read-only
    STATUS          current
    DESCRIPTION     
            "The number of primary error records received in error files from the
             component corresponding to the sessionCompIndex."
    ::= { amaInEntry 18 }

amaInSecErrRecRcv OBJECT-TYPE
    SYNTAX          Counter32
    MAX-ACCESS      read-only
    STATUS          current
    DESCRIPTION     
            "The number of secondary error records received in error files from the
             component corresponding to the sessionCompIndex."
    ::= { amaInEntry 19 }

amaInErrRecDet OBJECT-TYPE
    SYNTAX          Counter32
    MAX-ACCESS      read-only
    STATUS          current
    DESCRIPTION     
            "The number of error records created by the local host from erroneous records
             and files detected. These are records and files received from the component
             corresponding to the sessionCompIndex. If the local host cannot determine
             where the files or records were from, this entry is updated and cross-referenced
             with a corresponding sessionCompIndex value of NULL."
    ::= { amaInEntry 20 }

amaInEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { amaInEntry 21 }

amaInCriticalLocFileSeqRestart OBJECT-TYPE
    SYNTAX          Counter32
    MAX-ACCESS      read-only
    STATUS          current
    DESCRIPTION     
            "The number of times the local component cannot initiate the transfer of
             inbound AMA files for a particular file category from the component identified
             by the value of sessionCompIndex because the file sequence number has been
             locally lost. A trap is generated when this counter is incremented."
    ::= { amaInEntry 22 }

amaInMinorLocFileSeqRestart OBJECT-TYPE
    SYNTAX          Counter32
    MAX-ACCESS      read-only
    STATUS          current
    DESCRIPTION     
            "The number of times a primary AMA file sequence number has been restarted
             by the local component for files received from the component corresponding to
             the sessionCompIndex for which the remote component is the initiator. A trap
             is generated when this counter is incremented."
    ::= { amaInEntry 23 }

amaInRemFileSeqRestart OBJECT-TYPE
    SYNTAX          Counter32
    MAX-ACCESS      read-only
    STATUS          current
    DESCRIPTION     
            "The number of times a primary AMA file sequence number has been restarted
             by the remote component for files received from the component corresponding
             to the sessionCompIndex. This condition occurs when the remote component
             sets the file sequence number restart indicator or file sequence number restart
             status to 1. A trap is generated when this counter is incremented."
    ::= { amaInEntry 24 }

amaOut OBJECT IDENTIFIER
    ::= { ama 2 }

amaOutTable OBJECT-TYPE
    SYNTAX          SEQUENCE OF AmaOutEntry
    MAX-ACCESS      not-accessible
    STATUS          current
    DESCRIPTION     
            "The (conceptual) table of outgoing files and records."
    ::= { amaOut 1 }

amaOutEntry OBJECT-TYPE
    SYNTAX          AmaOutEntry
    MAX-ACCESS      not-accessible
    STATUS          current
    DESCRIPTION     
            "The (conceptual) entry of files and records sent to one component that
             communicates with the local host. The sessionCompIndex represents the entry
             in the sessionCompTable that corresponds to the amaOutEntry."
    INDEX           { sessionCompIndex }
    ::= { amaOutTable 1 }

AmaOutEntry ::=
    SEQUENCE {
        amaOutPriAmaFiles               Counter32,
        amaOutSecAmaFiles               Counter32,
        amaOutPriErrFiles               Counter32,
        amaOutSecErrFiles               Counter32,
        amaOutPriTestFiles              Counter32,
        amaOutSecTestFiles              Counter32,
        amaOutProgramFiles              Counter32,
        amaOutPriorFilesFour            Counter32,
        amaOutPriorFilesThree           Counter32,
        amaOutPriorFilesTwo             Counter32,
        amaOutPriorFilesOne             Counter32,
        amaOutPriFilesRem               Gauge32,
        amaOutLastFileTime              DateAndTime,
        amaOutPriFilesMiss              Counter32,
        amaOutFilesDupl                 Counter32,
        amaOutFileSeqRestart            Counter32,
        amaOutPriAmaRec                 Counter32,
        amaOutSecAmaRec                 Counter32,
        amaOutPriErrRec                 Counter32,
        amaOutSecErrRec                 Counter32,
        amaOutEntryStatus               INTEGER
    }

amaOutPriAmaFiles OBJECT-TYPE
    SYNTAX          Counter32
    MAX-ACCESS      read-only
    STATUS          current
    DESCRIPTION     
            "The number of primary AMA files sent to the component corresponding to the
             sessionCompIndex."
    ::= { amaOutEntry 1 }

amaOutSecAmaFiles OBJECT-TYPE
    SYNTAX          Counter32
    MAX-ACCESS      read-only
    STATUS          current
    DESCRIPTION     
            "The number of secondary AMA files sent to the component corresponding to
             the sessionCompIndex."
    ::= { amaOutEntry 2 }

amaOutPriErrFiles OBJECT-TYPE
    SYNTAX          Counter32
    MAX-ACCESS      read-only
    STATUS          current
    DESCRIPTION     
            "The number of primary error files sent to the component corresponding to the
             sessionCompIndex."
    ::= { amaOutEntry 3 }

amaOutSecErrFiles OBJECT-TYPE
    SYNTAX          Counter32
    MAX-ACCESS      read-only
    STATUS          current
    DESCRIPTION     
            "The number of secondary error files sent to the component corresponding to
             the sessionCompIndex."
    ::= { amaOutEntry 4 }

amaOutPriTestFiles OBJECT-TYPE
    SYNTAX          Counter32
    MAX-ACCESS      read-only
    STATUS          current
    DESCRIPTION     
            "The number of primary test files sent to the component corresponding to the
             sessionCompIndex."
    ::= { amaOutEntry 5 }

amaOutSecTestFiles OBJECT-TYPE
    SYNTAX          Counter32
    MAX-ACCESS      read-only
    STATUS          current
    DESCRIPTION     
            "The number of secondary test files sent to the component corresponding to the
             sessionCompIndex."
    ::= { amaOutEntry 6 }

amaOutProgramFiles OBJECT-TYPE
    SYNTAX          Counter32
    MAX-ACCESS      read-only
    STATUS          current
    DESCRIPTION     
            "The number of program files sent to the component corresponding to the
             sessionCompIndex."
    ::= { amaOutEntry 7 }

amaOutPriorFilesFour OBJECT-TYPE
    SYNTAX          Counter32
    MAX-ACCESS      read-only
    STATUS          current
    DESCRIPTION     
            "The number of files with priority level 4 sent to the component corresponding
             to the sessionCompIndex."
    ::= { amaOutEntry 8 }

amaOutPriorFilesThree OBJECT-TYPE
    SYNTAX          Counter32
    MAX-ACCESS      read-only
    STATUS          current
    DESCRIPTION     
            "The number of files with priority level 3 sent to the component corresponding
             to the sessionCompIndex."
    ::= { amaOutEntry 9 }

amaOutPriorFilesTwo OBJECT-TYPE
    SYNTAX          Counter32
    MAX-ACCESS      read-only
    STATUS          current
    DESCRIPTION     
            "The number of files with priority level 2 sent to the component corresponding
             to the sessionCompIndex."
    ::= { amaOutEntry 10 }

amaOutPriorFilesOne OBJECT-TYPE
    SYNTAX          Counter32
    MAX-ACCESS      read-only
    STATUS          current
    DESCRIPTION     
            "The number of files with priority level 1 sent to the component corresponding
             to the sessionCompIndex."
    ::= { amaOutEntry 11 }

amaOutPriFilesRem OBJECT-TYPE
    SYNTAX          Gauge32
    MAX-ACCESS      read-only
    STATUS          current
    DESCRIPTION     
            "The number of primary AMA files remaining to be sent to the component
             corresponding to the sessionCompIndex."
    ::= { amaOutEntry 12 }

amaOutLastFileTime OBJECT-TYPE
    SYNTAX          DateAndTime
    MAX-ACCESS      read-only
    STATUS          current
    DESCRIPTION     
            "The date and time the last file was sent to the component corresponding to
             sessionCompIndex."
    ::= { amaOutEntry 13 }

amaOutPriFilesMiss OBJECT-TYPE
    SYNTAX          Counter32
    MAX-ACCESS      read-only
    STATUS          current
    DESCRIPTION     
            "The number of missing primary AMA files (e.g., based on gaps in the File
             Sequence Number) which were to be sent to the component corresponding to
             the sessionCompIndex. A trap is generated when this counter is incremented."
    ::= { amaOutEntry 14 }

amaOutFilesDupl OBJECT-TYPE
    SYNTAX          Counter32
    MAX-ACCESS      read-only
    STATUS          current
    DESCRIPTION     
            "The number of times a primary AMA file to be sent to the component
             corresponding to the sessionCompIndex has been locally duplicated (e.g.,
             based on duplicate file names). A trap is generated when this counter is
             incremented."
    ::= { amaOutEntry 15 }

amaOutFileSeqRestart OBJECT-TYPE
    SYNTAX          Counter32
    MAX-ACCESS      read-only
    STATUS          current
    DESCRIPTION     
            "The number of times a primary AMA file sequence number has been locally
             restarted for files sent to the component corresponding to the
             sessionCompIndex. A trap is generated when this counter is incremented."
    ::= { amaOutEntry 16 }

amaOutPriAmaRec OBJECT-TYPE
    SYNTAX          Counter32
    MAX-ACCESS      read-only
    STATUS          current
    DESCRIPTION     
            "The number of primary AMA records sent in AMA files to the component
             corresponding to the sessionCompIndex."
    ::= { amaOutEntry 17 }

amaOutSecAmaRec OBJECT-TYPE
    SYNTAX          Counter32
    MAX-ACCESS      read-only
    STATUS          current
    DESCRIPTION     
            "The number of secondary AMA records sent in AMA files to the component
             corresponding to the sessionCompIndex."
    ::= { amaOutEntry 18 }

amaOutPriErrRec OBJECT-TYPE
    SYNTAX          Counter32
    MAX-ACCESS      read-only
    STATUS          current
    DESCRIPTION     
            "The number of primary error records sent in error files to the component
             corresponding to the sessionCompIndex."
    ::= { amaOutEntry 19 }

amaOutSecErrRec OBJECT-TYPE
    SYNTAX          Counter32
    MAX-ACCESS      read-only
    STATUS          current
    DESCRIPTION     
            "The number of secondary error records sent in error files to the component
             corresponding to the sessionCompIndex."
    ::= { amaOutEntry 20 }

amaOutEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { amaOutEntry 21 }

amaLimit OBJECT IDENTIFIER
    ::= { ama 3 }

amaLimitFileBytesIn OBJECT-TYPE
    SYNTAX          Integer32
    MAX-ACCESS      read-write
    STATUS          current
    DESCRIPTION     
            "The maximum file size (expressed in bytes) for any file being received. The
             default value is 4,294,967,295."
    ::= { amaLimit 1 }

amaLimitFileRecIn OBJECT-TYPE
    SYNTAX          Integer32 (0..16777215)
    MAX-ACCESS      read-write
    STATUS          current
    DESCRIPTION     
            "The maximum file size (expressed in records) for any file being received. The
             default value is 16,777,215."
    ::= { amaLimit 2 }

amaLimitFileBytesOut OBJECT-TYPE
    SYNTAX          Integer32
    MAX-ACCESS      read-write
    STATUS          current
    DESCRIPTION     
            "The maximum file size (expressed in bytes) for any file being sent. The default
             value is 4,294,967,295."
    ::= { amaLimit 3 }

amaLimitFileRecOut OBJECT-TYPE
    SYNTAX          Integer32 (0..16777215)
    MAX-ACCESS      read-write
    STATUS          current
    DESCRIPTION     
            "The maximum file size (expressed in records) for any file being sent. The
             default value is 16,777,215."
    ::= { amaLimit 4 }

amaLimitFileBlockOut OBJECT-TYPE
    SYNTAX          Integer32 (0..32760)
    MAX-ACCESS      read-write
    STATUS          current
    DESCRIPTION     
            "The maximum block size (expressed in bytes) for any block being sent to a
             RAO from the DPMS. The default value is 32,760. This value must be less than
             the value of amaLimitFileBytesOut."
    ::= { amaLimit 5 }

amaStorage OBJECT IDENTIFIER
    ::= { ama 4 }

amaStorageTable OBJECT-TYPE
    SYNTAX          SEQUENCE OF AmaStorageEntry
    MAX-ACCESS      not-accessible
    STATUS          current
    DESCRIPTION     
            "The (conceptual) table of long-term storage devices contained by the host for
             AMA data storage. A (conceptual) entry exists only if a correspondent value of
             hrDeviceType (from the Host Resources MIB module) object is
             `hrDeviceDiskStorage'."
    ::= { amaStorage 1 }

amaStorageEntry OBJECT-TYPE
    SYNTAX          AmaStorageEntry
    MAX-ACCESS      not-accessible
    STATUS          current
    DESCRIPTION     
            "A (conceptual) entry for one long-term storage device contained by the host.
             The hrDeviceIndex (from the Host Resources MIB module) in the index
             represents the entry in the hrDeviceTable (from the Host Resources MIB
             module) that corresponds to the amaStorageEntry."
    INDEX           { hrDeviceIndex }
    ::= { amaStorageTable 1 }

AmaStorageEntry ::=
    SEQUENCE {
        amaStorageTotalOccuLevel        Gauge32,
        amaStoragePriOccuLevel          Gauge32,
        amaStoragePriOccuThres          Integer32,
        amaStorageAmaFiles              Gauge32,
        amaStorageAmaRecords            Gauge32,
        amaStorageErrorFiles            Gauge32,
        amaStorageErrorRecords          Gauge32,
        amaStorageDbRecords             Gauge32,
        amaStorageDbOccuLevel           Gauge32,
        amaStorageEntryStatus           INTEGER
    }

amaStorageTotalOccuLevel OBJECT-TYPE
    SYNTAX          Gauge32
    MAX-ACCESS      read-only
    STATUS          current
    DESCRIPTION     
            "Percentage of hrDeviceIndex (from the Host Resources MIB module) mass
             storage occupied (e.g., 45 = 45%)."
    ::= { amaStorageEntry 1 }

amaStoragePriOccuLevel OBJECT-TYPE
    SYNTAX          Gauge32 (0..100)
    MAX-ACCESS      read-only
    STATUS          current
    DESCRIPTION     
            "Percentage of hrDeviceIndex (from the Host Resources MIB module) mass
             storage occupied by primary AMA data (e.g., 45 = 45%)."
    ::= { amaStorageEntry 2 }

amaStoragePriOccuThres OBJECT-TYPE
    SYNTAX          Integer32 (0..100)
    MAX-ACCESS      read-write
    STATUS          current
    DESCRIPTION     
            "The primary AMA data occupancy level threshold (e.g., 90 = 90%). The default
             value is 90."
    ::= { amaStorageEntry 3 }

amaStorageAmaFiles OBJECT-TYPE
    SYNTAX          Gauge32
    MAX-ACCESS      read-only
    STATUS          current
    DESCRIPTION     
            "Number of primary AMA files currently on the hrDeviceIndex (from the Host
             Resources MIB module) storage device."
    ::= { amaStorageEntry 4 }

amaStorageAmaRecords OBJECT-TYPE
    SYNTAX          Gauge32
    MAX-ACCESS      read-only
    STATUS          current
    DESCRIPTION     
            "Number of primary AMA records, contained in AMA files, currently on the
             hrDeviceIndex (from the Host Resources MIB module) storage device."
    ::= { amaStorageEntry 5 }

amaStorageErrorFiles OBJECT-TYPE
    SYNTAX          Gauge32
    MAX-ACCESS      read-only
    STATUS          current
    DESCRIPTION     
            "Number of primary error files currently on the hrDeviceIndex (from the Host
             Resources MIB module) storage device."
    ::= { amaStorageEntry 6 }

amaStorageErrorRecords OBJECT-TYPE
    SYNTAX          Gauge32
    MAX-ACCESS      read-only
    STATUS          current
    DESCRIPTION     
            "Number of primary error records, contained in Error files, currently on the
             hrDeviceIndex storage device."
    ::= { amaStorageEntry 7 }

amaStorageDbRecords OBJECT-TYPE
    SYNTAX          Gauge32
    MAX-ACCESS      read-only
    STATUS          current
    DESCRIPTION     
            "Number of AMA Database records currently on the hrDeviceIndex (from the
             Host Resources MIB module) storage device."
    ::= { amaStorageEntry 8 }

amaStorageDbOccuLevel OBJECT-TYPE
    SYNTAX          Gauge32
    MAX-ACCESS      read-only
    STATUS          current
    DESCRIPTION     
            "Percentage of hrDeviceIndex (from the Host Resources MIB module) mass
             storage occupied by AMA Database data (e.g., 45 = 45%)."
    ::= { amaStorageEntry 9 }

amaStorageEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { amaStorageEntry 10 }

amaAudit OBJECT IDENTIFIER
    ::= { ama 5 }

amaAuditTable OBJECT-TYPE
    SYNTAX          SEQUENCE OF AmaAuditEntry
    MAX-ACCESS      not-accessible
    STATUS          current
    DESCRIPTION     
            "The (conceptual) table of auditing information, containing counts of incoming
             and outgoing primary AMA records, counts of changes to the number of
             primary AMA records in storage, and counts of primary AMA records upon
             which specialized processing has been performed. Each row contains
             accumulated counts of records processed over a fifteen-minute interval of the
             day. Row 0 represents midnight-12:15 AM, row 1 represents 12:15-12:30 AM, and
             so forth, until row 95, which represents 11:45 PM- midnight."
    ::= { amaAudit 1 }

amaAuditEntry OBJECT-TYPE
    SYNTAX          AmaAuditEntry
    MAX-ACCESS      not-accessible
    STATUS          current
    DESCRIPTION     
            "The (conceptual) entry of counts of changes to the number of records in
             storage, and counts of records upon which special processing has been
             performed, for a single fifteen-minute time interval."
    INDEX           { amaAuditTimeIndex }
    ::= { amaAuditTable 1 }

AmaAuditEntry ::=
    SEQUENCE {
        amaAuditTimeIndex               Integer32,
        amaAuditAMARecsIn               Counter32,
        amaAuditAMARecsOut              Counter32,
        amaAuditAMARecsConsolidated     Counter32,
        amaAuditAMARecsIntroduced       Counter32,
        amaAuditChangeInAMARecsStored   Integer32,
        amaAuditAMACalcRecsLost         Counter32,
        amaAuditAMACalcRecsDupl         Counter32,
        amaAuditAMADetectRecsLost       Counter32,
        amaAuditAMADetectRecsDupl       Counter32
    }

amaAuditTimeIndex OBJECT-TYPE
    SYNTAX          Integer32 (0..95)
    MAX-ACCESS      read-only
    STATUS          current
    DESCRIPTION     
            "The index to the rows of the AmaAuditSPMTable, and one of the indices to the
             rows of the amaAuditInOutTable. Each integer represents a fifteen-minute
             interval of the day, with the index '0' corresponding to midnight-12:15 AM, and
             the index '95' corresponding to 11:45 PM-midnight."
    ::= { amaAuditEntry 1 }

amaAuditAMARecsIn OBJECT-TYPE
    SYNTAX          Counter32
    MAX-ACCESS      read-only
    STATUS          current
    DESCRIPTION     
            "The total number of primary AMA records which arrive over any interface
             (network interface or removable media interface) in the time interval specified
             by the amaAuditTimeIndex."
    ::= { amaAuditEntry 2 }

amaAuditAMARecsOut OBJECT-TYPE
    SYNTAX          Counter32
    MAX-ACCESS      read-only
    STATUS          current
    DESCRIPTION     
            "The total number of primary AMA records which depart (i.e., become non-primary)
             over any interface (network interface or removable media interface)
             in the time interval specified by the amaAuditTimeIndex."
    ::= { amaAuditEntry 3 }

amaAuditAMARecsConsolidated OBJECT-TYPE
    SYNTAX          Counter32
    MAX-ACCESS      read-only
    STATUS          current
    DESCRIPTION     
            "The number of primary AMA records removed by the aggregation operation in
             the time interval specified by the amaAuditTimeIndex. For example, if 10
             primary AMA records are aggregated and 1 composite record is produced, this
             counter should be incremented by 9."
    ::= { amaAuditEntry 4 }

amaAuditAMARecsIntroduced OBJECT-TYPE
    SYNTAX          Counter32
    MAX-ACCESS      read-only
    STATUS          current
    DESCRIPTION     
            "The number of primary AMA records created by the distribution or
             decomposition operations in the time interval specified by the
             amaAuditTimeIndex. For example, if 1 primary AMA record is distributed to 10
             Application Systems, this counter should be incremented by 9."
    ::= { amaAuditEntry 5 }

amaAuditChangeInAMARecsStored OBJECT-TYPE
    SYNTAX          Integer32
    MAX-ACCESS      read-only
    STATUS          current
    DESCRIPTION     
            "The change in the number of primary AMA records residing in mass storage in
             the time interval specified by the amaAuditTimeIndex."
    ::= { amaAuditEntry 6 }

amaAuditAMACalcRecsLost OBJECT-TYPE
    SYNTAX          Counter32
    MAX-ACCESS      read-only
    STATUS          current
    DESCRIPTION     
            "The number of primary AMA records calculated to have been lost in the time
             interval specified by the amaAuditTimeIndex. A trap is generated when this
             counter is incremented."
    ::= { amaAuditEntry 7 }

amaAuditAMACalcRecsDupl OBJECT-TYPE
    SYNTAX          Counter32
    MAX-ACCESS      read-only
    STATUS          current
    DESCRIPTION     
            "The number of primary AMA records calculated to have been unintentionally
             duplicated in the time interval specified by the amaAuditTimeIndex. A trap is
             generated when this counter is incremented."
    ::= { amaAuditEntry 8 }

amaAuditAMADetectRecsLost OBJECT-TYPE
    SYNTAX          Counter32
    MAX-ACCESS      read-only
    STATUS          current
    DESCRIPTION     
            "The number of primary AMA records detected to have been lost in the time
             interval specified by the amaAuditTimeIndex. A trap is generated when this
             counter is incremented."
    ::= { amaAuditEntry 9 }

amaAuditAMADetectRecsDupl OBJECT-TYPE
    SYNTAX          Counter32
    MAX-ACCESS      read-only
    STATUS          current
    DESCRIPTION     
            "The number of primary AMA records detected to have been unintentionally
             duplicated in the time interval specified by the amaAuditTimeIndex. A trap is
             generated when this counter is incremented."
    ::= { amaAuditEntry 10 }

access OBJECT IDENTIFIER
    ::= { gr1343Core 3 }

accessLogin OBJECT IDENTIFIER
    ::= { access 1 }

accessLoginTable OBJECT-TYPE
    SYNTAX          SEQUENCE OF AccessLoginEntry
    MAX-ACCESS      not-accessible
    STATUS          current
    DESCRIPTION     
            "The (conceptual) table of users' identification, authentication and access
             control information. A user could be a human or machine."
    ::= { accessLogin 1 }

accessLoginEntry OBJECT-TYPE
    SYNTAX          AccessLoginEntry
    MAX-ACCESS      not-accessible
    STATUS          current
    DESCRIPTION     
            "The (conceptual) entry for a user's access information."
    INDEX           { accessLoginIndex }
    ::= { accessLoginTable 1 }

AccessLoginEntry ::=
    SEQUENCE {
        accessLoginIndex                Integer32,
        accessLoginLoginId              DisplayString,
        accessLoginPassword             DisplayString,
        accessLoginCommunityName        DisplayString,
        accessLoginNumLogins            Counter32,
        accessLoginLastLogin            DateAndTime,
        accessLoginAuthorFtp            INTEGER,
        accessLoginAuthorRda            INTEGER,
        accessLoginAuthorTelnet         INTEGER,
        accessLoginAuthorTftp           INTEGER,
        accessLoginEntryStatus          INTEGER
    }

accessLoginIndex OBJECT-TYPE
    SYNTAX          Integer32 (1..2147483647)
    MAX-ACCESS      read-write
    STATUS          current
    DESCRIPTION     
            "A unique value identifying the user."
    ::= { accessLoginEntry 1 }

accessLoginLoginId OBJECT-TYPE
    SYNTAX          DisplayString (SIZE(6..20))
    MAX-ACCESS      read-write
    STATUS          current
    DESCRIPTION     
            "The user's login ID. This string is used for local identification and for remote
             identification via FTP, Telnet and (if supported) RDA."
    ::= { accessLoginEntry 2 }

accessLoginPassword OBJECT-TYPE
    SYNTAX          DisplayString (SIZE(6..20))
    MAX-ACCESS      read-write
    STATUS          current
    DESCRIPTION     
            "The user's plaintext password. This string is used for local authentication and/
             or for remote identification via FTP, Telnet and (if supported) RDA."
    ::= { accessLoginEntry 3 }

accessLoginCommunityName OBJECT-TYPE
    SYNTAX          DisplayString (SIZE(6..20))
    MAX-ACCESS      read-write
    STATUS          current
    DESCRIPTION     
            "The user's community name. This string is sent in SNMPv1 PDUs."
    ::= { accessLoginEntry 4 }

accessLoginNumLogins OBJECT-TYPE
    SYNTAX          Counter32
    MAX-ACCESS      read-only
    STATUS          current
    DESCRIPTION     
            "The total number of logins to the local host by the user via local login, FTP,
             Telnet and (if supported) RDA."
    ::= { accessLoginEntry 5 }

accessLoginLastLogin OBJECT-TYPE
    SYNTAX          DateAndTime
    MAX-ACCESS      read-only
    STATUS          current
    DESCRIPTION     
            "The date and time of the last successful login to the local host by the user."
    ::= { accessLoginEntry 6 }

accessLoginAuthorFtp OBJECT-TYPE
    SYNTAX          INTEGER { yes(1), no(2), unknown(3) }
    MAX-ACCESS      read-write
    STATUS          current
    DESCRIPTION     
            "Indicates if the user is authorized to set up an FTP session to/from the local
             host."
    ::= { accessLoginEntry 7 }

accessLoginAuthorRda OBJECT-TYPE
    SYNTAX          INTEGER { yes(1), no(2), unknown(3) }
    MAX-ACCESS      read-write
    STATUS          current
    DESCRIPTION     
            "Indicates if the user is authorized to set up an RDA session to/from the local
             host."
    ::= { accessLoginEntry 8 }

accessLoginAuthorTelnet OBJECT-TYPE
    SYNTAX          INTEGER { yes(1), no(2), unknown(3) }
    MAX-ACCESS      read-write
    STATUS          current
    DESCRIPTION     
            "Indicates if the user is authorized to set up a Telnet session to/from the local
             host."
    ::= { accessLoginEntry 9 }

accessLoginAuthorTftp OBJECT-TYPE
    SYNTAX          INTEGER { yes(1), no(2), unknown(3) }
    MAX-ACCESS      read-write
    STATUS          current
    DESCRIPTION     
            "Indicates if the user is authorized to set up a TFTP session to/from the local
             host."
    ::= { accessLoginEntry 10 }

accessLoginEntryStatus OBJECT-TYPE
    SYNTAX          INTEGER { valid(1), invalid(2) }
    MAX-ACCESS      read-write
    STATUS          current
    DESCRIPTION     
            "This object indicates if a table entry is valid or invalid. The value of this object
             is set to 1 when the entry is active and is set to 2 when the entry is inactive."
    ::= { accessLoginEntry 11 }

accessAssociation OBJECT IDENTIFIER
    ::= { access 2 }

accessAssociationTable OBJECT-TYPE
    SYNTAX          SEQUENCE OF AccessAssociationEntry
    MAX-ACCESS      not-accessible
    STATUS          current
    DESCRIPTION     
            "The (conceptual) table of IP security association information."
    ::= { accessAssociation 1 }

accessAssociationEntry OBJECT-TYPE
    SYNTAX          AccessAssociationEntry
    MAX-ACCESS      not-accessible
    STATUS          current
    DESCRIPTION     
            "The (conceptual) entry for one destination component's security association
             information."
    INDEX           { sessionCompIndex }
    ::= { accessAssociationTable 1 }

AccessAssociationEntry ::=
    SEQUENCE {
        accessAssociationAHAlg          INTEGER,
        accessAssociationAHKey          OCTET STRING,
        accessAssociationAHKeySize      Integer32,
        accessAssociationESPAlg         INTEGER,
        accessAssociationESPKey         OCTET STRING,
        accessAssociationESPKeySize     Integer32,
        accessAssociationIVPresence     INTEGER,
        accessAssociationIVSize         Integer32
    }

accessAssociationAHAlg OBJECT-TYPE
    SYNTAX          INTEGER { noah(1), keyedmd5(2) }
    MAX-ACCESS      read-write
    STATUS          current
    DESCRIPTION     
            "Indicates the authentication algorithm and algorithm mode being used with the
             IP Authentication Header (AH) mechanism."
    ::= { accessAssociationEntry 1 }

accessAssociationAHKey OBJECT-TYPE
    SYNTAX          OCTET STRING (SIZE(8..128))
    MAX-ACCESS      read-write
    STATUS          current
    DESCRIPTION     
            "The key used with the AH authentication algorithm. The key is a bit string
             which contains a minimum of 64 bits and a maximum of 1024 bits. The security
             key has no translation into an integer or characters."
    ::= { accessAssociationEntry 2 }

accessAssociationAHKeySize OBJECT-TYPE
    SYNTAX          Integer32 (64..1024)
    MAX-ACCESS      read-write
    STATUS          current
    DESCRIPTION     
            "Indicates the number of low-order bits for the key used with the AH
             authentication algorithm."
    ::= { accessAssociationEntry 3 }

accessAssociationESPAlg OBJECT-TYPE
    SYNTAX          INTEGER { noesp(1), descbc(2) }
    MAX-ACCESS      read-write
    STATUS          current
    DESCRIPTION     
            "Indicates the encryption algorithm and algorithm mode being used with the IP
             Encapsulating Security Payload (ESP) mechanism."
    ::= { accessAssociationEntry 4 }

accessAssociationESPKey OBJECT-TYPE
    SYNTAX          OCTET STRING (SIZE(8..128))
    MAX-ACCESS      read-write
    STATUS          current
    DESCRIPTION     
            "The key used with the ESP encryption algorithm. The key is a bit string which
             contains a minimum of 64 bits and a maximum of 1024 bits. The security key has
             no translation into an integer or characters."
    ::= { accessAssociationEntry 5 }

accessAssociationESPKeySize OBJECT-TYPE
    SYNTAX          Integer32 (64..1024)
    MAX-ACCESS      read-write
    STATUS          current
    DESCRIPTION     
            "Indicates the number of low-order bits for the key used with the ESP
             encryption algorithm."
    ::= { accessAssociationEntry 6 }

accessAssociationIVPresence OBJECT-TYPE
    SYNTAX          INTEGER { present(1), absent(2) }
    MAX-ACCESS      read-write
    STATUS          current
    DESCRIPTION     
            "Indicates the presence/absence of the Initialization Vector used with the ESP
             algorithm. The IV enables the encryption algorithm to decrypt datagrams
             without having to receive the remaining segments of the ESP payload."
    ::= { accessAssociationEntry 7 }

accessAssociationIVSize OBJECT-TYPE
    SYNTAX          Integer32 (1..256)
    MAX-ACCESS      read-write
    STATUS          current
    DESCRIPTION     
            "Indicates the number of bits for the Initialization Vector used with the ESP
             encryption algorithm."
    ::= { accessAssociationEntry 8 }

END -- end of module Gr1343Core-MIB.
